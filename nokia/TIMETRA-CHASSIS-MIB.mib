TIMETRA-CHASSIS-MIB DEFINITIONS ::= BEGIN

IMPORTS
    SnmpAdminString
                                                         FROM SNMP-FRAMEWORK-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DateAndTime, DisplayString, MacAddress,
    RowPointer, RowStatus,
    TEXTUAL-CONVENTION, TimeInterval,
    TimeStamp, TruthValue
                                                         FROM SNMPv2-TC
    timetraSRMIBModules, tmnxSRConfs,
    tmnxSRNotifyPrefix, tmnxSRObjs
                                                         FROM TIMETRA-GLOBAL-MIB
    Dot1PUntagValue, THPolCIRRateOverride,
    THPolPIRRateOverride, TIngPolicerId,
    TItemDescription, TItemLongDescription,
    TItemVeryLongDescription,
    TLNamedItemOrEmpty, TLevel, TNamedItem,
    TNamedItemOrEmpty, TPerPacketOffsetOvr,
    TPlcrBurstSizeBytesOverride,
    TPolicerBurstSizeBytesOverride,
    TmnxActionType, TmnxAdminState,
    TmnxCamOverloadState,
    TmnxEnabledDisabled,
    TmnxEnabledDisabledOrNA, TmnxFPNumber,
    TmnxIngPolicerStatMode,
    TmnxIngPolicerStatModeOverride,
    TmnxInternalSchedWeightMode,
    TmnxIpSecIsaOperFlags, TmnxOperState,
    TmnxPortID,
    TmnxPortOptComplianceExtType, TmnxUuid
                                                         FROM TIMETRA-TC-MIB
    ;

tmnxChassisMIBModule             MODULE-IDENTITY
    LAST-UPDATED "201707010000Z"
    ORGANIZATION "Nokia"
    CONTACT-INFO
        "Nokia SROS Support
         Web: http://www.nokia.com"
    DESCRIPTION
        "This document is the SNMP MIB module to manage and provision the
         hardware components of the Nokia 7x50 device.

         Copyright 2003-2018 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201707010000Z"
    DESCRIPTION
        "Rev 16.0               01 Jul 2017 00:00
         16.0 release of the TIMETRA-CHASSIS-MIB."

    REVISION    "201601010000Z"
    DESCRIPTION
        "Rev 14.0               01 Jan 2016 00:00
         14.0 release of the TIMETRA-CHASSIS-MIB."

    REVISION    "201501010000Z"
    DESCRIPTION
        "Rev 13.0               01 Jan 2015 00:00
         13.0 release of the TIMETRA-CHASSIS-MIB."

    REVISION    "201401010000Z"
    DESCRIPTION
        "Rev 12.0               01 Jan 2014 00:00
         12.0 release of the TIMETRA-CHASSIS-MIB."

    REVISION    "201102010000Z"
    DESCRIPTION
        "Rev 9.0                01 Feb 2011 00:00
         9.0 release of the TIMETRA-CHASSIS-MIB."

    REVISION    "200902280000Z"
    DESCRIPTION
        "Rev 7.0                28 Feb 2009 00:00
         7.0 release of the TIMETRA-CHASSIS-MIB."

    REVISION    "200807010000Z"
    DESCRIPTION
        "Rev 6.1                01 Jul 2008 00:00
         6.1 release of the TIMETRA-CHASSIS-MIB."

    REVISION    "200801010000Z"
    DESCRIPTION
        "Rev 6.0                01 Jan 2008 00:00
         6.0 release of the TIMETRA-CHASSIS-MIB."

    REVISION    "200701010000Z"
    DESCRIPTION
        "Rev 5.0                01 Jan 2007 00:00
         5.0 release of the TIMETRA-CHASSIS-MIB."

    REVISION    "200603160000Z"
    DESCRIPTION
        "Rev 4.0                16 Mar 2006 00:00
         4.0 release of the TIMETRA-CHASSIS-MIB."

    REVISION    "200508310000Z"
    DESCRIPTION
        "Rev 3.0                31 Aug 2005 00:00
         3.0 release of the TIMETRA-CHASSIS-MIB."

    REVISION    "200501240000Z"
    DESCRIPTION
        "Rev 2.1                24 Jan 2005 00:00
         2.1 release of the TIMETRA-CHASSIS-MIB."

    REVISION    "200401150000Z"
    DESCRIPTION
        "Rev 2.0                15 Jan 2004 00:00
         2.0 release of the TIMETRA-CHASSIS-MIB."

    REVISION    "200308150000Z"
    DESCRIPTION
        "Rev 1.2                15 Aug 2003 00:00
         1.2 release of the TIMETRA-CHASSIS-MIB."

    REVISION    "200301200000Z"
    DESCRIPTION
        "Rev 1.0                20 Jan 2003 00:00
         Release 1.0 of the TIMETRA-CHASSIS-MIB."

    REVISION    "200008140000Z"
    DESCRIPTION
        "Rev 0.1                14 Aug 2000 00:00
         Initial version of the TIMETRA-CHASSIS-MIB."

    ::= { timetraSRMIBModules 2 }

TmnxAlarmState                   ::= TEXTUAL-CONVENTION
    STATUS      current
    DESCRIPTION
        "The TmnxAlarmState is an enumerated integer whose value indicates the
         current alarm state of a physical or logical component in the Nokia
         SROS series system."
    SYNTAX      INTEGER {
        unknown      (0),
        alarmActive  (1),
        alarmCleared (2)
    }

TmnxChassisIndex                 ::= TEXTUAL-CONVENTION
    STATUS      current
    DESCRIPTION
        "The TmnxChassisIndex is a unique index that identifies a chassis
         within an Nokia SROS system.  Note that initial releases will
         support only one chassis in a system."
    SYNTAX      Integer32 (1..32)

TmnxChassisIndexOrZero           ::= TEXTUAL-CONVENTION
    STATUS      current
    DESCRIPTION
        "The TmnxChassisIndexOrZero can be either a nonzero TmnxChassisIndex,
         or the value zero."
    SYNTAX      Integer32 (0..32)

TmnxPhysChassisIndex             ::= TEXTUAL-CONVENTION
    STATUS      current
    DESCRIPTION
        "The TmnxPhysChassisIndex is a unique index that identifies a physical
         chassis within Nokia SROS system."
    SYNTAX      Integer32 (1..100)

TmnxPhysChassisIndexOrZero       ::= TEXTUAL-CONVENTION
    STATUS      current
    DESCRIPTION
        "The TmnxPhysChassisIndexOrZero can be either a nonzero
         TmnxPhysChassisIndex, or the value zero."
    SYNTAX      Integer32 (0..100)

TmnxHwIndex                      ::= TEXTUAL-CONVENTION
    STATUS      current
    DESCRIPTION
        "The TmnxHwIndex is a unique integer index that identifies an Nokia
         SROS series manufactured hardware component, such as an IOM, CPM,
         Fabric or MDA card."
    SYNTAX      Integer32 (1..2147483647)

TmnxHwIndexOrZero                ::= TEXTUAL-CONVENTION
    STATUS      current
    DESCRIPTION
        "The TmnxHwIndexOrZero is a unique integer index that identifies an
         Nokia SROS series manufactured hardware component, such as an IOM,
         CPM, Fabric or MDA card. Also TmnxHwIndexOrZero can be zero."
    SYNTAX      Integer32 (0..2147483647)

TmnxHwClass                      ::= TEXTUAL-CONVENTION
    STATUS      current
    DESCRIPTION
        "TmnxHwClass is an enumerated integer that identifies the general
         hardware type of a component in the tmnxHwTable."
    SYNTAX      INTEGER {
        other                (1),
        unknown              (2),
        physChassis          (3),
        container            (4),
        powerSupply          (5),
        fan                  (6),
        sensor               (7),
        ioModule             (8),
        cpmModule            (9),
        fabricModule         (10),
        mdaModule            (11),
        flashDiskModule      (12),
        port                 (13),
        ccm                  (15),
        alarmInputModule     (19),
        pcm                  (20),
        powerShelf           (21),
        powerShelfController (22),
        cpmCarrier           (23),
        xioModule            (24)
    }

TmnxPhysChassisClass             ::= TEXTUAL-CONVENTION
    STATUS      current
    DESCRIPTION
        "TmnxPhysChassisClass is an enumerated integer that identifies the
         general physical chassis class in the tmnxPhysChassisTable. It is also
         used to indicate a sub-class of the TmnxHwClass type in a tmnxHwIndex.
         A value of 0 instead of 'routerChassis (3)' is used in tmnxHwIndex to
         represent router chassis.

         Values:
            other             (1) - Other chassis class
            unknown           (2) - Unknown chassis class
            routerChassis     (3) - Router chassis class
            ethSatChassis     (5) - Ethernet Satellite chassis class
            esaChassis        (7) - Extended Services Appliance chassis class
            "
    SYNTAX      INTEGER {
        other         (1),
        unknown       (2),
        routerChassis (3),
        ethSatChassis (5),
        reserved6     (6),
        esaChassis    (7)
    }

TmnxPhysChassisRole              ::= TEXTUAL-CONVENTION
    STATUS      current
    DESCRIPTION
        "The TmnxPhysChassisRole is an enumerated integer that indicates the
         general Physical Chassis role an individual physical chassis is
         provisioned to support.

         Values:
            standalone     (1)  - A chassis that is operating in a system
                                  with no more than one router chassis
            master         (2)  - The master router chassis in a 7950 XRS-40
                                  system
            extension      (3)  - An extension router chassis a 7950 XRS-40
                                  system
            sat-ethernet   (6)  - An Ethernet satellite chassis
            "
    SYNTAX      INTEGER {
        standalone   (1),
        master       (2),
        extension    (3),
        sat-ethernet (6),
        reserved7    (7)
    }

TmnxCardType                     ::= TEXTUAL-CONVENTION
    STATUS      current
    DESCRIPTION
        "TmnxCardType is an index into the tmnxCardTypeTable used to identify a
         specific type of card."
    SYNTAX      Unsigned32

TmnxCardSuppType                 ::= TEXTUAL-CONVENTION
    STATUS      current
    DESCRIPTION
        "The TmnxCardSuppType is a bit-mask specifying the valid card types
         supported for a specific card slot.

         When multiple bits are set, it can be used to identify a set or list
         of card types used in the tmnxCardTable and tmnxCpmCardTable to
         indicate supported cards within a specific chassis slot. Some example
         card types might be:

                    sfm-400g  -- 400g CPM/SF module
                    sfm-200g  -- 200g CPM/SF module
                    iom-20g   -- 2 x 10-Gig MDA IOM Card"
    SYNTAX      BITS {
        invalid-card-type  (0),
        unassigned         (1),
        supp-card-type-2   (2),
        supp-card-type-3   (3),
        supp-card-type-4   (4),
        supp-card-type-5   (5),
        supp-card-type-6   (6),
        supp-card-type-7   (7),
        supp-card-type-8   (8),
        supp-card-type-9   (9),
        supp-card-type-10  (10),
        supp-card-type-11  (11),
        supp-card-type-12  (12),
        supp-card-type-13  (13),
        supp-card-type-14  (14),
        supp-card-type-15  (15),
        supp-card-type-16  (16),
        supp-card-type-17  (17),
        supp-card-type-18  (18),
        supp-card-type-19  (19),
        supp-card-type-20  (20),
        supp-card-type-21  (21),
        supp-card-type-22  (22),
        supp-card-type-23  (23),
        supp-card-type-24  (24),
        supp-card-type-25  (25),
        supp-card-type-26  (26),
        supp-card-type-27  (27),
        supp-card-type-28  (28),
        supp-card-type-29  (29),
        supp-card-type-30  (30),
        supp-card-type-31  (31),
        supp-card-type-32  (32),
        supp-card-type-33  (33),
        supp-card-type-34  (34),
        supp-card-type-35  (35),
        supp-card-type-36  (36),
        supp-card-type-37  (37),
        supp-card-type-38  (38),
        supp-card-type-39  (39),
        supp-card-type-40  (40),
        supp-card-type-41  (41),
        supp-card-type-42  (42),
        supp-card-type-43  (43),
        supp-card-type-44  (44),
        supp-card-type-45  (45),
        supp-card-type-46  (46),
        supp-card-type-47  (47),
        supp-card-type-48  (48),
        supp-card-type-49  (49),
        supp-card-type-50  (50),
        supp-card-type-51  (51),
        supp-card-type-52  (52),
        supp-card-type-53  (53),
        supp-card-type-54  (54),
        supp-card-type-55  (55),
        supp-card-type-56  (56),
        supp-card-type-57  (57),
        supp-card-type-58  (58),
        supp-card-type-59  (59),
        supp-card-type-60  (60),
        supp-card-type-61  (61),
        supp-card-type-62  (62),
        supp-card-type-63  (63),
        supp-card-type-64  (64),
        supp-card-type-65  (65),
        supp-card-type-66  (66),
        supp-card-type-67  (67),
        supp-card-type-68  (68),
        supp-card-type-69  (69),
        supp-card-type-70  (70),
        supp-card-type-71  (71),
        supp-card-type-72  (72),
        supp-card-type-73  (73),
        supp-card-type-74  (74),
        supp-card-type-75  (75),
        supp-card-type-76  (76),
        supp-card-type-77  (77),
        supp-card-type-78  (78),
        supp-card-type-79  (79),
        supp-card-type-80  (80),
        supp-card-type-81  (81),
        supp-card-type-82  (82),
        supp-card-type-83  (83),
        supp-card-type-84  (84),
        supp-card-type-85  (85),
        supp-card-type-86  (86),
        supp-card-type-87  (87),
        supp-card-type-88  (88),
        supp-card-type-89  (89),
        supp-card-type-90  (90),
        supp-card-type-91  (91),
        supp-card-type-92  (92),
        supp-card-type-93  (93),
        supp-card-type-94  (94),
        supp-card-type-95  (95),
        supp-card-type-96  (96),
        supp-card-type-97  (97),
        supp-card-type-98  (98),
        supp-card-type-99  (99),
        supp-card-type-100 (100),
        supp-card-type-101 (101),
        supp-card-type-102 (102),
        supp-card-type-103 (103),
        supp-card-type-104 (104),
        supp-card-type-105 (105),
        supp-card-type-106 (106),
        supp-card-type-107 (107),
        supp-card-type-108 (108),
        supp-card-type-109 (109),
        supp-card-type-110 (110),
        supp-card-type-111 (111),
        supp-card-type-112 (112),
        supp-card-type-113 (113),
        supp-card-type-114 (114),
        supp-card-type-115 (115),
        supp-card-type-116 (116),
        supp-card-type-117 (117),
        supp-card-type-118 (118),
        supp-card-type-119 (119),
        supp-card-type-120 (120),
        supp-card-type-121 (121),
        supp-card-type-122 (122),
        supp-card-type-123 (123),
        supp-card-type-124 (124),
        supp-card-type-125 (125),
        supp-card-type-126 (126),
        supp-card-type-127 (127),
        supp-card-type-128 (128),
        supp-card-type-129 (129),
        supp-card-type-130 (130),
        supp-card-type-131 (131),
        supp-card-type-132 (132),
        supp-card-type-133 (133),
        supp-card-type-134 (134),
        supp-card-type-135 (135),
        supp-card-type-136 (136),
        supp-card-type-137 (137),
        supp-card-type-138 (138),
        supp-card-type-139 (139),
        supp-card-type-140 (140),
        supp-card-type-141 (141),
        supp-card-type-142 (142),
        supp-card-type-143 (143),
        supp-card-type-144 (144),
        supp-card-type-145 (145),
        supp-card-type-146 (146),
        supp-card-type-147 (147),
        supp-card-type-148 (148),
        supp-card-type-149 (149),
        supp-card-type-150 (150),
        supp-card-type-151 (151),
        supp-card-type-152 (152),
        supp-card-type-153 (153),
        supp-card-type-154 (154),
        supp-card-type-155 (155),
        supp-card-type-156 (156),
        supp-card-type-157 (157),
        supp-card-type-158 (158),
        supp-card-type-159 (159),
        supp-card-type-160 (160),
        supp-card-type-161 (161),
        supp-card-type-162 (162),
        supp-card-type-163 (163),
        supp-card-type-164 (164),
        supp-card-type-165 (165),
        supp-card-type-166 (166),
        supp-card-type-167 (167),
        supp-card-type-168 (168),
        supp-card-type-169 (169),
        supp-card-type-170 (170),
        supp-card-type-171 (171),
        supp-card-type-172 (172),
        supp-card-type-173 (173),
        supp-card-type-174 (174),
        supp-card-type-175 (175),
        supp-card-type-176 (176),
        supp-card-type-177 (177),
        supp-card-type-178 (178),
        supp-card-type-179 (179),
        supp-card-type-180 (180),
        supp-card-type-181 (181),
        supp-card-type-182 (182),
        supp-card-type-183 (183),
        supp-card-type-184 (184),
        supp-card-type-185 (185),
        supp-card-type-186 (186),
        supp-card-type-187 (187),
        supp-card-type-188 (188),
        supp-card-type-189 (189),
        supp-card-type-190 (190),
        supp-card-type-191 (191),
        supp-card-type-192 (192),
        supp-card-type-193 (193),
        supp-card-type-194 (194),
        supp-card-type-195 (195),
        supp-card-type-196 (196),
        supp-card-type-197 (197),
        supp-card-type-198 (198),
        supp-card-type-199 (199),
        supp-card-type-200 (200),
        supp-card-type-201 (201),
        supp-card-type-202 (202),
        supp-card-type-203 (203),
        supp-card-type-204 (204),
        supp-card-type-205 (205),
        supp-card-type-206 (206),
        supp-card-type-207 (207),
        supp-card-type-208 (208),
        supp-card-type-209 (209),
        supp-card-type-210 (210),
        supp-card-type-211 (211),
        supp-card-type-212 (212),
        supp-card-type-213 (213),
        supp-card-type-214 (214),
        supp-card-type-215 (215),
        supp-card-type-216 (216),
        supp-card-type-217 (217),
        supp-card-type-218 (218),
        supp-card-type-219 (219),
        supp-card-type-220 (220),
        supp-card-type-221 (221),
        supp-card-type-222 (222),
        supp-card-type-223 (223),
        supp-card-type-224 (224),
        supp-card-type-225 (225),
        supp-card-type-226 (226),
        supp-card-type-227 (227),
        supp-card-type-228 (228),
        supp-card-type-229 (229),
        supp-card-type-230 (230),
        supp-card-type-231 (231),
        supp-card-type-232 (232),
        supp-card-type-233 (233),
        supp-card-type-234 (234),
        supp-card-type-235 (235),
        supp-card-type-236 (236),
        supp-card-type-237 (237),
        supp-card-type-238 (238),
        supp-card-type-239 (239),
        supp-card-type-240 (240),
        supp-card-type-241 (241),
        supp-card-type-242 (242),
        supp-card-type-243 (243),
        supp-card-type-244 (244),
        supp-card-type-245 (245),
        supp-card-type-246 (246),
        supp-card-type-247 (247),
        supp-card-type-248 (248),
        supp-card-type-249 (249),
        supp-card-type-250 (250),
        supp-card-type-251 (251),
        supp-card-type-252 (252),
        supp-card-type-253 (253),
        supp-card-type-254 (254),
        supp-card-type-255 (255)
    }

TmnxPEQType                      ::= TEXTUAL-CONVENTION
    STATUS      current
    DESCRIPTION
        "TmnxPEQType is an index into the tmnxPEQTypeTable used to identify a
         specific type of PEQ"
    SYNTAX      Unsigned32

TmnxPEQSuppType                  ::= TEXTUAL-CONVENTION
    STATUS      current
    DESCRIPTION
        "The TmnxPEQSuppType is a bit-mask specifying the PEQ type supported
         for a specific PEQ slot.

         When multiple bits are set, it can be used to identify a set or
         list of PEQ types that can be used in the tmnxChassisPEQTable to
         indicate supported PEQs within a specific chassis PEQ slot.
         An example of a PEQ type is:
            apeq2000 -- apeq-dc-2000."
    SYNTAX      BITS {
        invalidPEQType (0),
        unassigned     (1),
        suppPEQType2   (2),
        suppPEQType3   (3),
        suppPEQType4   (4),
        suppPEQType5   (5),
        suppPEQType6   (6),
        suppPEQType7   (7),
        suppPEQType8   (8),
        suppPEQType9   (9),
        suppPEQType10  (10),
        suppPEQType11  (11),
        suppPEQType12  (12),
        suppPEQType13  (13),
        suppPEQType14  (14),
        suppPEQType15  (15),
        suppPEQType16  (16),
        suppPEQType17  (17),
        suppPEQType18  (18),
        suppPEQType19  (19),
        suppPEQType20  (20),
        suppPEQType21  (21),
        suppPEQType22  (22),
        suppPEQType23  (23)
    }

TmnxFabricType                   ::= TEXTUAL-CONVENTION
    STATUS      current
    DESCRIPTION
        "The TmnxFabricType data type is an integer that specifies an Nokia
         SROS series fabric card type.

         A TmnxFabricType value is valid when there is a corresponding row in
         the tmnxFabricTypeTable."
    SYNTAX      Unsigned32

TmnxFabricSuppType               ::= TEXTUAL-CONVENTION
    STATUS      current
    DESCRIPTION
        "The TmnxFabricSuppType is a bit-mask specifying the valid fabric card
         types supported for a specific card slot.

         When multiple bits are set, it can be used to identify a set or list
         of card types used in the tmnxFabricTable to indicate supported fabric
         cards within a specific chassis slot. Some example card types might
         be:

                    integrated -- the CPM/SF Module consists of an integrated
                                  fabric card."
    SYNTAX      BITS {
        invalidCardType (0),
        unassigned      (1),
        suppCardType2   (2),
        suppCardType3   (3),
        suppCardType4   (4),
        suppCardType5   (5),
        suppCardType6   (6),
        suppCardType7   (7),
        suppCardType8   (8),
        suppCardType9   (9),
        suppCardType10  (10),
        suppCardType11  (11),
        suppCardType12  (12),
        suppCardType13  (13),
        suppCardType14  (14),
        suppCardType15  (15),
        suppCardType16  (16),
        suppCardType17  (17),
        suppCardType18  (18),
        suppCardType19  (19),
        suppCardType20  (20),
        suppCardType21  (21),
        suppCardType22  (22),
        suppCardType23  (23),
        suppCardType24  (24),
        suppCardType25  (25),
        suppCardType26  (26),
        suppCardType27  (27),
        suppCardType28  (28),
        suppCardType29  (29),
        suppCardType30  (30),
        suppCardType31  (31),
        suppCardType32  (32),
        suppCardType33  (33),
        suppCardType34  (34),
        suppCardType35  (35),
        suppCardType36  (36),
        suppCardType37  (37),
        suppCardType38  (38),
        suppCardType39  (39),
        suppCardType40  (40),
        suppCardType41  (41),
        suppCardType42  (42),
        suppCardType43  (43),
        suppCardType44  (44),
        suppCardType45  (45),
        suppCardType46  (46),
        suppCardType47  (47),
        suppCardType48  (48),
        suppCardType49  (49),
        suppCardType50  (50),
        suppCardType51  (51),
        suppCardType52  (52),
        suppCardType53  (53),
        suppCardType54  (54),
        suppCardType55  (55),
        suppCardType56  (56),
        suppCardType57  (57),
        suppCardType58  (58),
        suppCardType59  (59),
        suppCardType60  (60),
        suppCardType61  (61),
        suppCardType62  (62),
        suppCardType63  (63),
        suppCardType64  (64),
        suppCardType65  (65),
        suppCardType66  (66),
        suppCardType67  (67),
        suppCardType68  (68),
        suppCardType69  (69),
        suppCardType70  (70),
        suppCardType71  (71),
        suppCardType72  (72),
        suppCardType73  (73),
        suppCardType74  (74),
        suppCardType75  (75),
        suppCardType76  (76),
        suppCardType77  (77),
        suppCardType78  (78),
        suppCardType79  (79)
    }

TmnxCardRebootType               ::= TEXTUAL-CONVENTION
    STATUS      current
    DESCRIPTION
        "The TmnxCardRebootType is an enumerated integer that describes the
         values used to support reboot operation style commands.

         GETs and GETNEXTs on a variable of this type always returns
         'not-applicable (2)'."
    SYNTAX      INTEGER {
        cardReset      (1),
        notApplicable  (2),
        cardPowerCycle (3)
    }

TmnxChassisType                  ::= TEXTUAL-CONVENTION
    STATUS      current
    DESCRIPTION
        "TmnxChassisType is an index into the tmnxChassisTypeTable used to
         identify a specific type of chassis."
    SYNTAX      Unsigned32

TmnxDeviceState                  ::= TEXTUAL-CONVENTION
    STATUS      current
    DESCRIPTION
        "The TmnxDeviceState data type is an enumerated integer that describes
         the values used to identify states of chassis components such as fans
         and power supplies."
    SYNTAX      INTEGER {
        deviceStateUnknown      (1),
        deviceNotEquipped       (2),
        deviceStateOk           (3),
        deviceStateFailed       (4),
        deviceStateOutOfService (5),
        deviceNotProvisioned    (6),
        deviceNotApplicable     (7),
        deviceFormatting        (8),
        deviceSecureErase       (9)
    }

TmnxCardFpIxrResourceEgressType  ::= TEXTUAL-CONVENTION
    STATUS      current
    DESCRIPTION
        "The TmnxCardFpIxrResourceEgressType indicates the IXR FP egress
         resource type.

         cluster - Clusters are hardware tables that provide egress
         encapsulation information. Clusters are organized into Banks which are
         grouped into Sets. There are two types of Cluster Banks, depending on
         how their entries will be used: Banks whose entries will be linked to
         other bank entries are called Linked Data Banks (for example, a MPLS
         Tunnel entry pointing to an ARP entry), and Banks whose entries that
         do not need linkages to other bank entries are called Non-Linked Data
         Banks (for example, an ARP entry that needs no further linkages).

         linkList - Link-Lists are hardware tables that provide linkage between
         two Cluster entries. For example, a Tunnel entry pointing to an ARP
         entry. Link-Lists are organized into Banks which are grouped into
         Sets. When Cluster banks are exhausted, a Link-List Bank can be
         converted into a Data bank which can either be Linked or Non-Linked
         Data, just like the Cluster Banks. There are three types of Link-List
         Banks, depending on how their entries are used: a type that just does
         the linkages referred to as Linked List, and two types for data:
         Linked Data and Non-Linked Data."
    SYNTAX      INTEGER {
        cluster  (1),
        linkList (2)
    }

TmnxCardFpIxrResourceEgressSet   ::= TEXTUAL-CONVENTION
    STATUS      current
    DESCRIPTION
        "A Set is a group of Cluster or Link-List Banks. Sets of Cluster or
         Link-List Banks are associated with Phases"
    SYNTAX      INTEGER {
        set0 (0),
        set1 (1),
        set2 (2),
        set3 (3),
        set4 (4),
        none (9999)
    }

TmnxCardFpIxrResourceEgressPhase ::= TEXTUAL-CONVENTION
    STATUS      current
    DESCRIPTION
        "A Phase is a stage in the egress processing pipeline. Each Phase can
         use a particular Set or Sets of Clusters and Link-Lists Banks. A Set
         of Clusters and Link-Lists Banks can be shared between Phases."
    SYNTAX      INTEGER {
        phase1 (1),
        phase2 (2),
        phase3 (3),
        phase4 (4),
        phase5 (5),
        phase6 (6),
        phase7 (7),
        phase8 (8)
    }

TmnxLEDState                     ::= TEXTUAL-CONVENTION
    STATUS      current
    DESCRIPTION
        "The TmnxLEDState data type is an enumerated integer that describes the
         values used to identify state LEDs on Nokia SROS series cards."
    SYNTAX      INTEGER {
        ledNotApplicable (0),
        ledOff           (1),
        ledRed           (2),
        ledAmber         (3),
        ledYellow        (4),
        ledGreen         (5),
        ledAmberBlink    (6),
        ledYellowBlink   (7),
        ledGreenBlink    (8),
        ledRedBlink      (9)
    }

TmnxMdaType                      ::= TEXTUAL-CONVENTION
    STATUS      current
    DESCRIPTION
        "TmnxMdaType is an index into the tmnxMdaTypeTable used to identify a
         specific type of MDA."
    SYNTAX      Unsigned32

TmnxXiomType                     ::= TEXTUAL-CONVENTION
    STATUS      current
    DESCRIPTION
        "TmnxXiomType is an index into the tmnxXiomTypeTable used to identify a
         specific type of XIOM."
    SYNTAX      Unsigned32

TmnxXiomSuppType                 ::= TEXTUAL-CONVENTION
    STATUS      current
    DESCRIPTION
        "The TmnxXiomSuppType specifies a list of XIOM types that are supported
         on the provisioned card.

         The bit value for a given XIOM supported type can be used as an index
         in tmnxXiomTypeTable to obtain more information about the XIOM."
    SYNTAX      BITS {
        invalid-xiom-type (0),
        unassigned        (1),
        supp-XIOM-type-2  (2),
        supp-XIOM-type-3  (3),
        supp-XIOM-type-4  (4),
        supp-XIOM-type-5  (5),
        supp-XIOM-type-6  (6),
        supp-XIOM-type-7  (7),
        supp-XIOM-type-8  (8),
        supp-XIOM-type-9  (9),
        supp-XIOM-type-10 (10),
        supp-XIOM-type-11 (11),
        supp-XIOM-type-12 (12),
        supp-XIOM-type-13 (13),
        supp-XIOM-type-14 (14),
        supp-XIOM-type-15 (15)
    }

TmnxMDASuppType                  ::= TEXTUAL-CONVENTION
    STATUS      current
    DESCRIPTION
        "The TmnxMDASuppType data type is a SNMP BIT that is used to identify
         the kind of Media Dependent Adapter (MDA) supported on a card.

         When multiple bits are set, it can be used to identify a set or list
         of supported MDAs within a specific card slot. The MDA types are
         defined in the tmnxMdaTypeTable."
    SYNTAX      BITS {
        invalid-MDA-type  (0),
        unassigned        (1),
        supp-MDA-type-2   (2),
        supp-MDA-type-3   (3),
        supp-MDA-type-4   (4),
        supp-MDA-type-5   (5),
        supp-MDA-type-6   (6),
        supp-MDA-type-7   (7),
        supp-MDA-type-8   (8),
        supp-MDA-type-9   (9),
        supp-MDA-type-10  (10),
        supp-MDA-type-11  (11),
        supp-MDA-type-12  (12),
        supp-MDA-type-13  (13),
        supp-MDA-type-14  (14),
        supp-MDA-type-15  (15),
        supp-MDA-type-16  (16),
        supp-MDA-type-17  (17),
        supp-MDA-type-18  (18),
        supp-MDA-type-19  (19),
        supp-MDA-type-20  (20),
        supp-MDA-type-21  (21),
        supp-MDA-type-22  (22),
        supp-MDA-type-23  (23),
        supp-MDA-type-24  (24),
        supp-MDA-type-25  (25),
        supp-MDA-type-26  (26),
        supp-MDA-type-27  (27),
        supp-MDA-type-28  (28),
        supp-MDA-type-29  (29),
        supp-MDA-type-30  (30),
        supp-MDA-type-31  (31),
        supp-MDA-type-32  (32),
        supp-MDA-type-33  (33),
        supp-MDA-type-34  (34),
        supp-MDA-type-35  (35),
        supp-MDA-type-36  (36),
        supp-MDA-type-37  (37),
        supp-MDA-type-38  (38),
        supp-MDA-type-39  (39),
        supp-MDA-type-40  (40),
        supp-MDA-type-41  (41),
        supp-MDA-type-42  (42),
        supp-MDA-type-43  (43),
        supp-MDA-type-44  (44),
        supp-MDA-type-45  (45),
        supp-MDA-type-46  (46),
        supp-MDA-type-47  (47),
        supp-MDA-type-48  (48),
        supp-MDA-type-49  (49),
        supp-MDA-type-50  (50),
        supp-MDA-type-51  (51),
        supp-MDA-type-52  (52),
        supp-MDA-type-53  (53),
        supp-MDA-type-54  (54),
        supp-MDA-type-55  (55),
        supp-MDA-type-56  (56),
        supp-MDA-type-57  (57),
        supp-MDA-type-58  (58),
        supp-MDA-type-59  (59),
        supp-MDA-type-60  (60),
        supp-MDA-type-61  (61),
        supp-MDA-type-62  (62),
        supp-MDA-type-63  (63),
        supp-MDA-type-64  (64),
        supp-MDA-type-65  (65),
        supp-MDA-type-66  (66),
        supp-MDA-type-67  (67),
        supp-MDA-type-68  (68),
        supp-MDA-type-69  (69),
        supp-MDA-type-70  (70),
        supp-MDA-type-71  (71),
        supp-MDA-type-72  (72),
        supp-MDA-type-73  (73),
        supp-MDA-type-74  (74),
        supp-MDA-type-75  (75),
        supp-MDA-type-76  (76),
        supp-MDA-type-77  (77),
        supp-MDA-type-78  (78),
        supp-MDA-type-79  (79),
        supp-MDA-type-80  (80),
        supp-MDA-type-81  (81),
        supp-MDA-type-82  (82),
        supp-MDA-type-83  (83),
        supp-MDA-type-84  (84),
        supp-MDA-type-85  (85),
        supp-MDA-type-86  (86),
        supp-MDA-type-87  (87),
        supp-MDA-type-88  (88),
        supp-MDA-type-89  (89),
        supp-MDA-type-90  (90),
        supp-MDA-type-91  (91),
        supp-MDA-type-92  (92),
        supp-MDA-type-93  (93),
        supp-MDA-type-94  (94),
        supp-MDA-type-95  (95),
        supp-MDA-type-96  (96),
        supp-MDA-type-97  (97),
        supp-MDA-type-98  (98),
        supp-MDA-type-99  (99),
        supp-MDA-type-100 (100),
        supp-MDA-type-101 (101),
        supp-MDA-type-102 (102),
        supp-MDA-type-103 (103),
        supp-MDA-type-104 (104),
        supp-MDA-type-105 (105),
        supp-MDA-type-106 (106),
        supp-MDA-type-107 (107),
        supp-MDA-type-108 (108),
        supp-MDA-type-109 (109),
        supp-MDA-type-110 (110),
        supp-MDA-type-111 (111),
        supp-MDA-type-112 (112),
        supp-MDA-type-113 (113),
        supp-MDA-type-114 (114),
        supp-MDA-type-115 (115),
        supp-MDA-type-116 (116),
        supp-MDA-type-117 (117),
        supp-MDA-type-118 (118),
        supp-MDA-type-119 (119),
        supp-MDA-type-120 (120),
        supp-MDA-type-121 (121),
        supp-MDA-type-122 (122),
        supp-MDA-type-123 (123),
        supp-MDA-type-124 (124),
        supp-MDA-type-125 (125),
        supp-MDA-type-126 (126),
        supp-MDA-type-127 (127),
        supp-MDA-type-128 (128),
        supp-MDA-type-129 (129),
        supp-MDA-type-130 (130),
        supp-MDA-type-131 (131),
        supp-MDA-type-132 (132),
        supp-MDA-type-133 (133),
        supp-MDA-type-134 (134),
        supp-MDA-type-135 (135),
        supp-MDA-type-136 (136),
        supp-MDA-type-137 (137),
        supp-MDA-type-138 (138),
        supp-MDA-type-139 (139),
        supp-MDA-type-140 (140),
        supp-MDA-type-141 (141),
        supp-MDA-type-142 (142),
        supp-MDA-type-143 (143),
        supp-MDA-type-144 (144),
        supp-MDA-type-145 (145),
        supp-MDA-type-146 (146),
        supp-MDA-type-147 (147),
        supp-MDA-type-148 (148),
        supp-MDA-type-149 (149),
        supp-MDA-type-150 (150),
        supp-MDA-type-151 (151),
        supp-MDA-type-152 (152),
        supp-MDA-type-153 (153),
        supp-MDA-type-154 (154),
        supp-MDA-type-155 (155),
        supp-MDA-type-156 (156),
        supp-MDA-type-157 (157),
        supp-MDA-type-158 (158),
        supp-MDA-type-159 (159),
        supp-MDA-type-160 (160),
        supp-MDA-type-161 (161),
        supp-MDA-type-162 (162),
        supp-MDA-type-163 (163),
        supp-MDA-type-164 (164),
        supp-MDA-type-165 (165),
        supp-MDA-type-166 (166),
        supp-MDA-type-167 (167),
        supp-MDA-type-168 (168),
        supp-MDA-type-169 (169),
        supp-MDA-type-170 (170),
        supp-MDA-type-171 (171),
        supp-MDA-type-172 (172),
        supp-MDA-type-173 (173),
        supp-MDA-type-174 (174),
        supp-MDA-type-175 (175),
        supp-MDA-type-176 (176),
        supp-MDA-type-177 (177),
        supp-MDA-type-178 (178),
        supp-MDA-type-179 (179),
        supp-MDA-type-180 (180),
        supp-MDA-type-181 (181),
        supp-MDA-type-182 (182),
        supp-MDA-type-183 (183),
        supp-MDA-type-184 (184),
        supp-MDA-type-185 (185),
        supp-MDA-type-186 (186),
        supp-MDA-type-187 (187),
        supp-MDA-type-188 (188),
        supp-MDA-type-189 (189),
        supp-MDA-type-190 (190),
        supp-MDA-type-191 (191),
        supp-MDA-type-192 (192),
        supp-MDA-type-193 (193),
        supp-MDA-type-194 (194),
        supp-MDA-type-195 (195),
        supp-MDA-type-196 (196),
        supp-MDA-type-197 (197),
        supp-MDA-type-198 (198),
        supp-MDA-type-199 (199),
        supp-MDA-type-200 (200),
        supp-MDA-type-201 (201),
        supp-MDA-type-202 (202),
        supp-MDA-type-203 (203),
        supp-MDA-type-204 (204),
        supp-MDA-type-205 (205),
        supp-MDA-type-206 (206),
        supp-MDA-type-207 (207),
        supp-MDA-type-208 (208),
        supp-MDA-type-209 (209),
        supp-MDA-type-210 (210),
        supp-MDA-type-211 (211),
        supp-MDA-type-212 (212),
        supp-MDA-type-213 (213),
        supp-MDA-type-214 (214),
        supp-MDA-type-215 (215),
        supp-MDA-type-216 (216),
        supp-MDA-type-217 (217),
        supp-MDA-type-218 (218),
        supp-MDA-type-219 (219),
        supp-MDA-type-220 (220),
        supp-MDA-type-221 (221),
        supp-MDA-type-222 (222),
        supp-MDA-type-223 (223),
        supp-MDA-type-224 (224),
        supp-MDA-type-225 (225),
        supp-MDA-type-226 (226),
        supp-MDA-type-227 (227),
        supp-MDA-type-228 (228),
        supp-MDA-type-229 (229),
        supp-MDA-type-230 (230),
        supp-MDA-type-231 (231),
        supp-MDA-type-232 (232),
        supp-MDA-type-233 (233),
        supp-MDA-type-234 (234),
        supp-MDA-type-235 (235),
        supp-MDA-type-236 (236),
        supp-MDA-type-237 (237),
        supp-MDA-type-238 (238),
        supp-MDA-type-239 (239),
        supp-MDA-type-240 (240),
        supp-MDA-type-241 (241),
        supp-MDA-type-242 (242),
        supp-MDA-type-243 (243),
        supp-MDA-type-244 (244),
        supp-MDA-type-245 (245),
        supp-MDA-type-246 (246),
        supp-MDA-type-247 (247),
        supp-MDA-type-248 (248),
        supp-MDA-type-249 (249),
        supp-MDA-type-250 (250),
        supp-MDA-type-251 (251),
        supp-MDA-type-252 (252),
        supp-MDA-type-253 (253),
        supp-MDA-type-254 (254),
        supp-MDA-type-255 (255),
        supp-MDA-type-256 (256),
        supp-MDA-type-257 (257),
        supp-MDA-type-258 (258),
        supp-MDA-type-259 (259),
        supp-MDA-type-260 (260),
        supp-MDA-type-261 (261),
        supp-MDA-type-262 (262),
        supp-MDA-type-263 (263),
        supp-MDA-type-264 (264),
        supp-MDA-type-265 (265),
        supp-MDA-type-266 (266),
        supp-MDA-type-267 (267),
        supp-MDA-type-268 (268),
        supp-MDA-type-269 (269),
        supp-MDA-type-270 (270),
        supp-MDA-type-271 (271),
        supp-MDA-type-272 (272),
        supp-MDA-type-273 (273),
        supp-MDA-type-274 (274),
        supp-MDA-type-275 (275),
        supp-MDA-type-276 (276),
        supp-MDA-type-277 (277),
        supp-MDA-type-278 (278),
        supp-MDA-type-279 (279),
        supp-MDA-type-280 (280),
        supp-MDA-type-281 (281),
        supp-MDA-type-282 (282),
        supp-MDA-type-283 (283),
        supp-MDA-type-284 (284),
        supp-MDA-type-285 (285),
        supp-MDA-type-286 (286),
        supp-MDA-type-287 (287),
        supp-MDA-type-288 (288),
        supp-MDA-type-289 (289),
        supp-MDA-type-290 (290),
        supp-MDA-type-291 (291),
        supp-MDA-type-292 (292),
        supp-MDA-type-293 (293),
        supp-MDA-type-294 (294),
        supp-MDA-type-295 (295),
        supp-MDA-type-296 (296),
        supp-MDA-type-297 (297),
        supp-MDA-type-298 (298),
        supp-MDA-type-299 (299),
        supp-MDA-type-300 (300),
        supp-MDA-type-301 (301),
        supp-MDA-type-302 (302),
        supp-MDA-type-303 (303),
        supp-MDA-type-304 (304),
        supp-MDA-type-305 (305),
        supp-MDA-type-306 (306),
        supp-MDA-type-307 (307),
        supp-MDA-type-308 (308),
        supp-MDA-type-309 (309),
        supp-MDA-type-310 (310),
        supp-MDA-type-311 (311),
        supp-MDA-type-312 (312),
        supp-MDA-type-313 (313),
        supp-MDA-type-314 (314),
        supp-MDA-type-315 (315),
        supp-MDA-type-316 (316),
        supp-MDA-type-317 (317),
        supp-MDA-type-318 (318),
        supp-MDA-type-319 (319),
        supp-MDA-type-320 (320),
        supp-MDA-type-321 (321),
        supp-MDA-type-322 (322),
        supp-MDA-type-323 (323),
        supp-MDA-type-324 (324),
        supp-MDA-type-325 (325),
        supp-MDA-type-326 (326),
        supp-MDA-type-327 (327),
        supp-MDA-type-328 (328),
        supp-MDA-type-329 (329),
        supp-MDA-type-330 (330),
        supp-MDA-type-331 (331),
        supp-MDA-type-332 (332),
        supp-MDA-type-333 (333),
        supp-MDA-type-334 (334),
        supp-MDA-type-335 (335),
        supp-MDA-type-336 (336),
        supp-MDA-type-337 (337),
        supp-MDA-type-338 (338),
        supp-MDA-type-339 (339),
        supp-MDA-type-340 (340),
        supp-MDA-type-341 (341),
        supp-MDA-type-342 (342),
        supp-MDA-type-343 (343),
        supp-MDA-type-344 (344),
        supp-MDA-type-345 (345),
        supp-MDA-type-346 (346),
        supp-MDA-type-347 (347),
        supp-MDA-type-348 (348),
        supp-MDA-type-349 (349),
        supp-MDA-type-350 (350),
        supp-MDA-type-351 (351),
        supp-MDA-type-352 (352),
        supp-MDA-type-353 (353),
        supp-MDA-type-354 (354),
        supp-MDA-type-355 (355),
        supp-MDA-type-356 (356),
        supp-MDA-type-357 (357),
        supp-MDA-type-358 (358),
        supp-MDA-type-359 (359),
        supp-MDA-type-360 (360),
        supp-MDA-type-361 (361),
        supp-MDA-type-362 (362),
        supp-MDA-type-363 (363),
        supp-MDA-type-364 (364),
        supp-MDA-type-365 (365),
        supp-MDA-type-366 (366),
        supp-MDA-type-367 (367),
        supp-MDA-type-368 (368),
        supp-MDA-type-369 (369),
        supp-MDA-type-370 (370),
        supp-MDA-type-371 (371),
        supp-MDA-type-372 (372),
        supp-MDA-type-373 (373),
        supp-MDA-type-374 (374),
        supp-MDA-type-375 (375),
        supp-MDA-type-376 (376),
        supp-MDA-type-377 (377),
        supp-MDA-type-378 (378),
        supp-MDA-type-379 (379),
        supp-MDA-type-380 (380),
        supp-MDA-type-381 (381),
        supp-MDA-type-382 (382),
        supp-MDA-type-383 (383),
        supp-MDA-type-384 (384),
        supp-MDA-type-385 (385),
        supp-MDA-type-386 (386),
        supp-MDA-type-387 (387),
        supp-MDA-type-388 (388),
        supp-MDA-type-389 (389),
        supp-MDA-type-390 (390),
        supp-MDA-type-391 (391),
        supp-MDA-type-392 (392),
        supp-MDA-type-393 (393),
        supp-MDA-type-394 (394),
        supp-MDA-type-395 (395),
        supp-MDA-type-396 (396),
        supp-MDA-type-397 (397),
        supp-MDA-type-398 (398),
        supp-MDA-type-399 (399),
        supp-MDA-type-400 (400),
        supp-MDA-type-401 (401),
        supp-MDA-type-402 (402),
        supp-MDA-type-403 (403),
        supp-MDA-type-404 (404),
        supp-MDA-type-405 (405),
        supp-MDA-type-406 (406),
        supp-MDA-type-407 (407),
        supp-MDA-type-408 (408),
        supp-MDA-type-409 (409),
        supp-MDA-type-410 (410),
        supp-MDA-type-411 (411),
        supp-MDA-type-412 (412),
        supp-MDA-type-413 (413),
        supp-MDA-type-414 (414),
        supp-MDA-type-415 (415),
        supp-MDA-type-416 (416),
        supp-MDA-type-417 (417),
        supp-MDA-type-418 (418),
        supp-MDA-type-419 (419),
        supp-MDA-type-420 (420),
        supp-MDA-type-421 (421),
        supp-MDA-type-422 (422),
        supp-MDA-type-423 (423),
        supp-MDA-type-424 (424),
        supp-MDA-type-425 (425),
        supp-MDA-type-426 (426),
        supp-MDA-type-427 (427),
        supp-MDA-type-428 (428),
        supp-MDA-type-429 (429),
        supp-MDA-type-430 (430),
        supp-MDA-type-431 (431),
        supp-MDA-type-432 (432),
        supp-MDA-type-433 (433),
        supp-MDA-type-434 (434),
        supp-MDA-type-435 (435),
        supp-MDA-type-436 (436),
        supp-MDA-type-437 (437),
        supp-MDA-type-438 (438),
        supp-MDA-type-439 (439),
        supp-MDA-type-440 (440),
        supp-MDA-type-441 (441),
        supp-MDA-type-442 (442),
        supp-MDA-type-443 (443),
        supp-MDA-type-444 (444),
        supp-MDA-type-445 (445),
        supp-MDA-type-446 (446),
        supp-MDA-type-447 (447),
        supp-MDA-type-448 (448),
        supp-MDA-type-449 (449),
        supp-MDA-type-450 (450),
        supp-MDA-type-451 (451),
        supp-MDA-type-452 (452),
        supp-MDA-type-453 (453),
        supp-MDA-type-454 (454),
        supp-MDA-type-455 (455),
        supp-MDA-type-456 (456),
        supp-MDA-type-457 (457),
        supp-MDA-type-458 (458),
        supp-MDA-type-459 (459),
        supp-MDA-type-460 (460),
        supp-MDA-type-461 (461),
        supp-MDA-type-462 (462),
        supp-MDA-type-463 (463),
        supp-MDA-type-464 (464),
        supp-MDA-type-465 (465),
        supp-MDA-type-466 (466),
        supp-MDA-type-467 (467),
        supp-MDA-type-468 (468),
        supp-MDA-type-469 (469),
        supp-MDA-type-470 (470),
        supp-MDA-type-471 (471),
        supp-MDA-type-472 (472),
        supp-MDA-type-473 (473),
        supp-MDA-type-474 (474),
        supp-MDA-type-475 (475),
        supp-MDA-type-476 (476),
        supp-MDA-type-477 (477),
        supp-MDA-type-478 (478),
        supp-MDA-type-479 (479),
        supp-MDA-type-480 (480),
        supp-MDA-type-481 (481),
        supp-MDA-type-482 (482),
        supp-MDA-type-483 (483),
        supp-MDA-type-484 (484),
        supp-MDA-type-485 (485),
        supp-MDA-type-486 (486),
        supp-MDA-type-487 (487),
        supp-MDA-type-488 (488),
        supp-MDA-type-489 (489),
        supp-MDA-type-490 (490),
        supp-MDA-type-491 (491),
        supp-MDA-type-492 (492),
        supp-MDA-type-493 (493),
        supp-MDA-type-494 (494),
        supp-MDA-type-495 (495),
        supp-MDA-type-496 (496),
        supp-MDA-type-497 (497),
        supp-MDA-type-498 (498),
        supp-MDA-type-499 (499),
        supp-MDA-type-500 (500),
        supp-MDA-type-501 (501),
        supp-MDA-type-502 (502),
        supp-MDA-type-503 (503),
        supp-MDA-type-504 (504),
        supp-MDA-type-505 (505),
        supp-MDA-type-506 (506),
        supp-MDA-type-507 (507),
        supp-MDA-type-508 (508),
        supp-MDA-type-509 (509),
        supp-MDA-type-510 (510),
        supp-MDA-type-511 (511)
    }

TmnxMDAChanType                  ::= TEXTUAL-CONVENTION
    STATUS      current
    DESCRIPTION
        "The TmnxMDAChanType data type indicates the type of channel that can
         be created on an MDA."
    SYNTAX      INTEGER {
        unknown     (0),
        sonetSts768 (1),
        sonetSts192 (2),
        sonetSts48  (3),
        sonetSts12  (4),
        sonetSts3   (5),
        sonetSts1   (6),
        sdhTug3     (7),
        sonetVtg    (8),
        sonetVt15   (9),
        sonetVt2    (10),
        sonetVt3    (11),
        sonetVt6    (12),
        pdhTu3      (13),
        pdhDs3      (14),
        pdhE3       (15),
        pdhDs1      (16),
        pdhE1       (17),
        pdhDs0Grp   (18),
        rs232       (19),
        socket      (20),
        tpif        (21)
    }

TmnxMdaAtmMode                   ::= TEXTUAL-CONVENTION
    STATUS      obsolete
    DESCRIPTION
        "TmnxMdaAtmMode is an enumerated integer whose value specifies the
         maximum number of Virtual Circuits for an ATM-capable Media Dependent
         Adapter (MDA)."
    SYNTAX      INTEGER {
        notApplicable (0),
        max8kVc       (1),
        max16kVc      (2)
    }

TmnxCcmType                      ::= TEXTUAL-CONVENTION
    STATUS      current
    DESCRIPTION
        "The TmnxCcmType data type is bit-mask field that describes
         the values used to identify the kind of Chassis Control
         module (CCM) installed on the chassis.  A TmnxCcmType bit
         value specifies the index value for the entry in the
         tmnxCcmTypeTable used to identify a specific type of CCM
         manufactured by Nokia.  When multiple bits are set, it can
         be used to identify a set or list of CCM types used in the
         tmnxCcmTable to indicate supported CCMs within a specific
         chassis slot.  Some example CCM types are:

                    unknown            -- unknown/uninstalled
                    ccm-v1             -- Chassis Control Module version 1"
    SYNTAX      Unsigned32

TmnxMcmType                      ::= TEXTUAL-CONVENTION
    STATUS      obsolete
    DESCRIPTION
        "The TmnxMcmType data type is bit-mask field that describes
         the values used to identify the kind of MDA Carrier
         module (MCM) installed on the chassis.  A TmnxMcmType bit
         value specifies the index value for the entry in the
         tmnxMcmTypeTable used to identify a specific type of MCM
         manufactured by Nokia.  When multiple bits are set, it can
         be used to identify a set or list of MCM types used in the
         tmnxMcmTable to indicate supported MCMs within a specific
         card slot.

         This typedef was obsoleted in release 20.2."
    SYNTAX      Unsigned32

TmnxSlotNum                      ::= TEXTUAL-CONVENTION
    STATUS      current
    DESCRIPTION
        "The TmnxSlotNum data type is an integer that specifies a slot in an
         Nokia SROS series chassis."
    SYNTAX      Integer32 (1..128)

TmnxSlotNumOrZero                ::= TEXTUAL-CONVENTION
    STATUS      current
    DESCRIPTION
        "The TmnxSlotNumOrZero data type is an integer that specifies a slot in
         an Nokia SROS series chassis or zero."
    SYNTAX      Integer32 (0..128)

TmnxPortAdminStatus              ::= TEXTUAL-CONVENTION
    STATUS      current
    DESCRIPTION
        "The desired administrative status of this port."
    SYNTAX      INTEGER {
        noop         (1),
        inService    (2),
        outOfService (3),
        diagnose     (4)
    }

TmnxChassisMode                  ::= TEXTUAL-CONVENTION
    STATUS      current
    DESCRIPTION
        "The TmnxChassisMode data type is an enumerated integer that specifies
         the values used to identify which set of scaling numbers and features
         are effective for an Nokia SROS series chassis. 'modeD' corresponds to
         the scaling and features that come with iom3-xp/imm modules or newer
         modules."
    SYNTAX      INTEGER {
        modeD (4)
    }

TmnxSETSRefSource                ::= TEXTUAL-CONVENTION
    STATUS      current
    DESCRIPTION
        "The TmnxSETSRefSource data type is an enumerated integer that
         describes the values used to identify the Synchronous Equipment Timing
         Source (SETS) timing reference source."
    SYNTAX      INTEGER {
        otherCPM    (0),
        reference1  (1),
        reference2  (2),
        bits        (3),
        bits2       (4),
        ptp         (5),
        noReference (6),
        synce       (7),
        synce2      (8),
        gnss        (9),
        gnss2       (10)
    }

TmnxSETSRefQualified             ::= TEXTUAL-CONVENTION
    STATUS      current
    DESCRIPTION
        "The TmnxSETSRefQualified data type is an enumerated integer that
         describes the values used to identify whether the reference is
         'qualified' or 'not-qualified' for use by SETS."
    SYNTAX      INTEGER {
        qualified     (1),
        not-qualified (2)
    }

TmnxSETSRefAlarm                 ::= TEXTUAL-CONVENTION
    STATUS      current
    DESCRIPTION
        "The TmnxSETSRefAlarm data type is a bitmap that describes the values
         used to identify the alarms on the SETS timing reference source if the
         source is 'not-qualified'.

         'los'    - loss of signal
         'oof'    - out of frequency range
         'oopir'  - out of pull in range."
    SYNTAX      BITS {
        los   (0),
        oof   (1),
        oopir (2)
    }

TmnxSETSStatus                   ::= TEXTUAL-CONVENTION
    STATUS      current
    DESCRIPTION
        "The TmnxSETSStatus textual convention specifies the status of the
         Synchronous Timing Equipment Source (SETS)."
    SYNTAX      INTEGER {
        notPresent     (1),
        masterFreerun  (2),
        masterHoldover (3),
        masterLocked   (4),
        slave          (5),
        acquiring      (6)
    }

TmnxBITSIfType                   ::= TEXTUAL-CONVENTION
    STATUS      current
    DESCRIPTION
        "The TmnxBITSIfType data type is an enumerated integer that describes
         the values used to identify the interface and framing types of a BITS
         (Building Integrated Timing Supply) interface."
    REFERENCE
        "G.703, 'Physical/Electrical Characteristics of Hierarchical Digital
         Interfaces', Section 13, November 2001."
    SYNTAX      INTEGER {
        none         (0),
        t1-esf       (1),
        t1-sf        (2),
        e1-pcm30crc  (3),
        e1-pcm31crc  (4),
        g703-2048khz (5)
    }

TmnxSSMQualityLevel              ::= TEXTUAL-CONVENTION
    STATUS      current
    DESCRIPTION
        "The TmnxSSMQualityLevel is an enumerated integer that describes the
         values used to identify the SSM Quality level of received SSM
         messages."
    SYNTAX      INTEGER {
        unknown (0),
        prs     (1),
        stu     (2),
        st2     (3),
        tnc     (4),
        st3e    (5),
        st3     (6),
        smc     (7),
        st4     (8),
        dus     (9),
        prc     (10),
        ssua    (11),
        ssub    (12),
        sec     (13),
        dnu     (14),
        inv     (15),
        pno     (16),
        eec1    (17),
        eec2    (18),
        failed  (19),
        eprtc   (20),
        prtc    (21),
        eprc    (22),
        eeec    (23)
    }

TmnxRefInState                   ::= TEXTUAL-CONVENTION
    STATUS      current
    DESCRIPTION
        "The TmnxRefInState is an enumerated integer that describes the values
         used to identify the state of system timing reference.

         A value of 'ptpAdminDisabled (17)' means that the PTP timing reference
         is not in use because 'tmnxPtpClockAdminState' is 'outOfService (3)'.
         This value only applies to the PTP timing reference.

         A value of 'ptpOperDown (18)' means that the PTP timing reference is
         not in use because 'tmnxPtpClockOperState' is 'outOfService (3)'. This
         value only applies to the PTP timing reference.

         A value of 'ptpNoParentClock (19)' means that the PTP timing reference
         is not in use because the local PTP clock has not selected a remote
         master clock to be the parent clock.  This value only applies to the
         PTP timing reference.

         A value of 'operSpeedNotSupported (20)' means that the timing
         reference is not in use because the copper based port is operating at
         10 Mbps where recovered timing is not supported.

         A value of 'cpmUnsupBITS2048khz (21)' means that the timing reference
         is not in use because the CPM does not meet the specifications for the
         2048kHz BITS output signal under G.703.

         A value of 'hwAdminDisabled (22)' means that the timing reference is
         not in use because one or more hardware component (port, MDA, etc.)
         has its admin-state out of service. This state value is only
         applicable for Ref-1 and Ref-2 timing references.

         A value of 'timingLoopDetected (23)' means that the timing reference
         is not in use because the clock identifier received by the reference
         is the clock identifier of this system."
    REFERENCE
        "IEEE Std 1588-2008 'IEEE Standard for a Precision Clock Synchronization
         Protocol for Networked Measurement and Control Systems'.
         G.703, 'Physical/Electrical Characteristics of Hierarchical Digital
         Interfaces', Section 13, November 2001."
    SYNTAX      INTEGER {
        disabled              (0),
        unqualified           (1),
        standby               (2),
        up                    (3),
        previousFailure       (4),
        lowQuality            (5),
        lof                   (6),
        ais                   (7),
        ghost                 (8),
        validating            (9),
        reserved-10           (10),
        reserved-11           (11),
        reserved-12           (12),
        fer                   (13),
        reserved-14           (14),
        reserved-15           (15),
        reserved-16           (16),
        ptpAdminDisabled      (17),
        ptpOperDown           (18),
        ptpNoParentClock      (19),
        operSpeedNotSupported (20),
        cpmUnsupBITS2048khz   (21),
        hwAdminDisabled       (22),
        timingLoopDetected    (23)
    }

TmnxBITSOutSource                ::= TEXTUAL-CONVENTION
    STATUS      current
    DESCRIPTION
        "The TmnxBITSOutSource is an enumerated integer that describes the
         values used to identity the source of the BITS (Building Integrated
         Timing Supply) output.

         When TmnxBITSOutSource is 'lineRef (1)', the BITS output timing is
         selected from either the one of the timing input references, without
         any filtering.  Either the first or second line reference, or the PTP
         timing input reference may be selected to be transmitted in this
         manner.  The BITS timing input is never selected in this mode.

         When TmnxBITSOutSource is 'internalClock (2)', the BITS output timing
         is driven from the system timing."
    REFERENCE
        "ITU-T G.8264/Y.1364 Distribution of timing through packet networks,
         Section A.7."
    SYNTAX      INTEGER {
        lineRef       (1),
        internalClock (2)
    }

TmnxCcagId                       ::= TEXTUAL-CONVENTION
    STATUS      obsolete
    DESCRIPTION
        "TmnxCcagId is an integer specifying the cross connect aggregation
         group. The value '0' is used when a ccag is not defined and is not a
         valid value when TmnxCcagId is used as an index.

         This typedef was made obsolete in release 21.2."
    SYNTAX      Integer32 (0..8)

TmnxCcagRate                     ::= TEXTUAL-CONVENTION
    STATUS      obsolete
    DESCRIPTION
        "TmnxCcagRate is an integer specifying the rate for a CCAG member in
         Kbps.  The range of TmnxCcagRate is from 0 Kbps to 100Gbps. The value
         '-1' is used for maximum rate available.

         This typedef was made obsolete in release 21.2."
    SYNTAX      Integer32 (-1..100000000)

TmnxCcagRateOption               ::= TEXTUAL-CONVENTION
    STATUS      obsolete
    DESCRIPTION
        "TmnxCcagRateOption specifies how the defined rate is
         applied to active Cross Connect Adaptors (CCAs).
         aggregate (1) -  the defined rate is equally divided among the CCAs in
                          the CCAG member list based on the number of active
                          CCAs.
         cca       (2) -  the defined rate is applied to all CCAs in the CCAG
                          member list.

         This typedef was made obsolete in release 21.2."
    SYNTAX      INTEGER {
        aggregate (1),
        cca       (2)
    }

TmnxChassisPemType               ::= TEXTUAL-CONVENTION
    STATUS      current
    DESCRIPTION
        "TmnxChassisPemType specifies what Power Entry Module (PEM) type is
         installed in the Chassis.
         not-applicable (0) - Chassis does not support an installed PEM.
         unknown (1)        - Unknown kind of PEM installed.
         pem (2)            - First generation of the PEM module.
         pem-3 (3)          - Second generation of the PEM module capable of
                              supporting the IOM3/IMM modules.
         peq (4)            - Power Equalizer."
    SYNTAX      INTEGER {
        not-applicable (0),
        unknown        (1),
        pem            (2),
        pem-3          (3),
        peq            (4)
    }

TmnxCardSlotBitMap               ::= TEXTUAL-CONVENTION
    STATUS      current
    DESCRIPTION
        "TmnxCardSlotBitMap specifies a bitmap of card slots. A bit value set
         to '1' indicates the slot is used by the object."
    SYNTAX      BITS {
        slot1  (0),
        slot2  (1),
        slot3  (2),
        slot4  (3),
        slot5  (4),
        slot6  (5),
        slot7  (6),
        slot8  (7),
        slot9  (8),
        slot10 (9),
        slot11 (10),
        slot12 (11),
        slot13 (12),
        slot14 (13),
        slot15 (14),
        slot16 (15),
        slot17 (16),
        slot18 (17),
        slot19 (18),
        slot20 (19),
        slot21 (20),
        slot22 (21),
        slot23 (22),
        slot24 (23)
    }

TmnxTunnelGroupId                ::= TEXTUAL-CONVENTION
    STATUS      current
    DESCRIPTION
        "TmnxTunnelGroupId is an integer specifying the ISA tunnel-group."
    SYNTAX      Unsigned32 (1..64)

TmnxTunnelGroupIdOrZero          ::= TEXTUAL-CONVENTION
    STATUS      current
    DESCRIPTION
        "TmnxTunnelGroupIdOrZero is an integer specifying the ISA tunnel-group
         A value of zero is used when the tunnel-group is not defined."
    SYNTAX      Unsigned32 (0..64)

TmnxPowerSupAssignType           ::= TEXTUAL-CONVENTION
    STATUS      current
    DESCRIPTION
        "TmnxPowerSupAssignType specifies the type of power supply that is
         assigned for a platform."
    SYNTAX      INTEGER {
        none       (0),
        dc         (1),
        acSingle   (2),
        acMultiple (3),
        default    (4),
        dcMultiple (5)
    }

TmnxPCMType                      ::= TEXTUAL-CONVENTION
    STATUS      current
    DESCRIPTION
        "TmnxPCMType specifies the type of PCM."
    SYNTAX      INTEGER {
        unassigned    (1),
        indeterminate (2),
        dual          (3),
        quad          (4)
    }

TmnxFpGeneration                 ::= TEXTUAL-CONVENTION
    STATUS      current
    DESCRIPTION
        "TmnxFpGeneration specifies the Forwarding Plane (FP) network processor
         generation."
    SYNTAX      INTEGER {
        not-applicable (0),
        fp2            (1),
        fp3            (2),
        fp4            (3),
        fp5            (4)
    }

TmnxPMType                       ::= TEXTUAL-CONVENTION
    STATUS      current
    DESCRIPTION
        "TmnxPMType is used to identify a specific type of Power Module (PM)"
    SYNTAX      Unsigned32

TmnxPMSuppType                   ::= TEXTUAL-CONVENTION
    STATUS      current
    DESCRIPTION
        "The TmnxPMSuppType is a bit-mask specifying the PM type supported for
         a specific PM slot.

         When multiple bits are set, it can be used to identify a set or
         list of PM types that can be used in the tmnxPhysChassisPMTable.
         An example of a PM type is:
            apeq2000 -- apeq-dc-2000."
    SYNTAX      BITS {
        invalidPMType (0),
        unassigned    (1),
        suppPMType2   (2),
        suppPMType3   (3),
        suppPMType4   (4),
        suppPMType5   (5),
        suppPMType6   (6),
        suppPMType7   (7),
        suppPMType8   (8),
        suppPMType9   (9),
        suppPMType10  (10),
        suppPMType11  (11),
        suppPMType12  (12),
        suppPMType13  (13),
        suppPMType14  (14),
        suppPMType15  (15),
        suppPMType16  (16),
        suppPMType17  (17),
        suppPMType18  (18),
        suppPMType19  (19),
        suppPMType20  (20),
        suppPMType21  (21),
        suppPMType22  (22),
        suppPMType23  (23)
    }

TmnxCardFunctionalLevel          ::= TEXTUAL-CONVENTION
    STATUS      current
    DESCRIPTION
        "The TmnxCardFunctionalLevel data type is an integer that specifies a
         functional level variant of a given Card."
    SYNTAX      INTEGER {
        unknown       (0),
        unrestricted  (1),
        he            (2),
        er            (3),
        cr            (4),
        he1200g-plus  (5),
        er1200g-plus  (6),
        cr1200g-plus  (7),
        he400g        (8),
        er400g        (9),
        cr400g        (10),
        he400g-plus   (11),
        er400g-plus   (12),
        cr400g-plus   (13),
        he800g-plus   (14),
        er800g-plus   (15),
        cr800g-plus   (16),
        he4800g-plus  (17),
        er4800g-plus  (18),
        cr4800g-plus  (19),
        he4800g       (20),
        er4800g       (21),
        cr4800g       (22),
        he2400g-plus  (23),
        er2400g-plus  (24),
        cr2400g-plus  (25),
        he2400g       (26),
        er2400g       (27),
        cr2400g       (28),
        he9600g       (29),
        er9600g       (30),
        cr9600g       (31),
        he14400g      (32),
        er14400g      (33),
        cr14400g      (34),
        he14400g-plus (35),
        er14400g-plus (36),
        cr14400g-plus (37),
        he2800g-plus  (38),
        er2800g-plus  (39),
        cr2800g-plus  (40),
        he6000g-plus  (41),
        er6000g-plus  (42),
        cr6000g-plus  (43),
        he18000g-plus (44),
        er18000g-plus (45),
        cr18000g-plus (46),
        he19200g      (47),
        er19200g      (48),
        cr19200g      (49)
    }

TmnxCardFunctionalUpgrade        ::= TEXTUAL-CONVENTION
    STATUS      current
    DESCRIPTION
        "The TmnxCardFunctionalUpgrade data type is an integer that specifies a
         functional level upgrade of a given Card"
    SYNTAX      INTEGER {
        unknown           (0),
        cr-er             (1),
        er-he             (2),
        cr400g-cr1200gp   (3),
        er400g-er1200gp   (4),
        he400g-he1200gp   (5),
        cr-er1200gp       (6),
        er-he1200gp       (7),
        cr-er400gp        (8),
        er-he400gp        (9),
        cr-er800gp        (10),
        er-he800gp        (11),
        cr400g-cr800gp    (12),
        er400g-er800gp    (13),
        he400g-he800gp    (14),
        cr800g-cr1200gp   (15),
        er800g-er1200gp   (16),
        he800g-he1200gp   (17),
        cr-er2400g        (18),
        er-he2400g        (19),
        any2400g-2400gp   (20),
        cr-er4800g        (21),
        er-he4800g        (22),
        any4800g-4800gp   (23),
        cr-er9600g        (24),
        er-he9600g        (25),
        cr-er14400g       (26),
        er-he14400g       (27),
        he9600g-he14400g  (28),
        er9600g-er14400g  (29),
        cr9600g-cr14400g  (30),
        any14400g-14400gp (31),
        any2400g-2800gp   (32),
        any4800g-6000gp   (33),
        any14400g-18000gp (34),
        he2400g-he2800gp  (35),
        er2400g-er2800gp  (36),
        cr2400g-cr2800gp  (37),
        he4800g-he6000gp  (38),
        er4800g-er6000gp  (39),
        cr4800g-cr6000gp  (40),
        he14400g-he19200g (41),
        er14400g-er19200g (42),
        cr14400g-cr19200g (43),
        cr-er2800gp       (44),
        er-he2800gp       (45),
        cr-er6000gp       (46),
        er-he6000gp       (47),
        cr-er19200g       (48),
        er-he19200g       (49)
    }

TmnxMDAFunctionalLevel           ::= TEXTUAL-CONVENTION
    STATUS      current
    DESCRIPTION
        "The TmnxMDAFunctionalLevel data type is an integer that specifies a
         functional level variant of a given MDA type."
    SYNTAX      INTEGER {
        unknown         (0),
        unrestricted    (1),
        he2400g         (2),
        he1600g         (3),
        he1200g         (4),
        er2400g         (5),
        er1600g         (6),
        er1200g         (7),
        cr2400g         (8),
        cr1600g         (9),
        cr1200g         (10),
        he2400g-plus    (11),
        er2400g-plus    (12),
        cr2400g-plus    (13),
        he3600g         (14),
        er3600g         (15),
        cr3600g         (16),
        he3600gdd       (17),
        er3600gdd       (18),
        cr3600gdd       (19),
        he4800g         (20),
        er4800g         (21),
        cr4800g         (22),
        he4800g-plus    (23),
        er4800g-plus    (24),
        cr4800g-plus    (25),
        he600g          (26),
        er600g          (27),
        cr600g          (28),
        he1200g-plus    (29),
        er1200g-plus    (30),
        cr1200g-plus    (31),
        he2400g-plus-4t (32),
        er2400g-plus-4t (33),
        cr2400g-plus-4t (34),
        he9600g         (35),
        er9600g         (36),
        cr9600g         (37),
        he9600g-plus    (38),
        er9600g-plus    (39),
        cr9600g-plus    (40),
        he14400g        (41),
        er14400g        (42),
        cr14400g        (43),
        he14400g-plus   (44),
        er14400g-plus   (45),
        cr14400g-plus   (46),
        he12000g-plus   (47),
        er12000g-plus   (48),
        cr12000g-plus   (49),
        he18000g-plus   (50),
        er18000g-plus   (51),
        cr18000g-plus   (52)
    }

TmnxMDAFunctionalUpgrade         ::= TEXTUAL-CONVENTION
    STATUS      current
    DESCRIPTION
        "The TmnxMDAFunctionalUpgrade data type is an integer that specifies a
         functional level upgrade of a given MDA."
    SYNTAX      INTEGER {
        unknown                (0),
        cr1200g-cr1600g        (1),
        cr1600g-cr2400g        (2),
        er1200g-er1600g        (3),
        er1600g-er2400g        (4),
        he1200g-he1600g        (5),
        he1600g-he2400g        (6),
        cr1200g-er1200g        (7),
        er1200g-he1200g        (8),
        cr1600g-er1600g        (9),
        er1600g-he1600g        (10),
        cr2400g-er2400g        (11),
        er2400g-he2400g        (12),
        any2400g-2400g-plus    (13),
        cr3600g-cr4800g        (14),
        er3600g-er4800g        (15),
        he3600g-he4800g        (16),
        cr3600g-er3600g        (17),
        er3600g-he3600g        (18),
        cr4800g-er4800g        (19),
        er4800g-he4800g        (20),
        any3600g-3600gdd       (21),
        any4800g-4800g-plus    (22),
        cr600g-cr1200g         (23),
        er600g-er1200g         (24),
        he600g-he1200g         (25),
        cr600g-er600g          (26),
        er600g-he600g          (27),
        any1200g-1200g-plus    (28),
        any2400g-2400g-plus-4t (29),
        cr-er9600g             (30),
        er-he9600g             (31),
        any9600g-9600g-plus    (32),
        cr-er14400g            (33),
        er-he14400g            (34),
        any14400g-14400g-plus  (35),
        he9600g-he12000g-plus  (36),
        er9600g-er12000g-plus  (37),
        cr9600g-cr12000g-plus  (38),
        he14400g-he18000g-plus (39),
        er14400g-er18000g-plus (40),
        cr14400g-cr18000g-plus (41),
        cr-er12000g-plus       (42),
        er-he12000g-plus       (43),
        cr-er18000g-plus       (44),
        er-he18000g-plus       (45)
    }

TmnxXiomFunctionalLevel          ::= TEXTUAL-CONVENTION
    STATUS      current
    DESCRIPTION
        "The TmnxXiomFunctionalLevel data type is an integer that specifies a
         functional level variant of a given XIOM type."
    SYNTAX      INTEGER {
        unknown      (0),
        unrestricted (1),
        he800gPlus   (2),
        er800gPlus   (3),
        cr800gPlus   (4),
        he1500gPlus  (5),
        er1500gPlus  (6),
        cr1500gPlus  (7),
        he1600gPlus  (8),
        er1600gPlus  (9),
        cr1600gPlus  (10),
        he2400gPlus  (11),
        er2400gPlus  (12),
        cr2400gPlus  (13),
        he3000gPlus  (14),
        er3000gPlus  (15),
        cr3000gPlus  (16),
        he2400g      (17),
        er2400g      (18),
        cr2400g      (19),
        he4800g      (20),
        er4800g      (21),
        cr4800g      (22),
        he6000gPlus  (23),
        er6000gPlus  (24),
        cr6000gPlus  (25),
        he3200gPlus  (26),
        er3200gPlus  (27),
        cr3200gPlus  (28)
    }

TmnxXiomFunctionalUpgrade        ::= TEXTUAL-CONVENTION
    STATUS      current
    DESCRIPTION
        "The TmnxXiomFunctionalUpgrade data type is an integer that specifies a
         functional level upgrade of a given XIOM."
    SYNTAX      INTEGER {
        unknown            (0),
        cr800gCr1500gPlus  (1),
        er800gEr1500gPlus  (2),
        he800gHe1500gPlus  (3),
        cr1600gCr2400gPlus (4),
        er1600gEr2400gPlus (5),
        he1600gHe2400gPlus (6),
        cr2400gCr3000gPlus (7),
        er2400gEr3000gPlus (8),
        he2400gHe3000gPlus (9),
        crEr800gPlus       (10),
        erHe800gPlus       (11),
        crEr1500gPlus      (12),
        erHe1500gPlus      (13),
        crEr1600gPlus      (14),
        erHe1600gPlus      (15),
        crEr2400gPlus      (16),
        erHe2400gPlus      (17),
        crEr3000gPlus      (18),
        erHe3000gPlus      (19),
        cr4800gCr6000gPlus (20),
        er4800gEr6000gPlus (21),
        he4800gHe6000gPlus (22),
        crEr2400g          (23),
        erHe2400g          (24),
        crEr4800g          (25),
        erHe4800g          (26),
        crEr6000gPlus      (27),
        erHe6000gPlus      (28),
        cr1600gCr3000gPlus (29),
        er1600gEr3000gPlus (30),
        he1600gHe3000gPlus (31),
        crEr3200gPlus      (32),
        erHe3200gPlus      (33),
        cr3200gCr6000gPlus (34),
        er3200gEr6000gPlus (35),
        he3200gHe6000gPlus (36)
    }

TmnxGnssConstellation            ::= TEXTUAL-CONVENTION
    STATUS      current
    DESCRIPTION
        "TmnxGnssConstellation specifies or indicates the type of satellites
         that the GNSS receiver uses to acquire a fix.  The value 'gps'
         specifies that the receiver only uses the United States' Global
         Positioning System (GPS) satellites.  The value 'gps-glonass' specifies
         that the receiver uses both GPS and Russia's GLONASS satellites."
    SYNTAX      INTEGER {
        unknown     (0),
        gps         (1),
        gps-glonass (2)
    }

TmnxCardFilterProfile            ::= TEXTUAL-CONVENTION
    STATUS      current
    DESCRIPTION
        "TmnxCardFilterProfile specifies the filter scale profile for the card.
         The value 'none' specifies the default filter allocation for the
         chassis. The value 'profile-a' specifies a different filter allocation
         allowing additional ingress IPv4 filter entries at the expense of
         egress IPv4  and IPv6 filter entries."
    SYNTAX      INTEGER {
        none      (0),
        profile-a (1)
    }

TmnxCpmPowerShelfCommsFailStatus ::= TEXTUAL-CONVENTION
    STATUS      current
    DESCRIPTION
        "The value of TmnxCpmPowerShelfCommsFailStatus indicates which CPMs
         cannot communicate with the power shelf.

         Values:
            cpmA (0) - CPM A cannot communicate with the power shelf
            cpmB (1) - CPM B cannot communicate with the power shelf"
    SYNTAX      BITS {
        cpmA (0),
        cpmB (1)
    }

TmnxHwEventType                  ::= TEXTUAL-CONVENTION
    STATUS      current
    DESCRIPTION
        "The TmnxHwEventType is an enumerated integer that describes the types
         of events that can be detected and reported for different types of
         hardware.

         Not all types of events are supported on all hardware."
    SYNTAX      INTEGER {
        soft-error          (1),
        internal-frame-loss (2),
        memory-error        (3),
        datapath-link-error (4)
    }

TmnxHwEventAction                ::= TEXTUAL-CONVENTION
    STATUS      current
    DESCRIPTION
        "The value of TmnxHwEventAction describes the action to be taken when
         event is detected.

         The actions supported by this system include:
             none     (0) - No action
             log-only (1) - Log the event
             reset    (2) - Reset to recover the event
             fail     (3) - Fail the equipment"
    SYNTAX      INTEGER {
        none     (0),
        log-only (1),
        reset    (2),
        fail     (3)
    }

TmnxEsaId                        ::= TEXTUAL-CONVENTION
    STATUS      current
    DESCRIPTION
        "The TmnxEsaId uniquely identifies an Extended Services Appliance (ESA)
         within a Nokia SROS system."
    SYNTAX      Integer32 (1..16)

TmnxEsaIdOrZero                  ::= TEXTUAL-CONVENTION
    STATUS      current
    DESCRIPTION
        "The TmnxEsaIdOrZero can be either a nonzero TmnxEsaId, or the value
         zero."
    SYNTAX      Integer32 (0..16)

TmnxEsaVmId                      ::= TEXTUAL-CONVENTION
    STATUS      current
    DESCRIPTION
        "The TmnxEsaVmId uniquely identifies a virtual machine within an
         Extended Services Appliance (ESA) within a Nokia SROS system."
    SYNTAX      Unsigned32 (1..4)

TmnxEsaVmIdOrZero                ::= TEXTUAL-CONVENTION
    STATUS      current
    DESCRIPTION
        "The TmnxEsaVmIdOrZero can be either a nonzero TmnxEsaVmId, or the
         value zero."
    SYNTAX      Unsigned32 (0..4)

TmnxEsaDeviceState               ::= TEXTUAL-CONVENTION
    STATUS      current
    DESCRIPTION
        "The value of TmnxEsaDeviceState indicates the status of a certain
         device reported by the ESA as follows:
            - Unknown    : Device status not reported. Esa not connected or not booted yet.
            - Ok         : Device is functioning normally.
            - Degraded   : Device status is degraded.
            - Failed     : Device status is failed.
            - Unsupported: Device status reporting is unsupported."
    SYNTAX      INTEGER {
        unknown     (1),
        ok          (2),
        degraded    (3),
        failed      (4),
        unsupported (5)
    }

TmnxEsaDeviceRedundancyState     ::= TEXTUAL-CONVENTION
    STATUS      current
    DESCRIPTION
        "The TmnxEsaDeviceRedundancyState indicates the redundancy status of an ESA device,
         as follows:
            - Unknown          : Device redundancy status not reported. Esa not connected or not booted yet.
            - Redundant        : Device is redundant.
            - Non-Redundant    : Device is non-redundant.
            - Failed-Redundant : Device status is failed-redundant.
            - Unsupported      : Device redundancy state reporting is unsupported."
    SYNTAX      INTEGER {
        unknown          (1),
        redundant        (2),
        non-redundant    (3),
        failed-redundant (4),
        unsupported      (5)
    }

TmnxEsaDeviceMismatchState       ::= TEXTUAL-CONVENTION
    STATUS      current
    DESCRIPTION
        "The TmnxEsaDeviceMismatchState indicates the mismatch status of an ESA device,
         as follows:
            - unknown     : Device mismatch status not reported. Esa not connected or not booted yet.
            - noMismatch  : Device is in no mismatch state.
            - mismatch    : Device is in mismatch state.
            - unsupported : Device mismatch state reporting is unsupported."
    SYNTAX      INTEGER {
        unknown     (1),
        noMismatch  (2),
        mismatch    (3),
        unsupported (4)
    }

TmnxSBUefiVarsState              ::= TEXTUAL-CONVENTION
    STATUS      current
    DESCRIPTION
        "The TmnxSBUefiVarsState indicates whether the UEFI variables of a bootable device
         are up-to-date with the system, or in an error condition, as follows:
            - ok            : Device UEFI variables are up-to-date with the system.
            - updateReqd    : Device UEFI variables must be updated to be compatible with the
                              system.
            - unknown       : Device UEFI variables not currently available."
    SYNTAX      INTEGER {
        ok         (1),
        updateReqd (2),
        unknown    (3)
    }

TmnxIxrResourceOwner             ::= TEXTUAL-CONVENTION
    STATUS      current
    DESCRIPTION
        "The TmnxIxrResourceOwner is an enumerated integer that identifies the
         application that owns a resource."
    SYNTAX      INTEGER {
        bgp               (1),
        rsvp              (2),
        ldp               (3),
        srMpls            (4),
        serviceSdpBindGre (5),
        serviceSapRingAps (6),
        anysec            (8),
        service           (9),
        serviceSap        (10),
        serviceSdpBind    (11),
        serviceEvpn       (12),
        interface         (13),
        arp               (14),
        ipv6              (15),
        rtm               (16),
        ptp               (17),
        bfd               (18),
        port              (19),
        ethCfm            (20),
        treeSid           (21),
        serviceSdpGre     (22),
        portLagVlanQos    (23),
        srv6              (24)
    }

TmnxCardIxrResourceOwner         ::= TEXTUAL-CONVENTION
    STATUS      current
    DESCRIPTION
        "The TmnxCardIxrResourceOwner is an enumerated integer that identifies
         the application that owns a card resource."
    SYNTAX      INTEGER {
        system                (0),
        filter                (1),
        ipMulticast           (2),
        mpls                  (3),
        ipRouting             (4),
        arp                   (5),
        nd                    (6),
        interface             (7),
        sapEndpoint           (8),
        mplsEcmp              (9),
        ipRoutingEcmp         (10),
        srv6DirectIpTransport (11),
        tunnelEcmp            (12),
        rvplsOism             (13),
        sdpBindings           (14),
        evpnBindings          (15),
        mvpnNhlfe             (16),
        mplsMulticastFrr      (17),
        sbfd                  (18)
    }

TmnxEsaHostPortMonReportValue    ::= TEXTUAL-CONVENTION
    STATUS      current
    DESCRIPTION
        "The TmnxEsaHostPortMonReportValue is an enumerated integer that
         describes the values used to identify the reason an alarm has been
         raised for a fault in Monitoring on an Ethernet Port.
         TmnxPortEtherMonReportStatus defines the valid alarm values."
    SYNTAX      INTEGER {
        noFault             (0),
        sdThresholdExceeded (1),
        sfThresholdExceeded (2)
    }

TmnxMdaFlexGroupErrors           ::= TEXTUAL-CONVENTION
    STATUS      current
    DESCRIPTION
        "The value of TmnxMdaFlexGroupErrors indicates the error conditions
         related to a Flex group, as follows:
            - notUsed                : No error conditions present.
            - overheadFrameNotLocked : Group does not have overhead frame lock.
            - deskewFailed           : Group member not deskewed.
            - localPhyFault          : One or more members have a local PHY fault.
            - remotePhyFault         : One or more members received remote PHY fault.
            - badGroupNumber         : One or more PHY instances received a bad group
                                       number.
            - badPhyNumber           : One or more PHY instances received a bad PHY
                                       number.
            - badPhyInstanceNumber   : One or more PHY instances received a bad PHY
                                       instance number.
            - flexEMapMismatch       : The received FlexE map does not map the
                                       local map.
            - clientCalendarError    : One or more PHY instances received an invalid
                                       calendar.
            - calendarInUseError     : One or more PHY instances received an indication
                                       of the wrong calendar in use."
    SYNTAX      BITS {
        notUsed                (0),
        overheadFrameNotLocked (1),
        deskewFailed           (2),
        localPhyFault          (3),
        remotePhyFault         (4),
        badGroupNumber         (5),
        badPhyNumber           (6),
        badPhyInstanceNumber   (7),
        flexEMapMismatch       (8),
        clientCalendarError    (9),
        calendarInUseError     (10)
    }

TmnxMdaFlexMemberErrors          ::= TEXTUAL-CONVENTION
    STATUS      current
    DESCRIPTION
        "The value of TmnxMdaFlexMemberErrors indicates the error conditions
         related to a Flex member, as follows:
            - notUsed       : No error conditions present.
            - los           : No receive signal present.
            - highBer       : High receive BER.
            - amNotLocked   : Unable to achieve alignment marker lock.
            - deskewFailed  : Unable to deskew this PHY.
            - remotePhyFault: Member PHY has remote fault."
    SYNTAX      BITS {
        notUsed        (0),
        los            (1),
        highBer        (2),
        amNotLocked    (3),
        deskewFailed   (4),
        remotePhyFault (5)
    }

TmnxMdaFlexMbrInstErrors         ::= TEXTUAL-CONVENTION
    STATUS      current
    DESCRIPTION
        "The value of TmnxMdaFlexMbrInstErrors indicates the error conditions
         relating to a 100G FlexE PHY instance, as follows:
            - notUsed               : No error conditions present.
            - badCrc                : Header CRC failed.
            - multiframeNotLocked   : Cannot achieve multiframe lock.
            - badGroupNumber        : Received group number doesn't match local value.
            - badPhyNumber          : Received PHY number doesn't match local value.
            - badPhyInstanceNumber  : Received PHY instance number error (duplicate).
            - flexEMapMismatch      : The received FlexE map does not match the local map data.
            - clientCalendarError   : The data in the client calendar is not a supported configuration.
            - calendarInUseError    : The received calendar in use indicate has wrong value."
    SYNTAX      BITS {
        notUsed              (0),
        badCrc               (1),
        multiframeNotLocked  (2),
        badGroupNumber       (3),
        badPhyNumber         (4),
        badPhyInstanceNumber (5),
        flexEMapMismatch     (6),
        clientCalendarError  (7),
        calendarInUseError   (8)
    }

TmnxFpIxrAvailableLifs           ::= TEXTUAL-CONVENTION
    STATUS      current
    DESCRIPTION
        "The value of TmnxFpIxrAvailableLifs indicates the availability of
         LIF types for a given FP and Cluster phase, as follows:
          - undetermined           : Availability cannot be determined at this time.
          - noneAvailable          : No LIF types are available.
          - standardLifsOnly       : Only standard LIFs are available.
          - dataLifsOnly           : Only data LIFs are available.
          - standardAndDataLifs    : Both standard and data LIFs are available.
          - notApplicable          : Not applicable."
    SYNTAX      INTEGER {
        undetermined        (0),
        noneAvailable       (1),
        standardLifsOnly    (2),
        dataLifsOnly        (3),
        standardAndDataLifs (4),
        notApplicable       (-1)
    }

tmnxHwObjs                       OBJECT IDENTIFIER ::= { tmnxSRObjs 2 }

tmnxChassisObjs                  OBJECT IDENTIFIER ::= { tmnxHwObjs 1 }

tmnxChassisTotalNumber           OBJECT-TYPE
    SYNTAX      Integer32 (1..32)
    MAX-ACCESS  read-only
    STATUS      current
    DESCRIPTION
        "The number of chassis installed in this system.  For the first
         release of the Nokia 7x50 series product, there is only
         1 chassis per system.  A multi-chassis system model is supported
         to allow for future product expansion."
    ::= { tmnxChassisObjs 1 }

tmnxChassisLastChange            OBJECT-TYPE
    SYNTAX      TimeStamp
    MAX-ACCESS  read-only
    STATUS      current
    DESCRIPTION
        "The value of tmnxChassisLastChange indicates the time, since system
         startup, when tmnxChassisTable last changed."
    ::= { tmnxChassisObjs 2 }

tmnxChassisTable                 OBJECT-TYPE
    SYNTAX      SEQUENCE OF TmnxChassisEntry
    MAX-ACCESS  not-accessible
    STATUS      current
    DESCRIPTION
        "tmnxChassisTable contains Nokia 7x50 system level information."
    ::= { tmnxChassisObjs 3 }

tmnxChassisEntry                 OBJECT-TYPE
    SYNTAX      TmnxChassisEntry
    MAX-ACCESS  not-accessible
    STATUS      current
    DESCRIPTION
        "tmnxChassisEntry consists of the system level information pertaining
         to the hardware present in the system.

         Only one entry is created and maintained by the system, which is
         assigned the tmnxChassisIndex value '1'. Once this entry is created,
         it cannot be destroyed. Additional entries cannot be manually created
         or destroyed.

         Support of multiple chassis' are managed through the use of
         tmnxPhysChassisTable."
    INDEX       { tmnxChassisIndex }
    ::= { tmnxChassisTable 1 }

TmnxChassisEntry                 ::= SEQUENCE
{
    tmnxChassisIndex                 TmnxChassisIndex,
    tmnxChassisRowStatus             RowStatus,
    tmnxChassisName                  TLNamedItemOrEmpty,
    tmnxChassisType                  TmnxChassisType,
    tmnxChassisLocation              TItemDescription,
    tmnxChassisCoordinates           TItemDescription,
    tmnxChassisNumSlots              Unsigned32,
    tmnxChassisNumPorts              Unsigned32,
    tmnxChassisNumPwrSupplies        Unsigned32,
    tmnxChassisNumFanTrays           Unsigned32,
    tmnxChassisNumFans               Unsigned32,
    tmnxChassisCriticalLEDState      TmnxLEDState,
    tmnxChassisMajorLEDState         TmnxLEDState,
    tmnxChassisMinorLEDState         TmnxLEDState,
    tmnxChassisBaseMacAddress        MacAddress,
    tmnxChassisCLLICode              DisplayString,
    tmnxChassisReboot                TmnxActionType,
    tmnxChassisUpgrade               TmnxActionType,
    tmnxChassisAdminMode             TmnxChassisMode,
    tmnxChassisOperMode              TmnxChassisMode,
    tmnxChassisModeForce             TmnxActionType,
    tmnxChassisUpdateWaitTime        Unsigned32,
    tmnxChassisUpdateTimeLeft        Unsigned32,
    tmnxChassisOverTempState         INTEGER,
    tmnxChassisMixedModeIomAdminMode TmnxEnabledDisabled,
    tmnxChassisMixedModeIomUpgrList  BITS,
    tmnxChassisRedForcedSingleSfm    TruthValue,
    tmnxChassisOperNumSlots          Unsigned32,
    tmnxChassisOperTopology          INTEGER,
    tmnxChassisFabricSpeed           INTEGER,
    tmnxChassisPortIdScheme          INTEGER,
    tmnxChassisVsrCongestionMgmt     TruthValue,
    tmnxChassisAlarmLEDState         TmnxLEDState,
    tmnxChassisFPGenerationFP2       TruthValue,
    tmnxChassisFPGenerationFP3       TruthValue,
    tmnxChassisFPGenerationFP4       TruthValue,
    tmnxChassisNumPhysicalPorts      Unsigned32,
    tmnxChassisFPGenerationVFP       TruthValue,
    tmnxChassisSystemProfile         INTEGER,
    tmnxChassisFPGenerationFP5       TruthValue,
    tmnxChassisRebootReqd            TruthValue,
    tmnxChassisRebootReqdReason      BITS,
    tmnxChassisOsSecPasswd           TmnxEnabledDisabled,
    tmnxChassisAntiTheftLocked       TruthValue,
    tmnxChassisPortSpeedMode         DisplayString
}

tmnxChassisIndex                 OBJECT-TYPE
    SYNTAX      TmnxChassisIndex
    MAX-ACCESS  not-accessible
    STATUS      current
    DESCRIPTION
        "The value of tmnxChassisIndex specifies a system identifier. The value
         of this object cannot be changed. The only supported value is '1'.

         Different values of TmnxPhysChassisIndex are used to identify
         different physical chassis (e.g. in an XRS-40 system) in
         tmnxPhysChassisTable."
    ::= { tmnxChassisEntry 1 }

tmnxChassisRowStatus             OBJECT-TYPE
    SYNTAX      RowStatus
    MAX-ACCESS  read-create
    STATUS      current
    DESCRIPTION
        "The value of tmnxChassisRowStatus specifies the row status of the
         system."
    ::= { tmnxChassisEntry 2 }

tmnxChassisName                  OBJECT-TYPE
    SYNTAX      TLNamedItemOrEmpty
    MAX-ACCESS  read-create
    STATUS      current
    DESCRIPTION
        "The value of tmnxChassisName specifies the administrative name
         that is assigned to the system.  Setting tmnxChassisName to the
         empty string, ''H, resets tmnxChassisName to the TiMOS default value."
    DEFVAL      { "" }
    ::= { tmnxChassisEntry 3 }

tmnxChassisType                  OBJECT-TYPE
    SYNTAX      TmnxChassisType
    MAX-ACCESS  read-only
    STATUS      current
    DESCRIPTION
        "The value of tmnxChassisType indicates the type of chassis used in
         this Nokia SROS system.  The value of this object is the
         tmnxChassisTypeIndex for the entry in the tmnxChassisTypeTable that
         represents the Nokia SROS series chassis model for this
         system.  Chassis types are distinguished by their backplane type."
    ::= { tmnxChassisEntry 4 }

tmnxChassisLocation              OBJECT-TYPE
    SYNTAX      TItemDescription
    MAX-ACCESS  read-create
    STATUS      current
    DESCRIPTION
        "The value of tmnxChassisLocation specifies the site location of this
         system. This could be used for a Common Language Location Identifier,
         CLLI, code string if desired.

         A CLLI code is an 11 character standardized geographic identifier that
         uniquely identifies the geographic location of places and certain
         functional categories of equipment unique to the telecommunications
         industry.

         All valid CLLI codes are created, updated and maintained in the
         Central Location Online Entry System (CLONES) database."
    DEFVAL      { "" }
    ::= { tmnxChassisEntry 5 }

tmnxChassisCoordinates           OBJECT-TYPE
    SYNTAX      TItemDescription
    MAX-ACCESS  read-create
    STATUS      current
    DESCRIPTION
        "The value of tmnxChassisCoordinates specifies the Global Positioning
         System (GPS) coordinates for the location of the system.

            N 45 58 23, W 34 56 12
            N37 37' 00 latitude, W122 22' 00 longitude
            N36*39.246'  W121*40.121'

         Two-dimensional GPS positioning offers latitude and longitude
         information as a four dimensional vector:

            <Direction, hours, minutes, seconds>

         where Direction is one of the four basic values: N, S, W, E; hours
         ranges from 0 to 180 (for latitude) and 0 to 90 for longitude, and,
         finally, minutes and seconds range from 0 to 60.

         Thus <W, 122, 56, 89> is an example of longitude and <N, 85, 66, 43>
         is an example of latitude.

         Four bytes of addressing space (one byte for each of the four
         dimensions) are necessary to store latitude and four bytes are also
         sufficient to store longitude. Thus eight bytes total are necessary
         to address the whole surface of earth with precision down to 0.1
         mile!  Notice that if we desired precision down to 0.001 mile (1.8
         meters) then we would need just five bytes for each component, or ten
         bytes together for the full address (as military versions provide)."
    DEFVAL      { "" }
    ::= { tmnxChassisEntry 6 }

tmnxChassisNumSlots              OBJECT-TYPE
    SYNTAX      Unsigned32
    MAX-ACCESS  read-only
    STATUS      current
    DESCRIPTION
        "The value of tmnxChassisNumSlots indicates the maximum number of slots
         that can be made available for plug-in cards if the maximum number of
         physical router chassis are populated. This includes both CPM and
         IOM/IMM/XCM slots. For systems that support only a single physical
         chassis, tmnxChassisNumSlots and tmnxChassisOperNumSlots are the same
         value and are equal to the number of physical slots in the chassis.
         Also see tmnxChassisOperNumSlots."
    ::= { tmnxChassisEntry 7 }

tmnxChassisNumPorts              OBJECT-TYPE
    SYNTAX      Unsigned32
    MAX-ACCESS  read-only
    STATUS      current
    DESCRIPTION
        "The value of tmnxChassisNumPorts indicates the total number of
         faceplate ports and connectors currently installed for all of the
         physical router chassis in the system. This count does not include the
         Ethernet ports on the CPM cards that are used for management access."
    ::= { tmnxChassisEntry 8 }

tmnxChassisNumPwrSupplies        OBJECT-TYPE
    SYNTAX      Unsigned32
    MAX-ACCESS  read-only
    STATUS      current
    DESCRIPTION
        "The value of tmnxChassisNumPwrSupplies indicates the total number of
         power supplies installed for all of the physical router chassis in the
         system."
    ::= { tmnxChassisEntry 9 }

tmnxChassisNumFanTrays           OBJECT-TYPE
    SYNTAX      Unsigned32
    MAX-ACCESS  read-only
    STATUS      current
    DESCRIPTION
        "The value of tmnxChassisNumFanTrays indicates the total number of fan
         trays installed for all of the physical router chassis in the system."
    ::= { tmnxChassisEntry 10 }

tmnxChassisNumFans               OBJECT-TYPE
    SYNTAX      Unsigned32
    MAX-ACCESS  read-only
    STATUS      current
    DESCRIPTION
        "The value of tmnxChassisNumFans indicates the total number of fans
         installed for all of the physical router chassis in the system."
    ::= { tmnxChassisEntry 11 }

tmnxChassisCriticalLEDState      OBJECT-TYPE
    SYNTAX      TmnxLEDState
    MAX-ACCESS  read-only
    STATUS      current
    DESCRIPTION
        "The value of tmnxChassisCriticalLEDState indicates the current state
         of the Critical LED in the system."
    ::= { tmnxChassisEntry 12 }

tmnxChassisMajorLEDState         OBJECT-TYPE
    SYNTAX      TmnxLEDState
    MAX-ACCESS  read-only
    STATUS      current
    DESCRIPTION
        "The value of tmnxChassisMajorLEDState indicates the current state of
         the Major LED in the system."
    ::= { tmnxChassisEntry 13 }

tmnxChassisMinorLEDState         OBJECT-TYPE
    SYNTAX      TmnxLEDState
    MAX-ACCESS  read-only
    STATUS      current
    DESCRIPTION
        "The value of tmnxChassisMinorLEDState indicates the current state of
         the Minor LED in the system."
    ::= { tmnxChassisEntry 14 }

tmnxChassisBaseMacAddress        OBJECT-TYPE
    SYNTAX      MacAddress
    MAX-ACCESS  read-only
    STATUS      current
    DESCRIPTION
        "The value of tmnxChassisBaseMacAddress indicates the base system
         ethernet MAC address. Special purpose MAC addresses used by the system
         software are constructed as offsets from this base address."
    ::= { tmnxChassisEntry 15 }

tmnxChassisCLLICode              OBJECT-TYPE
    SYNTAX      DisplayString
    MAX-ACCESS  read-create
    STATUS      current
    DESCRIPTION
        "The value of tmnxChassisCLLICode specifies the Common Language
         Location Identifier (CLLI) code for the system. A CLLI code is an 11
         character standardized geographic identifier that uniquely identifies
         the geographic location of places and certain functional categories of
         equipment unique to the telecommunications industry.

         If the set on this object specifies a non-null string, the string will
         automatically be truncated or padded (with spaces) to 11 characters."
    ::= { tmnxChassisEntry 16 }

tmnxChassisReboot                OBJECT-TYPE
    SYNTAX      TmnxActionType
    MAX-ACCESS  read-create
    STATUS      current
    DESCRIPTION
        "The value of tmnxChassisReboot specifies if the system will perform a
         reboot.

         Setting the value of this object to 'doAction' causes a soft-reboot of
         the entire system including all the CPM and IOM cards for each
         physical chassis.

         Note that the reboot action is likely to occur before the SNMP SET
         response can be transmitted."
    DEFVAL      { notApplicable }
    ::= { tmnxChassisEntry 17 }

tmnxChassisUpgrade               OBJECT-TYPE
    SYNTAX      TmnxActionType
    MAX-ACCESS  read-create
    STATUS      current
    DESCRIPTION
        "The value of tmnxChassisUpgrade specifies if the system will perform
         an upgrade of all firmware as well as a reboot of the entire system
         including all the CPM and IOM cards for each physical chassis.

         CAUTION: This upgrade and reboot may take several minutes to
         complete.  The chassis MUST NOT be reset or powered down,
         nor cards inserted or removed, during this process.  Any of
         these prohibited actions may cause the cards to be rendered
         inoperable.

         tmnxChassisUpgrade and tmnxChassisReboot must be set together in the
         same SNMP SET request PDU or else the SET request will fail with an
         inconsistentValue error.

         Note that the reboot action is likely to occur before the SNMP SET
         response can be transmitted."
    DEFVAL      { notApplicable }
    ::= { tmnxChassisEntry 18 }

tmnxChassisAdminMode             OBJECT-TYPE
    SYNTAX      TmnxChassisMode
    MAX-ACCESS  read-create
    STATUS      current
    DESCRIPTION
        "The value of tmnxChassisAdminMode specifies the scaling and feature
         set for all of the IOM cards in the system. Setting
         tmnxChassisAdminMode to a particular mode corresponds to the scaling
         and feature sets supported on that IOM card type."
    DEFVAL      { modeD }
    ::= { tmnxChassisEntry 19 }

tmnxChassisOperMode              OBJECT-TYPE
    SYNTAX      TmnxChassisMode
    MAX-ACCESS  read-only
    STATUS      current
    DESCRIPTION
        "The value of tmnxChassisOperMode indicates the operational scaling and
         feature set for all IOM cards in the system for each physical router
         chassis. Changing the value of tmnxChassisAdminMode from a greater
         mode to a lesser mode (downgrade) will result in tmnxChassisAdminMode
         indicating the new mode while tmnxChassisOperMode indicates previous
         mode until the configuration is saved and the system rebooted, at
         which point, the actual downgrade will take effect and both
         tmnxChassisAdminMode and tmnxChassisOperMode will indicate the new
         mode.

         Upgrading from a lesser mode to a greater mode (e.g. From 'modeA' to
         'modeB') will take effect immediately and the tmnxChassisOperMode will
         indicate the same mode as that of tmnxChassisAdminMode."
    ::= { tmnxChassisEntry 20 }

tmnxChassisModeForce             OBJECT-TYPE
    SYNTAX      TmnxActionType
    MAX-ACCESS  read-create
    STATUS      current
    DESCRIPTION
        "The value of tmnxChassisModeForce specifies the force mode of the
         system. Setting the value of this object to 'doAction' in the same
         SNMP SET request where tmnxChassisAdminMode is set to a greater mode
         than the current mode (e.g. New mode 'modeB', while current is
         'modeA') allows each physical chassis in the system to be upgraded to
         the new mode even if there are IOM cards in the physical chassis with
         a tmnxCardAssignedType value that does not support the new mode.

         An attempt to set tmnxChassisModeForce to 'doAction' without also
         setting tmnxChassisAdminMode, in the same SNMP SET request will fail
         with an inconsistentValue error."
    DEFVAL      { notApplicable }
    ::= { tmnxChassisEntry 21 }

tmnxChassisUpdateWaitTime        OBJECT-TYPE
    SYNTAX      Unsigned32 (15..600)
    UNITS       "seconds"
    MAX-ACCESS  read-create
    STATUS      obsolete
    DESCRIPTION
        "The value of tmnxChassisUpdateWaitTime specifies the time to wait
         before rebooting IOM cards running older software versions following a
         software upgrade or downgrade activity switchover. This object was
         obsoleted in release 5.0."
    DEFVAL      { 15 }
    ::= { tmnxChassisEntry 22 }

tmnxChassisUpdateTimeLeft        OBJECT-TYPE
    SYNTAX      Unsigned32
    UNITS       "seconds"
    MAX-ACCESS  read-only
    STATUS      obsolete
    DESCRIPTION
        "Following a software upgrade or downgrade activity switchover, the
         value of tmnxChassisUpdateTimeLeft indicates the time remaining before
         IOM cards or MDAs running older software versions will be rebooted."
    ::= { tmnxChassisEntry 23 }

tmnxChassisOverTempState         OBJECT-TYPE
    SYNTAX      INTEGER {
        stateOk       (1),
        stateOverTemp (2)
    }
    MAX-ACCESS  read-only
    STATUS      current
    DESCRIPTION
        "The value of tmnxChassisOverTempState indicates the over temperature
         state for the system.

         stateOk         Indicates all physical router chassis are below the
                         temperature threshold.
         stateOverTemp   Indicates at least one physical router chassis is
                         above the temperature threshold."
    ::= { tmnxChassisEntry 24 }

tmnxChassisMixedModeIomAdminMode OBJECT-TYPE
    SYNTAX      TmnxEnabledDisabled
    MAX-ACCESS  read-create
    STATUS      obsolete
    DESCRIPTION
        "The value of tmnxChassisMixedModeIomAdminMode specifies if the system
         should allow functionally to run with a mixture of forwarding
         hardware.

         When 'enabled(1)' on a 7450 chassis it allows SR functionality to be
         configured. SR functionality is a superset of ESS functionality. Once
         tmnxChassisMixedModeIomAdminMode is enabled, additional IOMs can be
         converted to SR functionality by setting the tmnxCardCapability field
         of the corresponding tmnxCardEntry.

         When 'enabled(1)' on a 7750 chassis it allows allows IPv6
         functionality without requiring chassis mode C or better.

         tmnxChassisMixedModeIomAdminMode is only applicable when
         tmnxChassisType indicates the chassis type is 7450 ESS-6, 7450 ESS-6v,
         7450 ESS-7, 7450 ESS-12, 7750 SR-7 or 7750 SR-12."
    DEFVAL      { disabled }
    ::= { tmnxChassisEntry 25 }

tmnxChassisMixedModeIomUpgrList  OBJECT-TYPE
    SYNTAX      BITS {
        iomSlot1  (0),
        iomSlot2  (1),
        iomSlot3  (2),
        iomSlot4  (3),
        iomSlot5  (4),
        iomSlot6  (5),
        iomSlot7  (6),
        iomSlot8  (7),
        iomSlot9  (8),
        iomSlot10 (9)
    }
    MAX-ACCESS  read-create
    STATUS      obsolete
    DESCRIPTION
        "The value of tmnxChassisMixedModeIomUpgrList specifies the list of IOM
         slots which are to operate with SR functionality on the 7450 chassis.

         tmnxChassisMixedModeIomUpgrList is only applicable when
         tmnxChassisType indicates the chassis type is 7450 ESS-7 or 7450
         ESS-12, and should only be set when enabling mixed-mode.

         tmnxChassisMixedModeIomUpgrList is a bitmap, with a bit for each IOM
         slot on the chassis.  If the bit for a particular IOM slot is '1', the
         SR functionality will be enabled on the IOM when enabling mixed-mode.
         If the bit is set to '0', the IOM will continue to operate with ESS
         functionality.

         To set a particular bit to '1':
         1.  The IOM slot must have a configured type of iom3-xp, or any type of
             IMM.
         2.  The installed IOM/IMM must be a 7750 IOM/IMM.  The platform type
             for an IOM/IMM can be read using tmnxHwEquippedPlatform.
         3.  tmnxChassisMixedModeIomAdminMode must be set to 'enabled (1)' in
             the same Set request packet."
    DEFVAL      { {} }
    ::= { tmnxChassisEntry 26 }

tmnxChassisRedForcedSingleSfm    OBJECT-TYPE
    SYNTAX      TruthValue
    MAX-ACCESS  read-create
    STATUS      current
    DESCRIPTION
        "The value of tmnxChassisRedForcedSingleSfm specifies whether or not
         the IGP single-SFM-overload state is forced to 'overload' in the
         router instances where single-SFM-overload state (referred to as
         TIMETRA-VRTR-MIB::vRtrSingleSfmOverloadAdminState) is equal to
         'inService'."
    DEFVAL      { false }
    ::= { tmnxChassisEntry 27 }

tmnxChassisOperNumSlots          OBJECT-TYPE
    SYNTAX      Unsigned32
    MAX-ACCESS  read-only
    STATUS      current
    DESCRIPTION
        "The value of tmnxChassisOperNumSlots indicates the number of slots
         that are available for plug-in cards of all the physical router
         chassis configured in the system. This includes both CPM and
         IOM/IMM/XCM slots. For systems that support multiple chassis, this
         value will change depending on how many chassis the system is
         configured to be operating with."
    ::= { tmnxChassisEntry 29 }

tmnxChassisOperTopology          OBJECT-TYPE
    SYNTAX      INTEGER {
        standalone (1),
        extended   (2)
    }
    MAX-ACCESS  read-only
    STATUS      current
    DESCRIPTION
        "The value of tmnxChassisOperTopology indicates the inter-chassis
         topology mode in which the system is operating. It indicates how
         multiple chassis are arranged and operate together as a single system.

         A value of 'standalone (1)' indicates that the system is comprised of
         a single physical router chassis.

         A value of 'extended(2)' in a 7950 XRS based system indicates that two
         router chassis are connected together in a 'back-to-back' topology
         with no additional switch fabric chassis. An extended chassis topology
         is comprised of two XRS-20 chassis and is also known as an XRS-40
         system."
    ::= { tmnxChassisEntry 30 }

tmnxChassisFabricSpeed           OBJECT-TYPE
    SYNTAX      INTEGER {
        notApplicable (0),
        speed6g       (1),
        speed10g      (2),
        speedS4       (3),
        speedS5       (4)
    }
    MAX-ACCESS  read-only
    STATUS      current
    DESCRIPTION
        "The value of tmnxChassisFabricSpeed indicates the system fabric speed.

         On systems that do not calculate the system fabric speed the value
         'notApplicable (0)' is returned."
    ::= { tmnxChassisEntry 31 }

tmnxChassisPortIdScheme          OBJECT-TYPE
    SYNTAX      INTEGER {
        schemeA   (1),
        schemeB   (2),
        schemeC   (3),
        schemeD   (4),
        schemeE   (5),
        reserved6 (6),
        reserved7 (7)
    }
    MAX-ACCESS  read-only
    STATUS      current
    DESCRIPTION
        "The value of tmnxChassisPortIdScheme indicates the encoding scheme
         used by physical ports and channels represented by the
         TIMETRA-TC-MIB::TmnxPortID textual convention.

         If you require the definition of these encodings, contact your Nokia
         support representative."
    ::= { tmnxChassisEntry 32 }

tmnxChassisVsrCongestionMgmt     OBJECT-TYPE
    SYNTAX      TruthValue
    MAX-ACCESS  read-create
    STATUS      current
    DESCRIPTION
        "The value of tmnxChassisVsrCongestionMgmt specifies whether Virtual
         Service Router congestion management is turned on."
    DEFVAL      { false }
    ::= { tmnxChassisEntry 33 }

tmnxChassisAlarmLEDState         OBJECT-TYPE
    SYNTAX      TmnxLEDState
    MAX-ACCESS  read-only
    STATUS      current
    DESCRIPTION
        "On systems that have a single alarm LED, the value of
         tmnxChassisAlarmLEDState indicates the current state of the alarm LED
         in the system."
    ::= { tmnxChassisEntry 34 }

tmnxChassisFPGenerationFP2       OBJECT-TYPE
    SYNTAX      TruthValue
    MAX-ACCESS  read-only
    STATUS      current
    DESCRIPTION
        "The value of tmnxChassisFPGenerationFP2 indicates whether the system
         contains at least one FP2 based line card."
    ::= { tmnxChassisEntry 35 }

tmnxChassisFPGenerationFP3       OBJECT-TYPE
    SYNTAX      TruthValue
    MAX-ACCESS  read-only
    STATUS      current
    DESCRIPTION
        "The value of tmnxChassisFPGenerationFP3 indicates whether the system
         contains at least one FP3 based line card."
    ::= { tmnxChassisEntry 36 }

tmnxChassisFPGenerationFP4       OBJECT-TYPE
    SYNTAX      TruthValue
    MAX-ACCESS  read-only
    STATUS      current
    DESCRIPTION
        "The value of tmnxChassisFPGenerationFP4 indicates whether the system
         contains at least one FP4 based line card."
    ::= { tmnxChassisEntry 37 }

tmnxChassisNumPhysicalPorts      OBJECT-TYPE
    SYNTAX      Unsigned32
    MAX-ACCESS  read-only
    STATUS      current
    DESCRIPTION
        "The value of tmnxChassisNumPhysicalPorts indicates the total number of
         faceplate ports and connector-ports currently installed for all the
         physical router chassis in the system. This count does not include the
         Ethernet ports on the CPM cards that are used for management access."
    ::= { tmnxChassisEntry 38 }

tmnxChassisFPGenerationVFP       OBJECT-TYPE
    SYNTAX      TruthValue
    MAX-ACCESS  read-only
    STATUS      current
    DESCRIPTION
        "The value of tmnxChassisFPGenerationVFP indicates whether the system
         contains at least one VFP based line card."
    ::= { tmnxChassisEntry 39 }

tmnxChassisSystemProfile         OBJECT-TYPE
    SYNTAX      INTEGER {
        none     (0),
        profileA (1),
        profileB (2)
    }
    MAX-ACCESS  read-only
    STATUS      current
    DESCRIPTION
        "The value of tmnxChassisSystemProfile indicates the system profile in
         the chassis.

           'none (0)'   - No system profile set, permits the co-existence of
                          FP3 and FP4-based line cards in the system.
           'profileA (1)- On SR, this system profile is primarily targeted at
                          subscriber services and layer 2/3 VPN business
                          services.
                          On SAR, this system profile is primarily targeted at
                          generic deployment scenarios, IP forwarding and MPLS
                          switching use-cases.
           'profileB (2)- On SR, this system profile is primarily targeted at
                          infrastructure routing, core, peering, and DC-GW
                          applications.
                          On SAR, this system profile is primarily targeted at
                          applications requiring high packet manipulation and
                          processing (e.g. NAT/IPSEC)."
    ::= { tmnxChassisEntry 40 }

tmnxChassisFPGenerationFP5       OBJECT-TYPE
    SYNTAX      TruthValue
    MAX-ACCESS  read-only
    STATUS      current
    DESCRIPTION
        "The value of tmnxChassisFPGenerationFP5 indicates whether the system
         contains at least one FP5 based line card."
    ::= { tmnxChassisEntry 41 }

tmnxChassisRebootReqd            OBJECT-TYPE
    SYNTAX      TruthValue
    MAX-ACCESS  read-only
    STATUS      current
    DESCRIPTION
        "The value of tmnxChassisRebootReqd indicates if a condition exists on
         the node that requires a manually triggered reboot."
    ::= { tmnxChassisEntry 42 }

tmnxChassisRebootReqdReason      OBJECT-TYPE
    SYNTAX      BITS {
        upgradeAslChange       (0),
        fpResourcePolicyChange (1),
        bofConfigurationChange (2),
        reserved3              (3),
        fpOptionsChange        (4),
        fpResourceAllocChange  (5),
        fpCamAllocChange       (6),
        isaMdaDeprovision      (7),
        reserved8              (8),
        reserved9              (9),
        reserved10             (10),
        reserved11             (11),
        reserved12             (12),
        reserved13             (13),
        reserved14             (14),
        reserved15             (15)
    }
    MAX-ACCESS  read-only
    STATUS      current
    DESCRIPTION
        "The value of tmnxChassisRebootReqdReason specifies a bitmask that
         identifies the reason(s) why a reboot is required."
    ::= { tmnxChassisEntry 43 }

tmnxChassisOsSecPasswd           OBJECT-TYPE
    SYNTAX      TmnxEnabledDisabled
    MAX-ACCESS  read-only
    STATUS      current
    DESCRIPTION
        "The value of tmnxChassisOsSecPasswd indicates whether a system-wide OS
         Security Password has been set, thereby activating the OS Security
         feature suite."
    ::= { tmnxChassisEntry 44 }

tmnxChassisAntiTheftLocked       OBJECT-TYPE
    SYNTAX      TruthValue
    MAX-ACCESS  read-only
    STATUS      current
    DESCRIPTION
        "The value of tmnxChassisAntiTheftLocked indicates whether the system
         is currently locked by the Anti-Theft component of the OS Security
         suite."
    ::= { tmnxChassisEntry 45 }

tmnxChassisPortSpeedMode         OBJECT-TYPE
    SYNTAX      DisplayString (SIZE (1..40))
    MAX-ACCESS  read-only
    STATUS      current
    DESCRIPTION
        "The value of tmnxChassisPortSpeedMode indicates the port speed mode
         that the chassis is operating in."
    ::= { tmnxChassisEntry 46 }

tmnxChassisFanTable              OBJECT-TYPE
    SYNTAX      SEQUENCE OF TmnxChassisFanEntry
    MAX-ACCESS  not-accessible
    STATUS      obsolete
    DESCRIPTION
        "This table contains information about fan trays.

         This table was made obsolete in release 15.0."
    ::= { tmnxChassisObjs 4 }

tmnxChassisFanEntry              OBJECT-TYPE
    SYNTAX      TmnxChassisFanEntry
    MAX-ACCESS  not-accessible
    STATUS      obsolete
    DESCRIPTION
        "Contains information regarding a fan tray.

         This entry was made obsolete in release 15.0."
    INDEX       {
        tmnxChassisIndex,
        tmnxChassisFanIndex
    }
    ::= { tmnxChassisFanTable 1 }

TmnxChassisFanEntry              ::= SEQUENCE
{
    tmnxChassisFanIndex              Unsigned32,
    tmnxChassisFanOperStatus         TmnxDeviceState,
    tmnxChassisFanSpeed              INTEGER,
    tmnxChassisFanRevision           INTEGER,
    tmnxChassisFanSpeedPercent       Unsigned32
}

tmnxChassisFanIndex              OBJECT-TYPE
    SYNTAX      Unsigned32 (1..31)
    MAX-ACCESS  not-accessible
    STATUS      obsolete
    DESCRIPTION
        "The unique value which identifies a specific fan tray in the chassis.

         This object was made obsolete in release 15.0."
    ::= { tmnxChassisFanEntry 1 }

tmnxChassisFanOperStatus         OBJECT-TYPE
    SYNTAX      TmnxDeviceState
    MAX-ACCESS  read-only
    STATUS      obsolete
    DESCRIPTION
        "Current status of the Fan tray.

         This object was made obsolete in release 15.0."
    ::= { tmnxChassisFanEntry 2 }

tmnxChassisFanSpeed              OBJECT-TYPE
    SYNTAX      INTEGER {
        notApplicable (0),
        unknown       (1),
        halfSpeed     (2),
        fullSpeed     (3)
    }
    MAX-ACCESS  read-only
    STATUS      obsolete
    DESCRIPTION
        "The value of tmnxChassisFanSpeed indicates if the fans in this fan
         tray are running at 'halfSpeed' or 'fullSpeed'.

         This object was made obsolete in release 15.0."
    ::= { tmnxChassisFanEntry 3 }

tmnxChassisFanRevision           OBJECT-TYPE
    SYNTAX      INTEGER {
        unknown (0),
        fan1    (1),
        hfFan2  (2)
    }
    MAX-ACCESS  read-only
    STATUS      obsolete
    DESCRIPTION
        "The value of tmnxChassisFanRevision indicates the fan tray revision.
         fan1   - represents the original fan tray.
         hfFan2 - represents the high-flow fan tray; second revision.

         This object was made obsolete in release 15.0."
    ::= { tmnxChassisFanEntry 4 }

tmnxChassisFanSpeedPercent       OBJECT-TYPE
    SYNTAX      Unsigned32 (0..100)
    UNITS       "percent"
    MAX-ACCESS  read-only
    STATUS      obsolete
    DESCRIPTION
        "The value of tmnxChassisFanSpeedPercent indicates the speed of the fan
         as a percentage of maximum speed.

         This object was made obsolete in release 15.0."
    ::= { tmnxChassisFanEntry 6 }

tmnxChassisPowerSupplyTable      OBJECT-TYPE
    SYNTAX      SEQUENCE OF TmnxChassisPowerSupplyEntry
    MAX-ACCESS  not-accessible
    STATUS      obsolete
    DESCRIPTION
        "This table contains information about power supply trays, also known
         as PEMs (Power Entry Modules).

         This table was made obsolete in release 15.0."
    ::= { tmnxChassisObjs 5 }

tmnxChassisPowerSupplyEntry      OBJECT-TYPE
    SYNTAX      TmnxChassisPowerSupplyEntry
    MAX-ACCESS  not-accessible
    STATUS      obsolete
    DESCRIPTION
        "Contains information regarding a power supply tray.

         This entry was made obsolete in release 15.0."
    INDEX       {
        tmnxChassisIndex,
        tmnxChassisPowerSupplyId
    }
    ::= { tmnxChassisPowerSupplyTable 1 }

TmnxChassisPowerSupplyEntry      ::= SEQUENCE
{
    tmnxChassisPowerSupplyId         Unsigned32,
    tmnxChassisPowerSupplyACStatus   TmnxDeviceState,
    tmnxChassisPowerSupplyDCStatus   TmnxDeviceState,
    tmnxChassisPowerSupplyTempStatus TmnxDeviceState,
    tmnxChassisPowerSupplyTempThreshold Integer32,
    tmnxChassisPowerSupply1Status    TmnxDeviceState,
    tmnxChassisPowerSupply2Status    TmnxDeviceState,
    tmnxChassisPowerSupplyAssignedType TmnxPowerSupAssignType,
    tmnxChassisPowerSupplyInputStatus TmnxDeviceState,
    tmnxChassisPowerSupplyOutputStatus TmnxDeviceState,
    tmnxChassisPowerSupplyPemType    TmnxChassisPemType,
    tmnxChassisPowerSupplyPemACRect  BITS,
    tmnxChassisPowerSupplyInFeedDown BITS,
    tmnxChassisPowerSupplyFanDir     INTEGER
}

tmnxChassisPowerSupplyId         OBJECT-TYPE
    SYNTAX      Unsigned32 (1..31)
    MAX-ACCESS  not-accessible
    STATUS      obsolete
    DESCRIPTION
        "The unique identifier index for a power supply tray in the chassis.

         This object was made obsolete in release 15.0."
    ::= { tmnxChassisPowerSupplyEntry 1 }

tmnxChassisPowerSupplyACStatus   OBJECT-TYPE
    SYNTAX      TmnxDeviceState
    MAX-ACCESS  read-only
    STATUS      obsolete
    DESCRIPTION
        "If the value of tmnxChassisPowerSupplyACStatus is 'deviceStateOk',
         the input AC voltage is within range.  If the value is
         'deviceStateFailed', an AC voltage out of range condition has been
         detected. A value of 'deviceNotEquipped' indicates that the AC
         power supply is not present.

         This object was made obsolete in release 15.0."
    ::= { tmnxChassisPowerSupplyEntry 2 }

tmnxChassisPowerSupplyDCStatus   OBJECT-TYPE
    SYNTAX      TmnxDeviceState
    MAX-ACCESS  read-only
    STATUS      obsolete
    DESCRIPTION
        "If the value of tmnxChassisPowerSupplyDCStatus is 'deviceStateOk',
         the output DC voltage is within range.  If the value is
         'deviceStateFailed', a DC voltage out of range condition has been
         detected. A value of 'deviceNotEquipped' indicates that the power
         supply is not present or the equipped power supply does not support the
         reporting of this status.

         This object was made obsolete in release 15.0."
    ::= { tmnxChassisPowerSupplyEntry 3 }

tmnxChassisPowerSupplyTempStatus OBJECT-TYPE
    SYNTAX      TmnxDeviceState
    MAX-ACCESS  read-only
    STATUS      obsolete
    DESCRIPTION
        "If the value of tmnxChassisPowerSupplyTempStatus is 'deviceStateOk',
         the current temperature is within acceptable range. If the value is
         'deviceStateFailed', a temperature too high condition has been
         detected.

         This object was made obsolete in release 15.0."
    ::= { tmnxChassisPowerSupplyEntry 4 }

tmnxChassisPowerSupplyTempThreshold OBJECT-TYPE
    SYNTAX      Integer32
    UNITS       "degrees celsius"
    MAX-ACCESS  read-only
    STATUS      obsolete
    DESCRIPTION
        "The temperature threshold for this power supply tray in degrees
         celsius.  When the temperature raises above
         tmnxChassisPowerSupplyTempThreshold, a 'temperature too high'
         event will be generated.

         This object was made obsolete in release 15.0."
    ::= { tmnxChassisPowerSupplyEntry 5 }

tmnxChassisPowerSupply1Status    OBJECT-TYPE
    SYNTAX      TmnxDeviceState
    MAX-ACCESS  read-only
    STATUS      obsolete
    DESCRIPTION
        "The overall status of an equipped power supply. For AC multiple power
         supplies, this represents the overall status of the first power supply
         in the tray (or shelf). For any other type, this represents the
         overall status of the power supply. If tmnxChassisPowerSupply1Status
         is 'deviceStateOk', then all monitored statuses are 'deviceStateOk'. A
         value of 'deviceStateFailed' represents a condition where at least one
         monitored status is in a failed state.

         This object was made obsolete in release 15.0."
    ::= { tmnxChassisPowerSupplyEntry 6 }

tmnxChassisPowerSupply2Status    OBJECT-TYPE
    SYNTAX      TmnxDeviceState
    MAX-ACCESS  read-only
    STATUS      obsolete
    DESCRIPTION
        "The overall status of an equipped power supply. For AC multiple power
         supplies, this represents the overall status of the second power
         supply in the tray (or shelf). For any other type, this field is
         unused and set to 'deviceNotEquipped'. If
         tmnxChassisPowerSupply2Status is 'deviceStateOk', then all monitored
         statuses are 'deviceStateOk'. A value of 'deviceStateFailed'
         represents a condition where at least one monitored status is in a
         failed state.

         This object was made obsolete in release 15.0."
    ::= { tmnxChassisPowerSupplyEntry 7 }

tmnxChassisPowerSupplyAssignedType OBJECT-TYPE
    SYNTAX      TmnxPowerSupAssignType
    MAX-ACCESS  read-create
    STATUS      obsolete
    DESCRIPTION
        "tmnxChassisPowerSupplyAssignedType configures the type of power supply
         for a platform. Based on the value assigned to this object, various
         power supply monitoring signals will be interpreted. For example, if a
         platform is provisioned to use DC power supplies, then the signal that
         indicates an AC power supply is missing can be ignored. The
         configuration of this object away from 'default (4)' is required for
         proper generation of traps and LED management.

         This object was made obsolete in release 15.0."
    DEFVAL      { default }
    ::= { tmnxChassisPowerSupplyEntry 8 }

tmnxChassisPowerSupplyInputStatus OBJECT-TYPE
    SYNTAX      TmnxDeviceState
    MAX-ACCESS  read-only
    STATUS      obsolete
    DESCRIPTION
        "If the value of tmnxChassisPowerSupplyInputStatus is 'deviceStateOk',
         the input voltage of the power supply is within range.  If the value
         is 'deviceStateFailed', an input voltage out of range condition has
         been detected. A value of 'deviceNotEquipped' indicates that the power
         supply is not present.

         This object was made obsolete in release 15.0."
    ::= { tmnxChassisPowerSupplyEntry 9 }

tmnxChassisPowerSupplyOutputStatus OBJECT-TYPE
    SYNTAX      TmnxDeviceState
    MAX-ACCESS  read-only
    STATUS      obsolete
    DESCRIPTION
        "If the value of tmnxChassisPowerSupplyOutputStatus is 'deviceStateOk',
         the output voltage of the power supply is within range.  If the value
         is 'deviceStateFailed', an output voltage out of range condition has
         been detected. A value of 'deviceNotEquipped' indicates that the power
         supply is not present.

         This object was made obsolete in release 15.0."
    ::= { tmnxChassisPowerSupplyEntry 10 }

tmnxChassisPowerSupplyPemType    OBJECT-TYPE
    SYNTAX      TmnxChassisPemType
    MAX-ACCESS  read-only
    STATUS      obsolete
    DESCRIPTION
        "The tmnxChassisPowerSupplyPemType indicates the Power Entry Module
         (PEM) type installed in the PEM slot.

         This object was made obsolete in release 15.0."
    ::= { tmnxChassisPowerSupplyEntry 11 }

tmnxChassisPowerSupplyPemACRect  OBJECT-TYPE
    SYNTAX      BITS {
        acRect1 (0),
        acRect2 (1)
    }
    MAX-ACCESS  read-only
    STATUS      obsolete
    DESCRIPTION
        "The value of tmnxChassisPowerSupplyPemACRect indicates which Power
         Entry Module AC rectifiers installed in the PEM slot are in a failed
         state or are missing.

         acRect1 (0) : The 1st PEM AC rectifier has failed or is missing.
         acRect2 (1) : The 2nd PEM AC rectifier has failed or is missing.

         This object was made obsolete in release 15.0."
    ::= { tmnxChassisPowerSupplyEntry 12 }

tmnxChassisPowerSupplyInFeedDown OBJECT-TYPE
    SYNTAX      BITS {
        inputFeedA (0),
        inputFeedB (1)
    }
    MAX-ACCESS  read-only
    STATUS      obsolete
    DESCRIPTION
        "The value of tmnxChassisPowerSupplyInFeedDown indicates which input
         feeds are not supplying power.

         inputFeedA (0) : Input feed A is not supplying power.
         inputFeedB (1) : Input feed B is not supplying power.

         This object was made obsolete in release 15.0."
    ::= { tmnxChassisPowerSupplyEntry 13 }

tmnxChassisPowerSupplyFanDir     OBJECT-TYPE
    SYNTAX      INTEGER {
        unknown     (0),
        frontToBack (1),
        backToFront (2)
    }
    MAX-ACCESS  read-only
    STATUS      obsolete
    DESCRIPTION
        "The value of tmnxChassisPowerSupplyFanDir indicates if the fan
         direction is 'frontToBack' or 'backToFront'.

         This object was made obsolete in release 15.0."
    ::= { tmnxChassisPowerSupplyEntry 14 }

tmnxChassisTypeTable             OBJECT-TYPE
    SYNTAX      SEQUENCE OF TmnxChassisTypeEntry
    MAX-ACCESS  not-accessible
    STATUS      current
    DESCRIPTION
        "The chassis type table has an entry for each chassis model supported
         by the platform. Some example chassis types are: '7750 SR-12', '7950
         XRS-20'."
    ::= { tmnxChassisObjs 6 }

tmnxChassisTypeEntry             OBJECT-TYPE
    SYNTAX      TmnxChassisTypeEntry
    MAX-ACCESS  not-accessible
    STATUS      current
    DESCRIPTION
        "Each row entry represents an Nokia SROS series Chassis
         model.  Rows in this table are created by the agent at initialization
         and cannot be created or destroyed by SNMP Get or Set requests."
    INDEX       { tmnxChassisTypeIndex }
    ::= { tmnxChassisTypeTable 1 }

TmnxChassisTypeEntry             ::= SEQUENCE
{
    tmnxChassisTypeIndex             TmnxChassisType,
    tmnxChassisTypeName              TNamedItemOrEmpty,
    tmnxChassisTypeDescription       TItemDescription,
    tmnxChassisTypeStatus            TruthValue
}

tmnxChassisTypeIndex             OBJECT-TYPE
    SYNTAX      TmnxChassisType
    MAX-ACCESS  not-accessible
    STATUS      current
    DESCRIPTION
        "The unique index value which identifies this type of Nokia SROS series
         chassis model."
    ::= { tmnxChassisTypeEntry 1 }

tmnxChassisTypeName              OBJECT-TYPE
    SYNTAX      TNamedItemOrEmpty
    MAX-ACCESS  read-only
    STATUS      current
    DESCRIPTION
        "The administrative name that identifies this type of Nokia
         SROS series chassis model.  This name string may be used in
         CLI commands to specify a particular chassis model type."
    ::= { tmnxChassisTypeEntry 2 }

tmnxChassisTypeDescription       OBJECT-TYPE
    SYNTAX      TItemDescription
    MAX-ACCESS  read-only
    STATUS      current
    DESCRIPTION
        "A detailed description of this Nokia SROS series chassis model."
    ::= { tmnxChassisTypeEntry 3 }

tmnxChassisTypeStatus            OBJECT-TYPE
    SYNTAX      TruthValue
    MAX-ACCESS  read-only
    STATUS      current
    DESCRIPTION
        "When tmnxChassisTypeStatus has a value of 'true' it indicates that
         this chassis model is supported in this revision of the management
         software.  When it has a value of 'false' there is no support."
    ::= { tmnxChassisTypeEntry 4 }

tmnxHwLastChange                 OBJECT-TYPE
    SYNTAX      TimeStamp
    MAX-ACCESS  read-only
    STATUS      current
    DESCRIPTION
        "The value of sysUpTime when the tmnxHwTable was last changed."
    ::= { tmnxChassisObjs 7 }

tmnxHwTable                      OBJECT-TYPE
    SYNTAX      SEQUENCE OF TmnxHwEntry
    MAX-ACCESS  not-accessible
    STATUS      current
    DESCRIPTION
        "The tmnxHwTable has an entry for each managed hardware component
         in the Nokia SROS series system's chassis.  Examples of
         these hardware component types are IOM, Fabric, and CPM cards,
         and CCM, and MDA modules.  Similar information for physical ports
         is in the tmnxPortObjs."
    ::= { tmnxChassisObjs 8 }

tmnxHwEntry                      OBJECT-TYPE
    SYNTAX      TmnxHwEntry
    MAX-ACCESS  not-accessible
    STATUS      current
    DESCRIPTION
        "Each row entry represents an Nokia SROS series manufactured
         hardware component.  Entries cannot be created and deleted via
         SNMP SET operations.  When an entry is created in one of the
         card tables, IOM, CPM, Fabric or MDA, a tmnxHwEntry is created
         for the common hardware management information for that card
         in that chassis.  When the card  is removed from the chassis,
         its corresponding tmnxHwEntry is deleted.

         The tmnxHwIndex is bitmapped. The tmnxPhysChassisClass is used to
         indicate a sub-class of a TmnxHwClass type. A value of 0 instead of
         'routerChassis (3)' is used to represent router chassis:

         | 32       25 | 24                17 | 16        9 | 8         1 |
         +-------------+----------------------+-------------+-------------+
         | TmnxHwClass | TmnxPhysChassisClass |     Slot    |     number  |
         +-------------+----------------------+-------------+-------------+

         The Slot field is only used for components on cards in slots. It is
         zero for all others.

         The number field starts from 1 and indicates which component. E.g.
         Power supply 1 or 2."
    INDEX       {
        tmnxChassisIndex,
        tmnxHwIndex
    }
    ::= { tmnxHwTable 1 }

TmnxHwEntry                      ::= SEQUENCE
{
    tmnxHwIndex                      TmnxHwIndex,
    tmnxHwID                         RowPointer,
    tmnxHwMfgString                  SnmpAdminString,
    tmnxHwMfgBoardNumber             OCTET STRING,
    tmnxHwSerialNumber               SnmpAdminString,
    tmnxHwManufactureDate            SnmpAdminString,
    tmnxHwClass                      TmnxHwClass,
    tmnxHwName                       TNamedItemOrEmpty,
    tmnxHwAlias                      TNamedItemOrEmpty,
    tmnxHwAssetID                    SnmpAdminString,
    tmnxHwCLEI                       SnmpAdminString,
    tmnxHwIsFRU                      TruthValue,
    tmnxHwContainedIn                Integer32,
    tmnxHwParentRelPos               Integer32,
    tmnxHwAdminState                 INTEGER,
    tmnxHwOperState                  INTEGER,
    tmnxHwTempSensor                 TruthValue,
    tmnxHwTemperature                Integer32,
    tmnxHwTempThreshold              Integer32,
    tmnxHwBootCodeVersion            DisplayString,
    tmnxHwSoftwareCodeVersion        DisplayString,
    tmnxHwSwLastBoot                 DateAndTime,
    tmnxHwSwState                    INTEGER,
    tmnxHwAlarmState                 TmnxAlarmState,
    tmnxHwLastAlarmEvent             RowPointer,
    tmnxHwClearAlarms                TmnxActionType,
    tmnxHwSwImageSource              INTEGER,
    tmnxHwMfgDeviations              SnmpAdminString,
    tmnxHwBaseMacAddress             MacAddress,
    tmnxHwFailureReason              DisplayString,
    tmnxHwEquippedPlatform           INTEGER,
    tmnxHwMfgAssemblyNumber          SnmpAdminString,
    tmnxHwFirmwareCodeVersion        DisplayString,
    tmnxHwPowerZone                  Unsigned32,
    tmnxHwFirmwareRevisionStatus     INTEGER,
    tmnxHwOverTempStatus             INTEGER
}

tmnxHwIndex                      OBJECT-TYPE
    SYNTAX      TmnxHwIndex
    MAX-ACCESS  not-accessible
    STATUS      current
    DESCRIPTION
        "The value of tmnxHwIndex is a unique index that identifies common
         management information for Nokia SROS series manufactured hardware
         components within the specified chassis."
    ::= { tmnxHwEntry 1 }

tmnxHwID                         OBJECT-TYPE
    SYNTAX      RowPointer
    MAX-ACCESS  read-only
    STATUS      current
    DESCRIPTION
        "The value of tmnxHwID is an object identifier that points to the table
         and row entry with additional management information specific to this
         hardware component's class. If there is no additional information
         specific to such component then the the tmnxHwID is set to 0.0."
    ::= { tmnxHwEntry 2 }

tmnxHwMfgString                  OBJECT-TYPE
    SYNTAX      SnmpAdminString (SIZE (0..253))
    MAX-ACCESS  read-only
    STATUS      obsolete
    DESCRIPTION
        "The tmnxHwMfgString contains unspecified Nokia SROS series
         manufacturing information and includes the Nokia vendor information.

         This object was made obsolete in release 11.0."
    ::= { tmnxHwEntry 3 }

tmnxHwMfgBoardNumber             OBJECT-TYPE
    SYNTAX      OCTET STRING (SIZE (0..32))
    MAX-ACCESS  read-only
    STATUS      current
    DESCRIPTION
        "The tmnxHwMfgBoardNumber contains the part number information."
    ::= { tmnxHwEntry 4 }

tmnxHwSerialNumber               OBJECT-TYPE
    SYNTAX      SnmpAdminString (SIZE (0..32))
    MAX-ACCESS  read-only
    STATUS      current
    DESCRIPTION
        "The unique Nokia SROS series serial number of the hardware component."
    ::= { tmnxHwEntry 5 }

tmnxHwManufactureDate            OBJECT-TYPE
    SYNTAX      SnmpAdminString (SIZE (8))
    MAX-ACCESS  read-only
    STATUS      current
    DESCRIPTION
        "The manufacturing date of the hardware component in 'mmddyyyy' ascii
         format."
    ::= { tmnxHwEntry 6 }

tmnxHwClass                      OBJECT-TYPE
    SYNTAX      TmnxHwClass
    MAX-ACCESS  read-only
    STATUS      current
    DESCRIPTION
        "The value of tmnxHwClass  indicates the general hardware type of this
         component.  If no appropriate enumeration exists for this hardware
         identify this hardware component then the value 'unknown (2)' is
         used."
    ::= { tmnxHwEntry 7 }

tmnxHwName                       OBJECT-TYPE
    SYNTAX      TNamedItemOrEmpty
    MAX-ACCESS  read-only
    STATUS      current
    DESCRIPTION
        "The value of tmnxHwName is the name of the component as assigned by
         the system software itself and is suitable for use in CLI commands.
         This may be a text name such as 'console' or a port ID such as '2/2'.

         If there is no predefined name then a zero length string is returned.

         Note that the value of tmnxHwName for two component entries will
         be the same if the CLI does not distinguish between them, e.g.  the
         chassis slot-1 and the card in slot-1."
    ::= { tmnxHwEntry 8 }

tmnxHwAlias                      OBJECT-TYPE
    SYNTAX      TNamedItemOrEmpty
    MAX-ACCESS  read-write
    STATUS      current
    DESCRIPTION
        "The value of tmnxHwAlias is the administrative name assigned to this
         hardware component by the CLI user or network manager.  It is saved
         across re-initializations and reboots of the system.

         The object tmnxHwAlias is not supported on rows where the tmnxHwClass
         is set to 'flashDiskModule (12)'. Attempts to set the tmnxHwAlias
         object on rows where it is not supported will result in an
         inconsistentValue error."
    DEFVAL      { "" }
    ::= { tmnxHwEntry 9 }

tmnxHwAssetID                    OBJECT-TYPE
    SYNTAX      SnmpAdminString
    MAX-ACCESS  read-write
    STATUS      current
    DESCRIPTION
        "The value of tmnxHwAssetID is an administratively assigned asset
         tracking identifier for this hardware component.  It is saved across
         re-initializations and reboots of the system.  If no asset tracking
         information is associated with this hardware component, a zero-length
         string is returned to an SNMP get request.

         The object tmnxHwAssetID is not supported on rows where the
         tmnxHwClass is set to 'flashDiskModule (12)'. Attempts to set the
         tmnxHwAssetID object on rows where it is not supported will result in
         an inconsistentValue error.

         Some hardware components do not have asset tracking identifiers.
         Components for which tmnxHwIsFRU has a value of 'false' do not
         need their own unique asset tracking identifier.  In this case, the
         agent denies write access to this object and returns a zero-length
         string to an SNMP get request."
    DEFVAL      { "" }
    ::= { tmnxHwEntry 10 }

tmnxHwCLEI                       OBJECT-TYPE
    SYNTAX      SnmpAdminString (SIZE (10))
    MAX-ACCESS  read-only
    STATUS      current
    DESCRIPTION
        "The Common Language Equipment Identifier, CLEI, code is a unique
         10 character identifier, that is fixed by the manufacturer.  It
         consists of ten alphanumeric characters.  The first seven characters
         present a concise summary of an equipment entity's circuit or
         transport capabilities, e.g., functional, electrical, bandwidth, etc.
         CLEI codes for plug-in or portable equipment with the same first
         seven characters (CLEI-7) are considered bidirectionally
         interchangeable and group under a G level record.  Most licensees
         plug-in inventories and records are controlled at the group level.
         The eighth character denotes the reference source used for coding
         the item, and the last two characters denote manufacturing vintage
         or version, and other complementary information.

         A ten character CLEI code that is developed for a specific piece of
         equipment is unique within the CLEI code universe and is used in A
         level records; the code is not assigned to any other equipment piece.
         Equipment is coded to a first or major application. When the same
         equipment is usable in another application or system, it is not
         recorded nor are additional codes developed for that purpose."
    REFERENCE
        "Bellcore (Telcordia Technologies) GR-485."
    ::= { tmnxHwEntry 11 }

tmnxHwIsFRU                      OBJECT-TYPE
    SYNTAX      TruthValue
    MAX-ACCESS  read-only
    STATUS      current
    DESCRIPTION
        "The value of tmnxHwIsFRU indicates whether or not this hardware
         component is a Field Replaceable Unit (FRU) or not.  Those components
         that are permanently contained within a FRU have a value of 'false'."
    ::= { tmnxHwEntry 12 }

tmnxHwContainedIn                OBJECT-TYPE
    SYNTAX      Integer32 (0..2147483647)
    MAX-ACCESS  read-only
    STATUS      current
    DESCRIPTION
        "The value of tmnxHwContainedIn is the tmnxHwIndex value for the row
         entry of the hardware component that contains this component. A value
         of zero indicates that this component is not contained in any other
         component."
    ::= { tmnxHwEntry 13 }

tmnxHwParentRelPos               OBJECT-TYPE
    SYNTAX      Integer32 (-1..2147483647)
    MAX-ACCESS  read-only
    STATUS      current
    DESCRIPTION
        "The value of tmnxHwParentRelPos indicates the relative position of
         this hardware component among all its 'sibling' components.  A sibling
         component shares the same instance values for tmnxHwContainedIn and
         tmnxHwClass objects.

         If the associated value of tmnxHwContainedIn is zero, then the value
         -1 is returned."
    ::= { tmnxHwEntry 14 }

tmnxHwAdminState                 OBJECT-TYPE
    SYNTAX      INTEGER {
        noop          (1),
        inService     (2),
        outOfService  (3),
        diagnose      (4),
        operateSwitch (5)
    }
    MAX-ACCESS  read-write
    STATUS      current
    DESCRIPTION
        "The desired administrative status of this hardware component.  Write
         access will be denied for those components that do not have
         administrative status.  An attempt to set tmnxHwAdminState to
         'operateSwitch (5)' will fail if the hardware component is not part
         of a redundant pair.  Some examples of redundant hardware are the
         CPM cards and fabric cards."
    DEFVAL      { noop }
    ::= { tmnxHwEntry 15 }

tmnxHwOperState                  OBJECT-TYPE
    SYNTAX      INTEGER {
        unknown            (1),
        inService          (2),
        outOfService       (3),
        diagnosing         (4),
        failed             (5),
        booting            (6),
        empty              (7),
        provisioned        (8),
        unprovisioned      (9),
        upgrade            (10),
        downgrade          (11),
        inServiceUpgrade   (12),
        inServiceDowngrade (13),
        resetPending       (14),
        softReset          (15),
        preExtension       (16),
        downloading        (17),
        powerSave          (18)
    }
    MAX-ACCESS  read-only
    STATUS      current
    DESCRIPTION
        "The actual operational status of this hardware component.

         unknown (1)                Status cannot be determined

         inService (2)              Online - If tmnxHwClass has a value of
                                    'ioModule (8)' or 'cpmModule (9), the
                                    card is present, booted, configured,
                                    and running.

         outOfService (3)           Ready - The hardware component is OK
                                    but is down because tmnxHwAdminState has
                                    a value of 'outOfService (3)'.

         diagnosing (4)             Not implemented.

         failed (5)                 This hardware component has failed.  The
                                    value of tmnxHwFailureReason indicates
                                    the type of failure.  If tmnxHwClass has
                                    a value of 'ioModule(8)' or 'cpmModule(9)',
                                    there is a card in the slot but it has
                                    failed.

         booting (6)                A card is in the transitional startup state.

         empty (7)                  There is no card in the slot and it has
                                    not been pre-configured.

         provisioned (8)            There is no card in the slot but it has
                                    been pre-configured.

         unprovisioned (9)          There is a card in the slot but it is not
                                    configured.

         upgrade (10)               Card software version is compatible with
                                    and newer than that running on the current
                                    active CPM.

         downgrade (11)             Card software version is compatible with
                                    and older than that running on the current
                                    active CPM.

         inServiceUpgrade (12)      Card is inService and the card software
                                    version is compatible with and newer than
                                    that running on the current active CPM.
                                    This state applies only to a standby CPM
                                    card. This enumeration is no longer
                                    supported as of release 5.0.

         inServiceDowngrade (13)    Card is inService and the card software
                                    is compatible with and older than that
                                    running on the current active CPM.  This
                                    state applies only to a standby CPM card.
                                    This enumeration is no longer supported
                                    as of release 5.0.

         resetPending (14)          Card is awaiting reset following an
                                    upgrade or downgrade activity switch.
                                    The card software version is upgrade
                                    or downgrade compatible but will be reset
                                    in order to update it to match the active
                                    CPM software.  The value of
                                    tmnxChassisUpdateWaitTime indicates the
                                    how long the system will wait following
                                    an upgrade or downgrade activity switch
                                    before it resets IOM cards.  This state
                                    applies only to IOM cards. This
                                    enumeration is no longer supported as of
                                    release 5.0.

         softReset (15)             Card is performing a soft reset. The
                                    data path is active, but control path
                                    transitional changes are suspended until
                                    the card leaves this state.

         preExtension (16)          State assigned to an unprovisioned hardware
                                    component associated with, or contained in,
                                    an (potentially non-existent) extension
                                    chassis in a 7950 XRS system that is
                                    operating in XRS-20 mode (i.e.
                                    tmnxChassisOperTopology is 'standalone(1)').
                                    The extension chassis and/or hardware
                                    component may or may not be physically
                                    present and connected to the master
                                    chassis. The system does not monitor
                                    extension chassis equipment when
                                    tmnxChassisOperTopology is 'standalone(1)'.
                                    In this case, for unprovisioned extension
                                    chassis equipment, a value of
                                    'preExtension(16)' is assigned.

          downloading (17)          Card has booted and its configuration is
                                    being downloaded.

          powerSave (18)            The switch fabric on the chassis is operating
                                    at a reduced capacity in order to save power.
                                    This is user initiated by enabling low power
                                    switch fabric mode."
    ::= { tmnxHwEntry 16 }

tmnxHwTempSensor                 OBJECT-TYPE
    SYNTAX      TruthValue
    MAX-ACCESS  read-only
    STATUS      current
    DESCRIPTION
        "The value of tmnxHwTempSensor indicates whether or not this hardware
         component contains a temperature sensor."
    ::= { tmnxHwEntry 17 }

tmnxHwTemperature                OBJECT-TYPE
    SYNTAX      Integer32
    UNITS       "degrees celsius"
    MAX-ACCESS  read-only
    STATUS      current
    DESCRIPTION
        "The current temperature reading in degrees celsius from this hardware
         component's temperature sensor.  If this component does not contain
         a temperature sensor, then the value -128 is returned."
    ::= { tmnxHwEntry 18 }

tmnxHwTempThreshold              OBJECT-TYPE
    SYNTAX      Integer32
    UNITS       "degrees celsius"
    MAX-ACCESS  read-only
    STATUS      current
    DESCRIPTION
        "The temperature threshold for this hardware component in degrees
         celsius.  When the value of tmnxHwTemperature raises above
         tmnxHwTempThreshold, a 'temperature too high' event will
         be generated."
    ::= { tmnxHwEntry 19 }

tmnxHwBootCodeVersion            OBJECT-TYPE
    SYNTAX      DisplayString
    MAX-ACCESS  read-only
    STATUS      current
    DESCRIPTION
        "The version number of boot eprom on the card in this slot.

         If no specific software program is associated with this hardware
         component then this object will contain a zero length string."
    ::= { tmnxHwEntry 20 }

tmnxHwSoftwareCodeVersion        OBJECT-TYPE
    SYNTAX      DisplayString
    MAX-ACCESS  read-only
    STATUS      current
    DESCRIPTION
        "The software product release version number for the software image
         currently running on this IOM or CPM card.

         If no specific software program is associated with this hardware
         component then this object will contain a zero length string."
    ::= { tmnxHwEntry 21 }

tmnxHwSwLastBoot                 OBJECT-TYPE
    SYNTAX      DateAndTime
    MAX-ACCESS  read-only
    STATUS      current
    DESCRIPTION
        "The date and time the software running on this IOM or CPM card was
         last rebooted.

         If this row entry represents a standby CPM card, the date and time
         indicated is when the standby completed its initial synchronization
         process and became ready to take over in case the active card fails or
         a manual switchover command is issued."
    ::= { tmnxHwEntry 22 }

tmnxHwSwState                    OBJECT-TYPE
    SYNTAX      INTEGER {
        unknown       (0),
        hwFailure     (1),
        swFailure     (2),
        hwInitting    (3),
        swDownloading (4),
        swInitting    (5),
        swInitted     (6),
        swRunning     (7)
    }
    MAX-ACCESS  read-only
    STATUS      obsolete
    DESCRIPTION
        "The state of the software running on this IOM or CPM card.

         The tmnxHwSwState object is obsolete.  The Nokia 7x50 platform
         cannot distinguish software status separate from the hardware
         status.  Instead of using this object, additional operational
         states have been added to tmnxHwOperState.

         If no specific software program is associated with this hardware
         component then this object will contain a zero."
    ::= { tmnxHwEntry 23 }

tmnxHwAlarmState                 OBJECT-TYPE
    SYNTAX      TmnxAlarmState
    MAX-ACCESS  read-only
    STATUS      current
    DESCRIPTION
        "The value of tmnxHwAlarmState indicates the current alarm state for
         this hardware component."
    ::= { tmnxHwEntry 24 }

tmnxHwLastAlarmEvent             OBJECT-TYPE
    SYNTAX      RowPointer
    MAX-ACCESS  read-only
    STATUS      obsolete
    DESCRIPTION
        "The value of tmnxHwLastAlarmEvent indicates the object name
         and instance value that points to the row entry in the ALARM-MIB
         containing the most recent alarm associated with this hardware
         component.  If tmnxHwAlarmState has a value of 'alarmCleared(2)', the
         most recent alarm event will be in the cleared alarm table.  If it has
         a value of 'alarmActive(1)', the most recent alarm event will be in
         the active alarm table.  If the value of tmnxHwLastAlarmEvent is
         '0.0', either no hardware component alarm events have occurred since
         the system was last booted, or the last hardware component alarm event
         has aged out and its entry is no longer available in the ALARM-MIB
         tables.

         This object was made obsolete in release 21.2."
    ::= { tmnxHwEntry 25 }

tmnxHwClearAlarms                OBJECT-TYPE
    SYNTAX      TmnxActionType
    MAX-ACCESS  read-write
    STATUS      obsolete
    DESCRIPTION
        "Setting this action variable causes all the active alarms associated
         with this hardware component to be moved from the ALARM-MIB
         active alarm table to the cleared alarm table.  This action button
         is primarily meant for use as a code development aid.  This object may
         be removed from the TIMETRA-CHASSIS-MIB before product release.

         This object was made obsolete in release 21.2."
    DEFVAL      { notApplicable }
    ::= { tmnxHwEntry 26 }

tmnxHwSwImageSource              OBJECT-TYPE
    SYNTAX      INTEGER {
        unknown   (0),
        primary   (1),
        secondary (2),
        tertiary  (3)
    }
    MAX-ACCESS  read-only
    STATUS      current
    DESCRIPTION
        "The value of tmnxHwSwImageSource indicates the location in the Boot
         Options File (BOF) where the software image file was found when the
         system last rebooted."
    ::= { tmnxHwEntry 27 }

tmnxHwMfgDeviations              OBJECT-TYPE
    SYNTAX      SnmpAdminString
    MAX-ACCESS  read-only
    STATUS      current
    DESCRIPTION
        "tmnxHwMfgDeviations contains a record of changes done by the
         manufacturing to the hardware or software and which is outside the
         normal revision control process."
    ::= { tmnxHwEntry 28 }

tmnxHwBaseMacAddress             OBJECT-TYPE
    SYNTAX      MacAddress
    MAX-ACCESS  read-only
    STATUS      current
    DESCRIPTION
        "tmnxHwBaseMacAddress contains the base MAC address of the hardware
         component. It is applicable only if tmnxHwClass is of type 'chassis',
         'ioModule', 'cpmModule' or 'mdaModule'."
    ::= { tmnxHwEntry 29 }

tmnxHwFailureReason              OBJECT-TYPE
    SYNTAX      DisplayString
    MAX-ACCESS  read-only
    STATUS      current
    DESCRIPTION
        "tmnxHwFailureReason indicates the reason why a hardware component
         'failed' as indicated in tmnxHwOperState."
    ::= { tmnxHwEntry 30 }

tmnxHwEquippedPlatform           OBJECT-TYPE
    SYNTAX      INTEGER {
        pfUnknown (0),
        pf7750    (1),
        pf7450    (2),
        pf7710    (3),
        pf7950    (4),
        pf7705    (5),
        pf7250    (6),
        pf7750dms (7)
    }
    MAX-ACCESS  read-only
    STATUS      current
    DESCRIPTION
        "The value of tmnxHwEquippedPlatform indicates the platform type
         of the installed hardware component, as read from the component's
         EEPROM.  For example, 'pf7750' is returned for an installed 7750
         iom3-xp.  pfUnknown is returned if the component's EEPROM is
         unreadable, or in the case of an empty slot."
    ::= { tmnxHwEntry 31 }

tmnxHwMfgAssemblyNumber          OBJECT-TYPE
    SYNTAX      SnmpAdminString (SIZE (0..32))
    MAX-ACCESS  read-only
    STATUS      current
    DESCRIPTION
        "The value of tmnxHwMfgAssemblyNumber may contain an assembly number
         which indicates manufacturing differences for a given part number."
    ::= { tmnxHwEntry 32 }

tmnxHwFirmwareCodeVersion        OBJECT-TYPE
    SYNTAX      DisplayString
    MAX-ACCESS  read-only
    STATUS      current
    DESCRIPTION
        "The software product release version number associated with the
         firmware version currently programmed on this card.

         If no specific software release is associated with this hardware
         component then this object will contain a zero length string."
    ::= { tmnxHwEntry 33 }

tmnxHwPowerZone                  OBJECT-TYPE
    SYNTAX      Unsigned32 (0..32)
    MAX-ACCESS  read-only
    STATUS      current
    DESCRIPTION
        "The value of tmnxHwPowerZone indicates the managed power-zone on an
         SROS series system that this device resides. Devices on differing
         power-zones are managed separately. That is, if power is restricted on
         one power-zone, higher priority devices may be forcefully powered off,
         while a power-zone without a power restriction may have low-priority
         devices boot up. This object maps the corresponding device with a row
         in the tmnxChassisPowerMgmtTable.

         A value of zero (0) indicates that this device does not use system
         power resources and thus does not reside in a power-zone."
    ::= { tmnxHwEntry 34 }

tmnxHwFirmwareRevisionStatus     OBJECT-TYPE
    SYNTAX      INTEGER {
        notApplicable        (0),
        acceptable           (1),
        notAcceptable        (2),
        upgradePending       (3),
        upgrading            (4),
        upgradeNextHardReset (5),
        powerCycleRequired   (6)
    }
    MAX-ACCESS  read-only
    STATUS      current
    DESCRIPTION
        "The value of tmnxHwFirmwareRevisionStatus indicates the firmware/FPGA
         revision status for the device. A device that does not support a
         firmware/FPGA revision status will always return 'notApplicable (0)'.

         The possible values of tmnxHwFirmwareRevisionStatus are:
             notApplicable (0)        - The device does not support this object
                                        or the device does support this object
                                        but the current firmware revision is
                                        not yet known (e.g. the device is
                                        currently initializing).

             acceptable (1)           - The device has a firmware revision that
                                        is acceptable with the current system
                                        configuration.

             notAcceptable (2)        - The device has a firmware revision that
                                        is not acceptable with the current
                                        system configuration.

             upgradePending (3)       - The device has a firmware revision that
                                        is not acceptable with the current
                                        system configuration; an upgrade will
                                        be issued on the device's firmware to
                                        bring it to an acceptable state.

             upgrading (4)            - The device's firmware is currently
                                        being upgraded to the latest revision
                                        acceptable with the current system
                                        configuration.

             upgradeNextHardReset (5) - The device's firmware is acceptable
                                        but a new revision is available and
                                        the card will be upgraded to this new
                                        revision on the next hard reset.

             powerCycleRequired (6)   - The device's firmware has been
                                        upgraded but the new firmware will not
                                        take effect until the device is
                                        power-cycled."
    ::= { tmnxHwEntry 35 }

tmnxHwOverTempStatus             OBJECT-TYPE
    SYNTAX      INTEGER {
        notApplicable (0),
        ok            (1),
        overTemp      (2)
    }
    MAX-ACCESS  read-only
    STATUS      current
    DESCRIPTION
        "The value of tmnxHwOverTempStatus indicates whether the temperature of
         the hardware element, represented by 'tmnxHwTemperature', has exceeded
         its threshold.

         The possible values of tmnxHwOverTempStatus are:
           notApplicable (0)    - The device does not support or does not include
                                  a temperature sensor.

           ok (1)               - The device has a temperature sensor, which reports
                                  that the current temperature of the device is less
                                  than its threshold temperature.

           overTemp (2)         - The device has a temperature sensor, which reports
                                  that the current temperature of the device has
                                  exceeded its threshold temperature."
    ::= { tmnxHwEntry 36 }

tmnxHwContainsTable              OBJECT-TYPE
    SYNTAX      SEQUENCE OF TmnxHwContainsEntry
    MAX-ACCESS  not-accessible
    STATUS      current
    DESCRIPTION
        "The tmnxHwContainsTable shows the container/containee relationship
         between entries in the tmnxHwTable.  The hardware component
         containment tree can be constructed from information in the
         tmnxHwTable, but this table provides the information in a more
         convenient format for the manager system to use."
    ::= { tmnxChassisObjs 9 }

tmnxHwContainsEntry              OBJECT-TYPE
    SYNTAX      TmnxHwContainsEntry
    MAX-ACCESS  not-accessible
    STATUS      current
    DESCRIPTION
        "Each row entry represents a single container/containee relationship.
         Entries cannot be created and deleted via SNMP SET operations."
    INDEX       {
        tmnxHwIndex,
        tmnxHwContainedIndex
    }
    ::= { tmnxHwContainsTable 1 }

TmnxHwContainsEntry              ::= SEQUENCE
{ tmnxHwContainedIndex             TmnxHwIndex }

tmnxHwContainedIndex             OBJECT-TYPE
    SYNTAX      TmnxHwIndex
    MAX-ACCESS  read-only
    STATUS      current
    DESCRIPTION
        "The value of tmnxHwContainedIndex indicates the tmnxHwIndex for the
         contained hardware component."
    ::= { tmnxHwContainsEntry 1 }

tmnxCcmTable                     OBJECT-TYPE
    SYNTAX      SEQUENCE OF TmnxCcmEntry
    MAX-ACCESS  not-accessible
    STATUS      current
    DESCRIPTION
        "This table contains information about CCM."
    ::= { tmnxChassisObjs 10 }

tmnxCcmEntry                     OBJECT-TYPE
    SYNTAX      TmnxCcmEntry
    MAX-ACCESS  not-accessible
    STATUS      current
    DESCRIPTION
        "Contains information regarding a CCM."
    INDEX       {
        tmnxChassisIndex,
        tmnxCcmIndex
    }
    ::= { tmnxCcmTable 1 }

TmnxCcmEntry                     ::= SEQUENCE
{
    tmnxCcmIndex                     Unsigned32,
    tmnxCcmOperStatus                TmnxDeviceState,
    tmnxCcmHwIndex                   TmnxHwIndex,
    tmnxCcmEquippedType              TmnxCcmType
}

tmnxCcmIndex                     OBJECT-TYPE
    SYNTAX      Unsigned32 (1..8)
    MAX-ACCESS  not-accessible
    STATUS      current
    DESCRIPTION
        "The unique value which identifies a specific CCM instance in the
         chassis."
    ::= { tmnxCcmEntry 1 }

tmnxCcmOperStatus                OBJECT-TYPE
    SYNTAX      TmnxDeviceState
    MAX-ACCESS  read-only
    STATUS      current
    DESCRIPTION
        "Current status of the CCM."
    ::= { tmnxCcmEntry 2 }

tmnxCcmHwIndex                   OBJECT-TYPE
    SYNTAX      TmnxHwIndex
    MAX-ACCESS  read-only
    STATUS      current
    DESCRIPTION
        "The value of tmnxCcmHwIndex is the index into the tmnxHwTable for the
         row entry that represents the hardware component information for this
         CCM."
    ::= { tmnxCcmEntry 3 }

tmnxCcmEquippedType              OBJECT-TYPE
    SYNTAX      TmnxCcmType
    MAX-ACCESS  read-only
    STATUS      current
    DESCRIPTION
        "A bit-mask that identifies the CCM type that is physically
         inserted into this chassis.  There will not be more than one
         bit set at a time in tmnxCcmEquippedType."
    ::= { tmnxCcmEntry 4 }

tmnxCcmTypeTable                 OBJECT-TYPE
    SYNTAX      SEQUENCE OF TmnxCcmTypeEntry
    MAX-ACCESS  not-accessible
    STATUS      current
    DESCRIPTION
        "The card type table has an entry for each Nokia 7710 series Chassis
         Control Module (CCM) model."
    ::= { tmnxChassisObjs 11 }

tmnxCcmTypeEntry                 OBJECT-TYPE
    SYNTAX      TmnxCcmTypeEntry
    MAX-ACCESS  not-accessible
    STATUS      current
    DESCRIPTION
        "Each row entry represents an Nokia 7710 series CCM model. Rows in this
         table are created by the agent at initialization and cannot be created
         or destroyed by SNMP Get or Set requests."
    INDEX       { tmnxCcmTypeIndex }
    ::= { tmnxCcmTypeTable 1 }

TmnxCcmTypeEntry                 ::= SEQUENCE
{
    tmnxCcmTypeIndex                 TmnxCcmType,
    tmnxCcmTypeName                  TNamedItemOrEmpty,
    tmnxCcmTypeDescription           TItemDescription,
    tmnxCcmTypeStatus                TruthValue
}

tmnxCcmTypeIndex                 OBJECT-TYPE
    SYNTAX      TmnxCcmType
    MAX-ACCESS  not-accessible
    STATUS      current
    DESCRIPTION
        "The unique index value which identifies this type of Nokia 7710 series
         CCM model."
    ::= { tmnxCcmTypeEntry 1 }

tmnxCcmTypeName                  OBJECT-TYPE
    SYNTAX      TNamedItemOrEmpty
    MAX-ACCESS  read-only
    STATUS      current
    DESCRIPTION
        "The administrative name that identifies this type of Nokia
         7710 series CCM model.  This name string may be used in CLI
         commands to specify a particular card model type."
    ::= { tmnxCcmTypeEntry 2 }

tmnxCcmTypeDescription           OBJECT-TYPE
    SYNTAX      TItemDescription
    MAX-ACCESS  read-only
    STATUS      current
    DESCRIPTION
        "A detailed description of this Nokia 7710 series CCM model."
    ::= { tmnxCcmTypeEntry 3 }

tmnxCcmTypeStatus                OBJECT-TYPE
    SYNTAX      TruthValue
    MAX-ACCESS  read-only
    STATUS      current
    DESCRIPTION
        "When tmnxCcmTypeStatus has a value of 'true' it
         indicates that this CCM is supported in this revision of the
         management software.  When it has a value of 'false' there is no
         support."
    ::= { tmnxCcmTypeEntry 4 }

tmnxFanTrayComponentTable        OBJECT-TYPE
    SYNTAX      SEQUENCE OF TmnxFanTrayComponentEntry
    MAX-ACCESS  not-accessible
    STATUS      obsolete
    DESCRIPTION
        "The Fan Tray Component table has an entry for every subcomponent of a
         Fan Tray that has monitored states. Not all fan trays have monitored
         subcomponents, in this case, this table will be empty for the given
         fan tray.

         This table was made obsolete in release 16.0."
    ::= { tmnxChassisObjs 12 }

tmnxFanTrayComponentEntry        OBJECT-TYPE
    SYNTAX      TmnxFanTrayComponentEntry
    MAX-ACCESS  not-accessible
    STATUS      current
    DESCRIPTION
        "Each row entry represents a fan tray component. Rows in this table are
         created by the agent at initialization and cannot be created or
         destroyed by SNMP Get or Set requests.

         This entry was made obsolete in release 16.0."
    INDEX       {
        tmnxChassisIndex,
        tmnxChassisFanIndex,
        tmnxFanTrayCompIndex
    }
    ::= { tmnxFanTrayComponentTable 1 }

TmnxFanTrayComponentEntry        ::= SEQUENCE
{
    tmnxFanTrayCompIndex             Unsigned32,
    tmnxFanTrayCompSpeed             Gauge32
}

tmnxFanTrayCompIndex             OBJECT-TYPE
    SYNTAX      Unsigned32
    MAX-ACCESS  not-accessible
    STATUS      obsolete
    DESCRIPTION
        "The tmnxFanTrayCompIndex specifies an individual fan tray component.

         This object was made obsolete in release 16.0."
    ::= { tmnxFanTrayComponentEntry 1 }

tmnxFanTrayCompSpeed             OBJECT-TYPE
    SYNTAX      Gauge32 (0..100)
    UNITS       "percent"
    MAX-ACCESS  read-only
    STATUS      obsolete
    DESCRIPTION
        "The tmnxFanTrayCompSpeed indicates the current speed of the fan tray
         component.

         This object was made obsolete in release 16.0."
    ::= { tmnxFanTrayComponentEntry 2 }

tmnxHwResourceTable              OBJECT-TYPE
    SYNTAX      SEQUENCE OF TmnxHwResourceEntry
    MAX-ACCESS  not-accessible
    STATUS      current
    DESCRIPTION
        "The tmnxHwResourceTable has an entry for each managed hardware
         component in the Nokia SROS series system's chassis that supports
         resource monitoring. Hardware components that do not support resource
         monitoring will not show up in this table.

         Rows in this table are created by the agent at initialization and
         cannot be created or destroyed by SNMP Get or Set requests."
    ::= { tmnxChassisObjs 13 }

tmnxHwResourceEntry              OBJECT-TYPE
    SYNTAX      TmnxHwResourceEntry
    MAX-ACCESS  not-accessible
    STATUS      current
    DESCRIPTION
        "Each tmnxHwResourceEntry row consists of the current resource levels
         for a particular managed hardware component."
    INDEX       {
        tmnxChassisIndex,
        tmnxHwIndex
    }
    ::= { tmnxHwResourceTable 1 }

TmnxHwResourceEntry              ::= SEQUENCE
{
    tmnxHwResourceCurrentVoltage     Integer32,
    tmnxHwResourcePeakVoltage        Integer32,
    tmnxHwResourcePeakVoltageTime    TimeStamp,
    tmnxHwResourceMinVoltage         Integer32,
    tmnxHwResourceMinVoltageTime     TimeStamp,
    tmnxHwResourceCurrentWattage     Integer32,
    tmnxHwResourcePeakWattage        Integer32,
    tmnxHwResourcePeakWattageTime    TimeStamp,
    tmnxHwResourceMinWattage         Integer32,
    tmnxHwResourceMinWattageTime     TimeStamp,
    tmnxHwResourceCurrentAmperage    Integer32,
    tmnxHwResourcePeakAmperage       Integer32,
    tmnxHwResourcePeakAmperageTime   TimeStamp,
    tmnxHwResourceMinAmperage        Integer32,
    tmnxHwResourceMinAmperageTime    TimeStamp,
    tmnxHwResourceMaxRequiredWattage Integer32
}

tmnxHwResourceCurrentVoltage     OBJECT-TYPE
    SYNTAX      Integer32
    MAX-ACCESS  read-only
    STATUS      current
    DESCRIPTION
        "The value of tmnxHwResourceCurrentVoltage indicates the current
         voltage use of the managed hardware component in milli-Volts (mV)."
    ::= { tmnxHwResourceEntry 1 }

tmnxHwResourcePeakVoltage        OBJECT-TYPE
    SYNTAX      Integer32
    MAX-ACCESS  read-only
    STATUS      current
    DESCRIPTION
        "The value of tmnxHwResourcePeakVoltage indicates the peak voltage use
         of the managed hardware component in milli-Volts (mV) last recorded at
         the time indicated by tmnxHwResourcePeakVoltageTime."
    ::= { tmnxHwResourceEntry 2 }

tmnxHwResourcePeakVoltageTime    OBJECT-TYPE
    SYNTAX      TimeStamp
    MAX-ACCESS  read-only
    STATUS      current
    DESCRIPTION
        "The value of tmnxHwResourcePeakVoltageTime indicates the time, since
         system initialization, that tmnxHwResourcePeakVoltage was last
         updated."
    ::= { tmnxHwResourceEntry 3 }

tmnxHwResourceMinVoltage         OBJECT-TYPE
    SYNTAX      Integer32
    MAX-ACCESS  read-only
    STATUS      current
    DESCRIPTION
        "The value of tmnxHwResourceMinVoltage indicates the lowest voltage use
         of the managed hardware component in milli-Volts (mV) last recorded at
         the time indicated by tmnxHwResourceMinVoltageTime."
    ::= { tmnxHwResourceEntry 4 }

tmnxHwResourceMinVoltageTime     OBJECT-TYPE
    SYNTAX      TimeStamp
    MAX-ACCESS  read-only
    STATUS      current
    DESCRIPTION
        "The value of tmnxHwResourceMinVoltageTime indicates the time, since
         system initialization, that tmnxHwResourceMinVoltage was last updated."
    ::= { tmnxHwResourceEntry 5 }

tmnxHwResourceCurrentWattage     OBJECT-TYPE
    SYNTAX      Integer32
    MAX-ACCESS  read-only
    STATUS      current
    DESCRIPTION
        "The value of tmnxHwResourceCurrentWattage indicates the current power
         use of the managed hardware component in milli-Watts (mW)."
    ::= { tmnxHwResourceEntry 6 }

tmnxHwResourcePeakWattage        OBJECT-TYPE
    SYNTAX      Integer32
    MAX-ACCESS  read-only
    STATUS      current
    DESCRIPTION
        "The value of tmnxHwResourcePeakWattage indicates the peak power use of
         the managed hardware component in milli-Watts (mW) last recorded at
         the time indicated by tmnxHwResourcePeakWattageTime."
    ::= { tmnxHwResourceEntry 7 }

tmnxHwResourcePeakWattageTime    OBJECT-TYPE
    SYNTAX      TimeStamp
    MAX-ACCESS  read-only
    STATUS      current
    DESCRIPTION
        "The value of tmnxHwResourcePeakWattageTime indicates the time, since
         system initialization, that tmnxHwResourcePeakWattage was last
         updated."
    ::= { tmnxHwResourceEntry 8 }

tmnxHwResourceMinWattage         OBJECT-TYPE
    SYNTAX      Integer32
    MAX-ACCESS  read-only
    STATUS      current
    DESCRIPTION
        "The value of tmnxHwResourceMinWattage indicates the lowest power use
         of the managed hardware component in milli-Watts (mW) last recorded at
         the time indicated by tmnxHwResourceMinWattageTime."
    ::= { tmnxHwResourceEntry 9 }

tmnxHwResourceMinWattageTime     OBJECT-TYPE
    SYNTAX      TimeStamp
    MAX-ACCESS  read-only
    STATUS      current
    DESCRIPTION
        "The value of tmnxHwResourceMinWattageTime indicates the time, since
         system initialization, that tmnxHwResourceMinWattage was last updated."
    ::= { tmnxHwResourceEntry 10 }

tmnxHwResourceCurrentAmperage    OBJECT-TYPE
    SYNTAX      Integer32
    MAX-ACCESS  read-only
    STATUS      current
    DESCRIPTION
        "The value of tmnxHwResourceCurrentAmperage indicates the current drawn
         by the managed hardware component in milli-Amperes (mA)."
    ::= { tmnxHwResourceEntry 11 }

tmnxHwResourcePeakAmperage       OBJECT-TYPE
    SYNTAX      Integer32
    MAX-ACCESS  read-only
    STATUS      current
    DESCRIPTION
        "The value of tmnxHwResourcePeakAmperage indicates the peak current
         drawn by the managed hardware component in milli-Amperes (mA) last
         recorded at the time indicated by tmnxHwResourcePeakAmperageTime."
    ::= { tmnxHwResourceEntry 12 }

tmnxHwResourcePeakAmperageTime   OBJECT-TYPE
    SYNTAX      TimeStamp
    MAX-ACCESS  read-only
    STATUS      current
    DESCRIPTION
        "The value of tmnxHwResourcePeakAmperageTime indicates the time, since
         system initialization, that tmnxHwResourcePeakAmperage was last
         updated."
    ::= { tmnxHwResourceEntry 13 }

tmnxHwResourceMinAmperage        OBJECT-TYPE
    SYNTAX      Integer32
    MAX-ACCESS  read-only
    STATUS      current
    DESCRIPTION
        "The value of tmnxHwResourceMinAmperage indicates the lowest current
         drawn by the managed hardware component in milli-Amperes (mA) last
         recorded at the time indicated by tmnxHwResourceMinAmperageTime."
    ::= { tmnxHwResourceEntry 14 }

tmnxHwResourceMinAmperageTime    OBJECT-TYPE
    SYNTAX      TimeStamp
    MAX-ACCESS  read-only
    STATUS      current
    DESCRIPTION
        "The value of tmnxHwResourceMinAmperageTime indicates the time, since
         system initialization, that tmnxHwResourceMinAmperage was last
         updated."
    ::= { tmnxHwResourceEntry 15 }

tmnxHwResourceMaxRequiredWattage OBJECT-TYPE
    SYNTAX      Integer32
    UNITS       "Wattage"
    MAX-ACCESS  read-only
    STATUS      current
    DESCRIPTION
        "The value of tmnxHwResourceMaxRequiredWattage indicates the maximum
         possible power consumption for this device.  This value is used to
         determine the amount of system power to reserve in order to safely
         power up the device."
    ::= { tmnxHwResourceEntry 16 }

tmnxPEQTypeTable                 OBJECT-TYPE
    SYNTAX      SEQUENCE OF TmnxPEQTypeEntry
    MAX-ACCESS  not-accessible
    STATUS      current
    DESCRIPTION
        "The tmnxPEQTypeTable has an entry for each Power Equalizer (PEQ) type
         supported by the system. Some example PEQ types are: 'apeq-dc-2000',
         'apeq-ac-3000'."
    ::= { tmnxChassisObjs 14 }

tmnxPEQTypeEntry                 OBJECT-TYPE
    SYNTAX      TmnxPEQTypeEntry
    MAX-ACCESS  not-accessible
    STATUS      current
    DESCRIPTION
        "Each row entry represents an Nokia SROS series Power Equalizer
         type.  Rows in this table are created by the agent at initialization
         and cannot be created or destroyed by SNMP Get or Set requests."
    INDEX       { tmnxPEQTypeIndex }
    ::= { tmnxPEQTypeTable 1 }

TmnxPEQTypeEntry                 ::= SEQUENCE
{
    tmnxPEQTypeIndex                 TmnxPEQType,
    tmnxPEQTypeName                  TNamedItemOrEmpty,
    tmnxPEQTypeDescription           TItemDescription,
    tmnxPEQTypeNumInputFeed          Unsigned32
}

tmnxPEQTypeIndex                 OBJECT-TYPE
    SYNTAX      TmnxPEQType
    MAX-ACCESS  not-accessible
    STATUS      current
    DESCRIPTION
        "The value of tmnxPEQTypeIndex specifies the unique index which
         identifies the type of Nokia SROS series Power Equalizer (PEQ)."
    ::= { tmnxPEQTypeEntry 1 }

tmnxPEQTypeName                  OBJECT-TYPE
    SYNTAX      TNamedItemOrEmpty
    MAX-ACCESS  read-only
    STATUS      current
    DESCRIPTION
        "The value of tmnxPEQTypeName indicates the administrative name that
         identifies the type of Nokia SROS series PEQ. This name string is used
         in CLI commands to specify a particular PEQ type."
    ::= { tmnxPEQTypeEntry 2 }

tmnxPEQTypeDescription           OBJECT-TYPE
    SYNTAX      TItemDescription
    MAX-ACCESS  read-only
    STATUS      current
    DESCRIPTION
        "The value of tmnxPEQTypeDescription indicates the detailed description
         of this Nokia SROS series PEQ type."
    ::= { tmnxPEQTypeEntry 3 }

tmnxPEQTypeNumInputFeed          OBJECT-TYPE
    SYNTAX      Unsigned32
    MAX-ACCESS  read-only
    STATUS      current
    DESCRIPTION
        "The value of tmnxPEQTypeNumInputFeed indicates the number of input
         feeds that this PEQ type has."
    ::= { tmnxPEQTypeEntry 4 }

tmnxChassisPEQTableLastChg       OBJECT-TYPE
    SYNTAX      TimeStamp
    MAX-ACCESS  read-only
    STATUS      obsolete
    DESCRIPTION
        "The value of tmnxChassisPEQTableLastChg indicates the time, since
         system startup, that a row in the tmnxChassisPEQTable last changed
         configuration.

         This object was made obsolete in release 15.0."
    ::= { tmnxChassisObjs 15 }

tmnxChassisPEQTable              OBJECT-TYPE
    SYNTAX      SEQUENCE OF TmnxChassisPEQEntry
    MAX-ACCESS  not-accessible
    STATUS      obsolete
    DESCRIPTION
        "The tmnxChassisPEQTable contains information about Power Equalizer
         type in the chassis.

         This table was made obsolete in release 15.0."
    ::= { tmnxChassisObjs 16 }

tmnxChassisPEQEntry              OBJECT-TYPE
    SYNTAX      TmnxChassisPEQEntry
    MAX-ACCESS  not-accessible
    STATUS      obsolete
    DESCRIPTION
        "Each row entry represents an Nokia SROS series PEQ slot.

         This table augments the tmnxChassisPowerSupplyTable on chassis that
         support PEQs.

         Rows in this table are created by the agent at initialization and
         cannot be created or destroyed by SNMP Get or Set requests.

         This entry was made obsolete in release 15.0."
    AUGMENTS    { tmnxChassisPowerSupplyEntry }
    ::= { tmnxChassisPEQTable 1 }

TmnxChassisPEQEntry              ::= SEQUENCE
{
    tmnxChassisPEQLastChangedTime    TimeStamp,
    tmnxChassisPEQAssignedType       TmnxPEQType,
    tmnxChassisPEQEquippedType       TmnxPEQType,
    tmnxChassisPEQSupportedTypes     TmnxPEQSuppType,
    tmnxChassisPEQAvailableWattage   Unsigned32,
    tmnxChassisPEQInputPowerMode     Unsigned32
}

tmnxChassisPEQLastChangedTime    OBJECT-TYPE
    SYNTAX      TimeStamp
    MAX-ACCESS  read-only
    STATUS      obsolete
    DESCRIPTION
        "The value of tmnxChassisPEQLastChangedTime indicates the time, since
         system startup, that an object in this row changed configuration.

         This object was made obsolete in release 15.0."
    ::= { tmnxChassisPEQEntry 1 }

tmnxChassisPEQAssignedType       OBJECT-TYPE
    SYNTAX      TmnxPEQType
    MAX-ACCESS  read-write
    STATUS      obsolete
    DESCRIPTION
        "The value of tmnxChassisPEQAssignedType specifies the administratively
         assigned (pre-provisioned) PEQ type defined in the tmnxPEQTypeTable
         that should occupy this PEQ slot in the chassis.  If
         tmnxChassisPEQAssignedType has a value of 1 (unassigned), this slot has
         not yet been pre-provisioned.

         This object was made obsolete in release 15.0."
    DEFVAL      { 1 }
    ::= { tmnxChassisPEQEntry 2 }

tmnxChassisPEQEquippedType       OBJECT-TYPE
    SYNTAX      TmnxPEQType
    MAX-ACCESS  read-only
    STATUS      obsolete
    DESCRIPTION
        "The value of tmnxChassisPEQEquippedType indicates the PEQ type of the
         PEQ that is physically inserted into this PEQ slot in the chassis. If
         the slot has been pre-provisioned, tmnxChassisPEQAssignedType is not
         equal to 1 (unassigned), and the value of tmnxChassisPEQEquippedType
         is not the same as tmnxChassisPEQAssignedType, a mismatch alarm will
         be raised.

         A value of 0 indicates the PEQ type is not recognized by the SROS.

         This object was made obsolete in release 15.0."
    ::= { tmnxChassisPEQEntry 3 }

tmnxChassisPEQSupportedTypes     OBJECT-TYPE
    SYNTAX      TmnxPEQSuppType
    MAX-ACCESS  read-only
    STATUS      obsolete
    DESCRIPTION
        "The value of tmnxChassisPEQSupportedTypes is a bit-mask that indicates
         what PEQ types can be physically supported in this PEQ slot in this
         chassis.

         This object was made obsolete in release 15.0."
    ::= { tmnxChassisPEQEntry 4 }

tmnxChassisPEQAvailableWattage   OBJECT-TYPE
    SYNTAX      Unsigned32
    UNITS       "watts"
    MAX-ACCESS  read-only
    STATUS      obsolete
    DESCRIPTION
        "The value of tmnxChassisPEQAvailableWattage indicates the reported
         available wattage of the PEQ.

         This object was made obsolete in release 15.0."
    ::= { tmnxChassisPEQEntry 5 }

tmnxChassisPEQInputPowerMode     OBJECT-TYPE
    SYNTAX      Unsigned32 (0 | 60 | 80)
    UNITS       "amperes"
    MAX-ACCESS  read-write
    STATUS      obsolete
    DESCRIPTION
        "The value of tmnxChassisPEQInputPowerMode specifies the input power
         mode of the PEQ.

         A value of zero indicates that the input power mode is not applicable
         for the PEQ. An SNMP SET request with a value of zero is not
         permitted.

         This object was made obsolete in release 15.0."
    ::= { tmnxChassisPEQEntry 6 }

tmnxChassisPowerMgmtTableLastChg OBJECT-TYPE
    SYNTAX      TimeStamp
    MAX-ACCESS  read-only
    STATUS      current
    DESCRIPTION
        "The value of tmnxChassisPowerMgmtTableLastChg indicates the time,
         since system startup, when a row in the tmnxChassisPowerMgmtTable last
         changed configuration."
    ::= { tmnxChassisObjs 17 }

tmnxChassisPowerMgmtTable        OBJECT-TYPE
    SYNTAX      SEQUENCE OF TmnxChassisPowerMgmtEntry
    MAX-ACCESS  not-accessible
    STATUS      current
    DESCRIPTION
        "The tmnxChassisPowerMgmtTable manages the power requirements on the
         SROS series system. This table controls the behavior of the system
         during power resource contention."
    ::= { tmnxChassisObjs 18 }

tmnxChassisPowerMgmtEntry        OBJECT-TYPE
    SYNTAX      TmnxChassisPowerMgmtEntry
    MAX-ACCESS  not-accessible
    STATUS      current
    DESCRIPTION
        "Each row in the tmnxChassisPowerMgmtTable represents a managed
         power-zone on an SROS series system.

         Rows in this table are created by the agent at initialization and
         cannot be created or destroyed by SNMP Get or Set requests."
    INDEX       {
        tmnxChassisIndex,
        tmnxChassisPwrMgmtZone
    }
    ::= { tmnxChassisPowerMgmtTable 1 }

TmnxChassisPowerMgmtEntry        ::= SEQUENCE
{
    tmnxChassisPwrMgmtZone           Unsigned32,
    tmnxChassisPwrMgmtChangedTime    TimeStamp,
    tmnxChassisPwrMgmtMode           INTEGER,
    tmnxChassisPwrMgmtSafetyLevel    Gauge32,
    tmnxChassisPwrMgmtSafetyAlert    Unsigned32,
    tChassisPwrMgmtLowPwrFabAdmState TmnxAdminState,
    tChassisPwrMgmtLowPwrFabCapacity Unsigned32
}

tmnxChassisPwrMgmtZone           OBJECT-TYPE
    SYNTAX      Unsigned32 (1..2)
    MAX-ACCESS  not-accessible
    STATUS      current
    DESCRIPTION
        "The value of tmnxChassisPwrMgmtZone specifies the managed power-zone
         for this management entity."
    ::= { tmnxChassisPowerMgmtEntry 1 }

tmnxChassisPwrMgmtChangedTime    OBJECT-TYPE
    SYNTAX      TimeStamp
    MAX-ACCESS  read-only
    STATUS      current
    DESCRIPTION
        "The value of tmnxChassisPwrMgmtChangedTime indicates the time, since
         system startup, when an object in this row changed configuration."
    ::= { tmnxChassisPowerMgmtEntry 2 }

tmnxChassisPwrMgmtMode           OBJECT-TYPE
    SYNTAX      INTEGER {
        none     (0),
        basic    (1),
        advanced (2)
    }
    MAX-ACCESS  read-write
    STATUS      current
    DESCRIPTION
        "The value of tmnxChassisPwrMgmtMode specifies how the system behaves
         during power contention.

             none (0)  - When set to 'none (0)' the node will bring up as much
                         provisioned equipment in order of priority as possible
                         without exceeding capacity of the equipped or assigned
                         PEQs.

                         In this mode no gradual shutdown of active cards is
                         enforced.

                         Note: No spare capacity is reserved.  Any failure may
                         result in brownouts or card failures.

             basic (1) - When set to 'basic (1)', the node will bring up, in
                         order of priority, as much of the provisioned equipment
                         as possible using the N+1 algorithm. This means enough
                         capacity will be held in reserve to ensure zero impact
                         should the highest rated PEQ fail or be removed.
                         However, subsequent failures may result in brownouts
                         if the system can't shutdown low priority cards in time
                         when the secondary failure/removal occurs.

             advanced (2) - When set to 'advanced (2)', the system will maintain
                         a spare PEQ as long as possible to make it immune to
                         the possibility of power brownouts. It does this by
                         shutting down low priority cards to restore N+1 when
                         N+1 is no longer in effect."
    DEFVAL      { basic }
    ::= { tmnxChassisPowerMgmtEntry 3 }

tmnxChassisPwrMgmtSafetyLevel    OBJECT-TYPE
    SYNTAX      Gauge32 (0..100)
    UNITS       "percent"
    MAX-ACCESS  read-write
    STATUS      current
    DESCRIPTION
        "The value of tmnxChassisPwrMgmtSafetyLevel specifies the percentage of
         the provisioned power requirement that will cause the system to start
         powering off lower-priority cards."
    DEFVAL      { 100 }
    ::= { tmnxChassisPowerMgmtEntry 4 }

tmnxChassisPwrMgmtSafetyAlert    OBJECT-TYPE
    SYNTAX      Unsigned32 (0..120000)
    UNITS       "watts"
    MAX-ACCESS  read-write
    STATUS      current
    DESCRIPTION
        "The value of tmnxChassisPwrMgmtSafetyAlert specifies the power
         capacity threshold where the SROS will trigger an event indicating a
         potential trigger of the safety-level state."
    DEFVAL      { 0 }
    ::= { tmnxChassisPowerMgmtEntry 5 }

tChassisPwrMgmtLowPwrFabAdmState OBJECT-TYPE
    SYNTAX      TmnxAdminState
    MAX-ACCESS  read-write
    STATUS      current
    DESCRIPTION
        "The value of tChassisPwrMgmtLowPwrFabAdmState specifies whether or not
         low power switch fabric mode can be enabled."
    DEFVAL      { outOfService }
    ::= { tmnxChassisPowerMgmtEntry 7 }

tChassisPwrMgmtLowPwrFabCapacity OBJECT-TYPE
    SYNTAX      Unsigned32 (1250..10000)
    UNITS       "centipercent"
    MAX-ACCESS  read-write
    STATUS      current
    DESCRIPTION
        "The value of tChassisPwrMgmtLowPwrFabCapacity indicates the percentage
         capacity of the switch fabrics in low power switch fabric mode.
         Setting this value to 100% (or 10000 centipercent) will disable low
         power switch fabric mode."
    DEFVAL      { 10000 }
    ::= { tmnxChassisPowerMgmtEntry 8 }

tChassisResTable                 OBJECT-TYPE
    SYNTAX      SEQUENCE OF TChassisResEntry
    MAX-ACCESS  not-accessible
    STATUS      current
    DESCRIPTION
        "The value of tChassisResTable represents system resource information
         that are specific to chassis."
    ::= { tmnxChassisObjs 19 }

tChassisResEntry                 OBJECT-TYPE
    SYNTAX      TChassisResEntry
    MAX-ACCESS  not-accessible
    STATUS      current
    DESCRIPTION
        "The value of tChassisResEntry represents chassis specific system
         resource information."
    INDEX       { tmnxChassisIndex }
    ::= { tChassisResTable 1 }

TChassisResEntry                 ::= SEQUENCE
{
    tChassisResSapIngQosPolTotal     Unsigned32,
    tChassisResSapIngQosPolAlloc     Unsigned32,
    tChassisResSapEgrQosPolTotal     Unsigned32,
    tChassisResSapEgrQosPolAlloc     Unsigned32,
    tChassisResIngQGrpTmplTotal      Unsigned32,
    tChassisResIngQGrpTmplAlloc      Unsigned32,
    tChassisResEgrQGrpTmplTotal      Unsigned32,
    tChassisResEgrQGrpTmplAlloc      Unsigned32,
    tChassisResPortEgrQGrpInstTotal  Unsigned32,
    tChassisResPortEgrQGrpInstAlloc  Unsigned32,
    tChassisResFPIngQGrpInstTotal    Unsigned32,
    tChassisResFPIngQGrpInstAlloc    Unsigned32,
    tChassisResPortEgrVPortTotal     Unsigned32,
    tChassisResPortEgrVPortAlloc     Unsigned32,
    tChassisResDynSvcNHEntryTotal    Unsigned32,
    tChassisResDynSvcNHEntryAlloc    Unsigned32,
    tChassisResIpSecNHEntryTotal     Unsigned32,
    tChassisResIpSecNHEntryAlloc     Unsigned32,
    tChassisResSubNHEntryTotal       Unsigned32,
    tChassisResSubNHEntryAlloc       Unsigned32,
    tChassisResSapTotal              Unsigned32,
    tChassisResSapAlloc              Unsigned32,
    tChassisResEgrStatVlanVoQTotal   Unsigned32,
    tChassisResEgrStatVlanVoQAlloc   Unsigned32,
    tChassisResEgrNoStatVlanVoQTotal Unsigned32,
    tChassisResEgrNoStatVlanVoQAlloc Unsigned32,
    tChassisResIngClassQosPolTotal   Unsigned32,
    tChassisResIngClassQosPolAlloc   Unsigned32,
    tChassisResEgrRemarkQosPolTotal  Unsigned32,
    tChassisResEgrRemarkQosPolAlloc  Unsigned32,
    tChassisResQueueMgmtQosPolTotal  Unsigned32,
    tChassisResQueueMgmtQosPolAlloc  Unsigned32,
    tChassisResApipeSapTotal         Unsigned32,
    tChassisResApipeSapAlloc         Unsigned32,
    tChassisResCpipeSapTotal         Unsigned32,
    tChassisResCpipeSapAlloc         Unsigned32,
    tChassisResEpipeSapTotal         Unsigned32,
    tChassisResEpipeSapAlloc         Unsigned32,
    tChassisResFpipeSapTotal         Unsigned32,
    tChassisResFpipeSapAlloc         Unsigned32,
    tChassisResIpipeSapTotal         Unsigned32,
    tChassisResIpipeSapAlloc         Unsigned32,
    tChassisResIesSapTotal           Unsigned32,
    tChassisResIesSapAlloc           Unsigned32,
    tChassisResMirrorSapTotal        Unsigned32,
    tChassisResMirrorSapAlloc        Unsigned32,
    tChassisResVplsSapTotal          Unsigned32,
    tChassisResVplsSapAlloc          Unsigned32,
    tChassisResVprnSapTotal          Unsigned32,
    tChassisResVprnSapAlloc          Unsigned32,
    tChassisResFastDepthMQueuesTotal Unsigned32,
    tChassisResFastDepthMQueuesAlloc Unsigned32,
    tChassisResDot1pFCMapTotal       Unsigned32,
    tChassisResDot1pFCMapAlloc       Unsigned32,
    tChassisResDscpFCMapTotal        Unsigned32,
    tChassisResDscpFCMapAlloc        Unsigned32,
    tChassisResLspExpFCMapTotal      Unsigned32,
    tChassisResLspExpFCMapAlloc      Unsigned32,
    tChassisResFCDot1pMapTotal       Unsigned32,
    tChassisResFCDot1pMapAlloc       Unsigned32,
    tChassisResFCDscpMapTotal        Unsigned32,
    tChassisResFCDscpMapAlloc        Unsigned32,
    tChassisResFCLspExpMapTotal      Unsigned32,
    tChassisResFCLspExpMapAlloc      Unsigned32,
    tChassisResPool1LagBundleIdTotal Unsigned32,
    tChassisResPool1LagBundleIdAlloc Unsigned32,
    tChassisResPool2LagBundleIdTotal Unsigned32,
    tChassisResPool2LagBundleIdAlloc Unsigned32,
    tChassisResSystemBundleNumTotal  Unsigned32,
    tChassisResSystemBundleNumAlloc  Unsigned32,
    tChassisResIOCapacityTotal       Unsigned32,
    tChassisResIOCapacityAlloc       Unsigned32,
    tChassisResMtuProfileTotal       Unsigned32,
    tChassisResMtuProfileAlloc       Unsigned32,
    tChassisResEprirTotal            Unsigned32,
    tChassisResEprirAlloc            Unsigned32,
    tChassisResEprirMirrorAlloc      Unsigned32,
    tChassisResEprirRadiusAlloc      Unsigned32,
    tChassisResEprirSatTrafGenTotal  Unsigned32,
    tChassisResEprirSatTrafGenAlloc  Unsigned32,
    tChassisResEprirReservedAlloc    Unsigned32,
    tChassisResEprirFilterAlloc      Unsigned32,
    tChassisResEgrStat4QVVoQTotal    Unsigned32,
    tChassisResEgrStat4QVVoQAlloc    Unsigned32,
    tChassisResEgrNoStat4QVVoQTotal  Unsigned32,
    tChassisResEgrNoStat4QVVoQAlloc  Unsigned32
}

tChassisResSapIngQosPolTotal     OBJECT-TYPE
    SYNTAX      Unsigned32
    MAX-ACCESS  read-only
    STATUS      current
    DESCRIPTION
        "The value of tChassisResSapIngQosPolTotal represents the total number
         of sap-ingress QoS policies that are allowed to be provisioned on this
         chassis.

         When the value of tChassisResSapIngQosPolTotal is zero, it indicates
         that this resource type is not supported on this chassis."
    ::= { tChassisResEntry 1 }

tChassisResSapIngQosPolAlloc     OBJECT-TYPE
    SYNTAX      Unsigned32
    MAX-ACCESS  read-only
    STATUS      current
    DESCRIPTION
        "The value of tChassisResSapIngQosPolAlloc represents the total number
         of sap-ingress QoS policies that are currently provisioned on this
         chassis."
    ::= { tChassisResEntry 2 }

tChassisResSapEgrQosPolTotal     OBJECT-TYPE
    SYNTAX      Unsigned32
    MAX-ACCESS  read-only
    STATUS      current
    DESCRIPTION
        "The value of tChassisResSapEgrQosPolTotal represents the total number
         of sap-egress QoS policies that are allowed to be provisioned on this
         chassis.

         When the value of tChassisResSapEgrQosPolTotal is zero, it indicates
         that this resource type is not supported on this chassis."
    ::= { tChassisResEntry 3 }

tChassisResSapEgrQosPolAlloc     OBJECT-TYPE
    SYNTAX      Unsigned32
    MAX-ACCESS  read-only
    STATUS      current
    DESCRIPTION
        "The value of tChassisResSapEgrQosPolAlloc represents the total number
         of sap-egress QoS policies that are currently provisioned on this
         chassis."
    ::= { tChassisResEntry 4 }

tChassisResIngQGrpTmplTotal      OBJECT-TYPE
    SYNTAX      Unsigned32
    MAX-ACCESS  read-only
    STATUS      current
    DESCRIPTION
        "The value of tChassisResIngQGrpTmplTotal represents the total number
         of ingress queue-group-templates that are allowed to be provisioned on
         this chassis.

         When the value of tChassisResIngQGrpTmplTotal is zero, it indicates
         that this resource type is not supported on this chassis."
    ::= { tChassisResEntry 5 }

tChassisResIngQGrpTmplAlloc      OBJECT-TYPE
    SYNTAX      Unsigned32
    MAX-ACCESS  read-only
    STATUS      current
    DESCRIPTION
        "The value of tChassisResIngQGrpTmplAlloc represents the total number
         of ingress queue-group-templates that are currently provisioned on
         this chassis."
    ::= { tChassisResEntry 6 }

tChassisResEgrQGrpTmplTotal      OBJECT-TYPE
    SYNTAX      Unsigned32
    MAX-ACCESS  read-only
    STATUS      current
    DESCRIPTION
        "The value of tChassisResEgrQGrpTmplTotal represents the total number
         of egress queue-group-templates that are allowed to be provisioned on
         this chassis.

         When the value of tChassisResEgrQGrpTmplTotal is zero, it indicates
         that this resource type is not supported on this chassis."
    ::= { tChassisResEntry 7 }

tChassisResEgrQGrpTmplAlloc      OBJECT-TYPE
    SYNTAX      Unsigned32
    MAX-ACCESS  read-only
    STATUS      current
    DESCRIPTION
        "The value of tChassisResEgrQGrpTmplAlloc represents the total number
         of egress queue-group-templates that are currently provisioned on this
         chassis."
    ::= { tChassisResEntry 8 }

tChassisResPortEgrQGrpInstTotal  OBJECT-TYPE
    SYNTAX      Unsigned32
    MAX-ACCESS  read-only
    STATUS      current
    DESCRIPTION
        "The value of tChassisResPortEgrQGrpInstTotal represents the total
         number of port egress queue-group instances across all the ports on
         this chassis including access and network instances that are allowed
         to be provisioned.

         When the value of tChassisResPortEgrQGrpInstTotal is zero, it
         indicates that this resource type is not supported on this chassis."
    ::= { tChassisResEntry 9 }

tChassisResPortEgrQGrpInstAlloc  OBJECT-TYPE
    SYNTAX      Unsigned32
    MAX-ACCESS  read-only
    STATUS      current
    DESCRIPTION
        "The value of tChassisResPortEgrQGrpInstAlloc represents the total
         number of port egress queue-group instances across all the ports on
         this chassis including access and network instances that are currently
         provisioned."
    ::= { tChassisResEntry 10 }

tChassisResFPIngQGrpInstTotal    OBJECT-TYPE
    SYNTAX      Unsigned32
    MAX-ACCESS  read-only
    STATUS      current
    DESCRIPTION
        "The value of tChassisResFPIngQGrpInstTotal represents the total number
         of forwarding-plane (FP) ingress queue-group instances across all the
         FP on this chassis including access and network instances that are
         allowed to be provisioned.

         When the value of tChassisResFPIngQGrpInstTotal is zero, it indicates
         that this resource type is not supported on this chassis."
    ::= { tChassisResEntry 11 }

tChassisResFPIngQGrpInstAlloc    OBJECT-TYPE
    SYNTAX      Unsigned32
    MAX-ACCESS  read-only
    STATUS      current
    DESCRIPTION
        "The value of tChassisResFPIngQGrpInstAlloc represents the total number
         of forwarding-plane (FP) ingress queue-group instances across all the
         FP on this chassis including access and network instances that are
         allowed to be provisioned."
    ::= { tChassisResEntry 12 }

tChassisResPortEgrVPortTotal     OBJECT-TYPE
    SYNTAX      Unsigned32
    MAX-ACCESS  read-only
    STATUS      current
    DESCRIPTION
        "The value of tChassisResPortEgrVPortTotal represents the total number
         of egress virtual ports across all the ports on this chassis that are
         allowed to be provisioned.

         When the value of tChassisResPortEgrVPortTotal is zero, it indicates
         that this resource type is not supported on this chassis."
    ::= { tChassisResEntry 13 }

tChassisResPortEgrVPortAlloc     OBJECT-TYPE
    SYNTAX      Unsigned32
    MAX-ACCESS  read-only
    STATUS      current
    DESCRIPTION
        "The value of tChassisResPortEgrVPortAlloc represents the total number
         of port virtual ports across all the ports on this chassis that are
         currently provisioned."
    ::= { tChassisResEntry 14 }

tChassisResDynSvcNHEntryTotal    OBJECT-TYPE
    SYNTAX      Unsigned32
    MAX-ACCESS  read-only
    STATUS      current
    DESCRIPTION
        "The value of tChassisResDynSvcNHEntryTotal represents the total number
         of dynamic service next-hop entries supported on this chassis.

         When the value of tChassisResDynSvcNHEntryTotal is zero, it indicates
         that this resource type is not supported on this chassis."
    ::= { tChassisResEntry 15 }

tChassisResDynSvcNHEntryAlloc    OBJECT-TYPE
    SYNTAX      Unsigned32
    MAX-ACCESS  read-only
    STATUS      current
    DESCRIPTION
        "The value of tChassisResDynSvcNHEntryAlloc represents the total number
         of dynamic service next-hop entries currently in use on this chassis.

         The value of tChassisResDynSvcNHEntryAlloc will always equal to the
         sum of tChassisResIpSecNHEntryAlloc and tChassisResSubNHEntryAlloc
         since IPsec next-hop and subscriber next-hop resources are subsets of
         dynamic service next-hop entry resources."
    ::= { tChassisResEntry 16 }

tChassisResIpSecNHEntryTotal     OBJECT-TYPE
    SYNTAX      Unsigned32
    MAX-ACCESS  read-only
    STATUS      current
    DESCRIPTION
        "The value of tChassisResIpSecNHEntryTotal represents the total number
         of IPsec next-hop entries supported on this chassis.

         When the value of tChassisResIpSecNHEntryTotal is zero, it indicates
         that this resource type is not supported on this chassis.

         The value of tChassisResIpSecNHEntryTotal will always be less than or
         equal to tChassisResDynSvcNHEntryTotal since IPsec next-hop entry
         resources are a subset of dynamic service next-hop entry resources."
    ::= { tChassisResEntry 17 }

tChassisResIpSecNHEntryAlloc     OBJECT-TYPE
    SYNTAX      Unsigned32
    MAX-ACCESS  read-only
    STATUS      current
    DESCRIPTION
        "The value of tChassisResIpSecNHEntryAlloc represents the total number
         of IPsec next-hop entries currently in use on this chassis.

         The value of tChassisResIpSecNHEntryAlloc will always be less than or
         equal to tChassisResDynSvcNHEntryAlloc since IPsec next-hop entry
         resources are a subset of dynamic service next-hop entry resources."
    ::= { tChassisResEntry 18 }

tChassisResSubNHEntryTotal       OBJECT-TYPE
    SYNTAX      Unsigned32
    MAX-ACCESS  read-only
    STATUS      current
    DESCRIPTION
        "The value of tChassisResSubNHEntryTotal represents the total number of
         subscriber next-hop entries supported on this chassis.

         When the value of tChassisResSubNHEntryTotal is zero, it indicates
         that this resource type is not supported on this chassis.

         The value of tChassisResSubNHEntryTotal will always be less than or
         equal to tChassisResDynSvcNHEntryTotal since subscriber next-hop entry
         resources are a subset of dynamic service next-hop entry resources."
    ::= { tChassisResEntry 19 }

tChassisResSubNHEntryAlloc       OBJECT-TYPE
    SYNTAX      Unsigned32
    MAX-ACCESS  read-only
    STATUS      current
    DESCRIPTION
        "The value of tChassisResSubNHEntryAlloc represents the total number of
         subscriber next-hop entries currently in use on this chassis.

         The value of tChassisResSubNHEntryAlloc will always be less than or
         equal to tChassisResDynSvcNHEntryAlloc since subscriber next-hop entry
         resources are a subset of dynamic service next hop entry resources."
    ::= { tChassisResEntry 20 }

tChassisResSapTotal              OBJECT-TYPE
    SYNTAX      Unsigned32
    MAX-ACCESS  read-only
    STATUS      current
    DESCRIPTION
        "The value of tChassisResSapTotal represents the total number of
         provisioned SAP entries supported on this chassis.

         When the value of tChassisResSapTotal is zero, it indicates that this
         resource type is not supported on this chassis."
    ::= { tChassisResEntry 21 }

tChassisResSapAlloc              OBJECT-TYPE
    SYNTAX      Unsigned32
    MAX-ACCESS  read-only
    STATUS      current
    DESCRIPTION
        "The value of tChassisResSapAlloc represents the total number of
         provisioned SAP entries currently in use on this chassis."
    ::= { tChassisResEntry 22 }

tChassisResEgrStatVlanVoQTotal   OBJECT-TYPE
    SYNTAX      Unsigned32
    MAX-ACCESS  read-only
    STATUS      current
    DESCRIPTION
        "The value of tChassisResEgrStatVlanVoQTotal represents the total
         number of stats enabled vlan Voq resources supported on this chassis.

         When the value of tChassisResEgrStatVlanVoQTotal is zero, it indicates
         that this resource type is not supported on this chassis."
    ::= { tChassisResEntry 23 }

tChassisResEgrStatVlanVoQAlloc   OBJECT-TYPE
    SYNTAX      Unsigned32
    MAX-ACCESS  read-only
    STATUS      current
    DESCRIPTION
        "The value of tChassisResEgrStatVlanVoQAlloc represents the total
         number of stats enabled vlan Voq resources currently in use on this
         chassis."
    ::= { tChassisResEntry 24 }

tChassisResEgrNoStatVlanVoQTotal OBJECT-TYPE
    SYNTAX      Unsigned32
    MAX-ACCESS  read-only
    STATUS      current
    DESCRIPTION
        "The value of tChassisResEgrNoStatVlanVoQTotal represents the total
         number of stats disabled vlan Voq resources supported on this chassis.

         When the value of tChassisResEgrNoStatVlanVoQTotal is zero, it
         indicates that this resource type is not supported on this chassis."
    ::= { tChassisResEntry 25 }

tChassisResEgrNoStatVlanVoQAlloc OBJECT-TYPE
    SYNTAX      Unsigned32
    MAX-ACCESS  read-only
    STATUS      current
    DESCRIPTION
        "The value of tChassisResEgrNoStatVlanVoQAlloc represents the total
         number of stats disabled vlan Voq resources currently in use on this
         chassis."
    ::= { tChassisResEntry 26 }

tChassisResIngClassQosPolTotal   OBJECT-TYPE
    SYNTAX      Unsigned32
    MAX-ACCESS  read-only
    STATUS      current
    DESCRIPTION
        "The value of tChassisResIngClassQosPolTotal represents the total
         number of ingress-classification policies that are allowed to be
         provisioned on this chassis. When the value of
         tChassisResIngClassQosPolTotal is zero, it indicates that this
         resource type is not supported on this chassis."
    ::= { tChassisResEntry 27 }

tChassisResIngClassQosPolAlloc   OBJECT-TYPE
    SYNTAX      Unsigned32
    MAX-ACCESS  read-only
    STATUS      current
    DESCRIPTION
        "The value of tChassisResIngClassQosPolAlloc represents the total
         number of ingress-classification policies that are currently
         provisioned on this chassis."
    ::= { tChassisResEntry 28 }

tChassisResEgrRemarkQosPolTotal  OBJECT-TYPE
    SYNTAX      Unsigned32
    MAX-ACCESS  read-only
    STATUS      current
    DESCRIPTION
        "The value of tChassisResEgrRemarkQosPolTotal represents the total
         number of egress-remark policies that are allowed to be provisioned on
         this chassis.

         When the value of tChassisResEgrRemarkQosPolTotal is zero, it
         indicates that this resource type is not supported on this chassis."
    ::= { tChassisResEntry 29 }

tChassisResEgrRemarkQosPolAlloc  OBJECT-TYPE
    SYNTAX      Unsigned32
    MAX-ACCESS  read-only
    STATUS      current
    DESCRIPTION
        "The value of tChassisResEgrRemarkQosPolAlloc represents the total
         number of egress-remark policies that are currently provisioned on
         this chassis."
    ::= { tChassisResEntry 30 }

tChassisResQueueMgmtQosPolTotal  OBJECT-TYPE
    SYNTAX      Unsigned32
    MAX-ACCESS  read-only
    STATUS      current
    DESCRIPTION
        "The value of tChassisResQueueMgmtQosPolTotal represents the total
         number of queue mgmt policies that are supported on this chassis.

         When the value of tChassisResQueueMgmtQosPolTotal is zero, it
         indicates that this resource type is not supported on this chassis."
    ::= { tChassisResEntry 31 }

tChassisResQueueMgmtQosPolAlloc  OBJECT-TYPE
    SYNTAX      Unsigned32
    MAX-ACCESS  read-only
    STATUS      current
    DESCRIPTION
        "The value of tChassisResQueueMgmtQosPolAlloc represents the total
         number of queue mgmt policies that are currently allocated on this FP."
    ::= { tChassisResEntry 32 }

tChassisResApipeSapTotal         OBJECT-TYPE
    SYNTAX      Unsigned32
    MAX-ACCESS  read-only
    STATUS      obsolete
    DESCRIPTION
        "The value of tChassisResApipeSapTotal represents the total number of
         provisioned Apipe entries supported on this chassis.

         When the value of tChassisResApipeSapTotal is zero, it indicates that
         this resource type is not supported on this chassis."
    ::= { tChassisResEntry 33 }

tChassisResApipeSapAlloc         OBJECT-TYPE
    SYNTAX      Unsigned32
    MAX-ACCESS  read-only
    STATUS      obsolete
    DESCRIPTION
        "The value of tChassisResApipeSapAlloc represents the total number of
         instances that are currently allocated on this chassis."
    ::= { tChassisResEntry 34 }

tChassisResCpipeSapTotal         OBJECT-TYPE
    SYNTAX      Unsigned32
    MAX-ACCESS  read-only
    STATUS      current
    DESCRIPTION
        "The value of tChassisResCpipeSapTotal represents the total number of
         provisioned Cpipe entries supported on this chassis.

         When the value of tChassisResCpipeSapTotal is zero, it indicates that
         this resource type is not supported on this chassis."
    ::= { tChassisResEntry 35 }

tChassisResCpipeSapAlloc         OBJECT-TYPE
    SYNTAX      Unsigned32
    MAX-ACCESS  read-only
    STATUS      current
    DESCRIPTION
        "The value of tChassisResCpipeSapAlloc represents the total number of
         instances that are currently allocated on this chassis."
    ::= { tChassisResEntry 36 }

tChassisResEpipeSapTotal         OBJECT-TYPE
    SYNTAX      Unsigned32
    MAX-ACCESS  read-only
    STATUS      current
    DESCRIPTION
        "The value of tChassisResEpipeSapTotal represents the total number of
         provisioned Epipe entries supported on this chassis.

         When the value of tChassisResEpipeSapTotal is zero, it indicates that
         this resource type is not supported on this chassis."
    ::= { tChassisResEntry 37 }

tChassisResEpipeSapAlloc         OBJECT-TYPE
    SYNTAX      Unsigned32
    MAX-ACCESS  read-only
    STATUS      current
    DESCRIPTION
        "The value of tChassisResEpipeSapAlloc represents the total number of
         instances that are currently allocated on this chassis."
    ::= { tChassisResEntry 38 }

tChassisResFpipeSapTotal         OBJECT-TYPE
    SYNTAX      Unsigned32
    MAX-ACCESS  read-only
    STATUS      obsolete
    DESCRIPTION
        "The value of tChassisResFpipeSapTotal represents the total number of
         provisioned Fpipe entries supported on this chassis.

         When the value of tChassisResFpipeSapTotal is zero, it indicates that
         this resource type is not supported on this chassis."
    ::= { tChassisResEntry 39 }

tChassisResFpipeSapAlloc         OBJECT-TYPE
    SYNTAX      Unsigned32
    MAX-ACCESS  read-only
    STATUS      obsolete
    DESCRIPTION
        "The value of tChassisResFpipeSapAlloc represents the total number of
         instances that are currently allocated on this chassis."
    ::= { tChassisResEntry 40 }

tChassisResIpipeSapTotal         OBJECT-TYPE
    SYNTAX      Unsigned32
    MAX-ACCESS  read-only
    STATUS      current
    DESCRIPTION
        "The value of tChassisResIpipeSapTotal represents the total number of
         provisioned Ipipe entries supported on this chassis.

         When the value of tChassisResIpipeSapTotal is zero, it indicates that
         this resource type is not supported on this chassis."
    ::= { tChassisResEntry 41 }

tChassisResIpipeSapAlloc         OBJECT-TYPE
    SYNTAX      Unsigned32
    MAX-ACCESS  read-only
    STATUS      current
    DESCRIPTION
        "The value of tChassisResIpipeSapAlloc represents the total number of
         instances that are currently allocated on this chassis."
    ::= { tChassisResEntry 42 }

tChassisResIesSapTotal           OBJECT-TYPE
    SYNTAX      Unsigned32
    MAX-ACCESS  read-only
    STATUS      current
    DESCRIPTION
        "The value of tChassisResIesSapTotal represents the total number of
         provisioned Ies entries supported on this chassis.

         When the value of tChassisResIesSapTotal is zero, it indicates that
         this resource type is not supported on this chassis."
    ::= { tChassisResEntry 43 }

tChassisResIesSapAlloc           OBJECT-TYPE
    SYNTAX      Unsigned32
    MAX-ACCESS  read-only
    STATUS      current
    DESCRIPTION
        "The value of tChassisResIesSapAlloc represents the total number of
         instances that are currently allocated on this chassis."
    ::= { tChassisResEntry 44 }

tChassisResMirrorSapTotal        OBJECT-TYPE
    SYNTAX      Unsigned32
    MAX-ACCESS  read-only
    STATUS      current
    DESCRIPTION
        "The value of tChassisResMirrorSapTotal represents the total number of
         provisioned Mirror entries supported on this chassis.

         When the value of tChassisResMirrorSapTotal is zero, it indicates that
         this resource type is not supported on this chassis."
    ::= { tChassisResEntry 45 }

tChassisResMirrorSapAlloc        OBJECT-TYPE
    SYNTAX      Unsigned32
    MAX-ACCESS  read-only
    STATUS      current
    DESCRIPTION
        "The value of tChassisResMirrorSapAlloc represents the total number of
         instances that are currently allocated on this chassis."
    ::= { tChassisResEntry 46 }

tChassisResVplsSapTotal          OBJECT-TYPE
    SYNTAX      Unsigned32
    MAX-ACCESS  read-only
    STATUS      current
    DESCRIPTION
        "The value of tChassisResVplsSapTotal represents the total number of
         provisioned Vpls entries supported on this chassis.

         When the value of tChassisResVplsSapTotal is zero, it indicates that
         this resource type is not supported on this chassis."
    ::= { tChassisResEntry 47 }

tChassisResVplsSapAlloc          OBJECT-TYPE
    SYNTAX      Unsigned32
    MAX-ACCESS  read-only
    STATUS      current
    DESCRIPTION
        "The value of tChassisResVplsSapAlloc represents the total number of
         instances that are currently allocated on this chassis."
    ::= { tChassisResEntry 48 }

tChassisResVprnSapTotal          OBJECT-TYPE
    SYNTAX      Unsigned32
    MAX-ACCESS  read-only
    STATUS      current
    DESCRIPTION
        "The value of tChassisResVprnSapTotal represents the total number of
         provisioned Vprn entries supported on this chassis.

         When the value of tChassisResVprnSapTotal is zero, it indicates that
         this resource type is not supported on this chassis."
    ::= { tChassisResEntry 49 }

tChassisResVprnSapAlloc          OBJECT-TYPE
    SYNTAX      Unsigned32
    MAX-ACCESS  read-only
    STATUS      current
    DESCRIPTION
        "The value of tChassisResVprnSapAlloc represents the total number of
         instances that are currently allocated on this chassis."
    ::= { tChassisResEntry 50 }

tChassisResFastDepthMQueuesTotal OBJECT-TYPE
    SYNTAX      Unsigned32
    MAX-ACCESS  read-only
    STATUS      current
    DESCRIPTION
        "The value of tChassisResFastDepthMQueuesTotal represents the total
         number of fast polled queue depth monitored queue resources that are
         allowed to provisioned on this chassis.

         When the value of tChassisResFastDepthMQueuesTotal is zero, it
         indicates that this resource type is not supported on this chassis."
    ::= { tChassisResEntry 51 }

tChassisResFastDepthMQueuesAlloc OBJECT-TYPE
    SYNTAX      Unsigned32
    MAX-ACCESS  read-only
    STATUS      current
    DESCRIPTION
        "The value of tChassisResFastDepthMQueuesAlloc represents the total
         number of fast polled queue depth monitored queue resources that are
         instances that are currently allocated on this chassis."
    ::= { tChassisResEntry 52 }

tChassisResDot1pFCMapTotal       OBJECT-TYPE
    SYNTAX      Unsigned32
    MAX-ACCESS  read-only
    STATUS      current
    DESCRIPTION
        "The value of tChassisResDot1pFCMapTotal represents the total number of
         Dot1p FC maps that are allowed on this chassis.

         When the value of tChassisResDot1pFCMapTotal is zero, it indicates
         that this resource type is not supported on this chassis."
    ::= { tChassisResEntry 53 }

tChassisResDot1pFCMapAlloc       OBJECT-TYPE
    SYNTAX      Unsigned32
    MAX-ACCESS  read-only
    STATUS      current
    DESCRIPTION
        "The value of tChassisResDot1pFCMapAlloc represents the number of Dot1p
         FC maps that are currently allocated on this chassis."
    ::= { tChassisResEntry 54 }

tChassisResDscpFCMapTotal        OBJECT-TYPE
    SYNTAX      Unsigned32
    MAX-ACCESS  read-only
    STATUS      current
    DESCRIPTION
        "The value of tChassisResDscpFCMapTotal represents the total number of
         Dscp FC maps that are allowed on this chassis.

         When the value of tChassisResDscpFCMapTotal is zero, it indicates that
         this resource type is not supported on this chassis."
    ::= { tChassisResEntry 55 }

tChassisResDscpFCMapAlloc        OBJECT-TYPE
    SYNTAX      Unsigned32
    MAX-ACCESS  read-only
    STATUS      current
    DESCRIPTION
        "The value of tChassisResDscpFCMapAlloc represents the number of Dscp
         FC maps that are currently allocated on this chassis."
    ::= { tChassisResEntry 56 }

tChassisResLspExpFCMapTotal      OBJECT-TYPE
    SYNTAX      Unsigned32
    MAX-ACCESS  read-only
    STATUS      current
    DESCRIPTION
        "The value of tChassisResLspExpFCMapTotal represents the total number
         of Dot1p FC maps that are allowed on this chassis.

         When the value of tChassisResLspExpFCMapTotal is zero, it indicates
         that this resource type is not supported on this chassis."
    ::= { tChassisResEntry 57 }

tChassisResLspExpFCMapAlloc      OBJECT-TYPE
    SYNTAX      Unsigned32
    MAX-ACCESS  read-only
    STATUS      current
    DESCRIPTION
        "The value of tChassisResLspExpFCMapAlloc represents the number of
         Lsp-Exp FC maps that are currently allocated on this chassis."
    ::= { tChassisResEntry 58 }

tChassisResFCDot1pMapTotal       OBJECT-TYPE
    SYNTAX      Unsigned32
    MAX-ACCESS  read-only
    STATUS      current
    DESCRIPTION
        "The value of tChassisResFCDot1pMapTotal represents the total number of
         FC Dot1p maps that are allowed on this chassis.

         When the value of tChassisResFCDot1pMapTotal is zero, it indicates
         that this resource type is not supported on this chassis."
    ::= { tChassisResEntry 59 }

tChassisResFCDot1pMapAlloc       OBJECT-TYPE
    SYNTAX      Unsigned32
    MAX-ACCESS  read-only
    STATUS      current
    DESCRIPTION
        "The value of tChassisResFCDot1pMapAlloc represents the number of FC
         Dot1p maps that are currently allocated on this chassis."
    ::= { tChassisResEntry 60 }

tChassisResFCDscpMapTotal        OBJECT-TYPE
    SYNTAX      Unsigned32
    MAX-ACCESS  read-only
    STATUS      current
    DESCRIPTION
        "The value of tChassisResFCDscpMapTotal represents the total number of
         FC Dscp maps that are allowed on this chassis.

         When the value of tChassisResFCDscpMapTotal is zero, it indicates that
         this resource type is not supported on this chassis."
    ::= { tChassisResEntry 61 }

tChassisResFCDscpMapAlloc        OBJECT-TYPE
    SYNTAX      Unsigned32
    MAX-ACCESS  read-only
    STATUS      current
    DESCRIPTION
        "The value of tChassisResFCDscpMapAlloc represents the number of FC
         Dscp maps that are currently allocated on this chassis."
    ::= { tChassisResEntry 62 }

tChassisResFCLspExpMapTotal      OBJECT-TYPE
    SYNTAX      Unsigned32
    MAX-ACCESS  read-only
    STATUS      current
    DESCRIPTION
        "The value of tChassisResFCLspExpMapTotal represents the total number
         of FC Lsp-Exp maps that are allowed on this chassis.

         When the value of tChassisResFCLspExpMapTotal is zero, it indicates
         that this resource type is not supported on this chassis."
    ::= { tChassisResEntry 63 }

tChassisResFCLspExpMapAlloc      OBJECT-TYPE
    SYNTAX      Unsigned32
    MAX-ACCESS  read-only
    STATUS      current
    DESCRIPTION
        "The value of tChassisResFCLspExpMapAlloc represents the number of FC
         Lsp-Exp maps that are currently allocated on this chassis."
    ::= { tChassisResEntry 64 }

tChassisResPool1LagBundleIdTotal OBJECT-TYPE
    SYNTAX      Unsigned32
    MAX-ACCESS  read-only
    STATUS      current
    DESCRIPTION
        "The value of tChassisResPool1LagBundleIdTotal represents the total
         number of Pool 1 LAG Bundle Ids that are allowed on this chassis.

         When the value of tChassisResPool1LagBundleIdTotal is zero, it
         indicates that this resource type is not supported on this chassis."
    ::= { tChassisResEntry 65 }

tChassisResPool1LagBundleIdAlloc OBJECT-TYPE
    SYNTAX      Unsigned32
    MAX-ACCESS  read-only
    STATUS      current
    DESCRIPTION
        "The value of tChassisResPool1LagBundleIdAlloc represents the number of
         Pool 1 LAG Bundle Ids that are currently allocated on this chassis."
    ::= { tChassisResEntry 66 }

tChassisResPool2LagBundleIdTotal OBJECT-TYPE
    SYNTAX      Unsigned32
    MAX-ACCESS  read-only
    STATUS      current
    DESCRIPTION
        "The value of tChassisResPool2LagBundleIdTotal represents the total
         number of Pool 2 LAG Bundle Ids that are allowed on this chassis.

         When the value of tChassisResPool2LagBundleIdTotal is zero, it
         indicates that this resource type is not supported on this chassis."
    ::= { tChassisResEntry 67 }

tChassisResPool2LagBundleIdAlloc OBJECT-TYPE
    SYNTAX      Unsigned32
    MAX-ACCESS  read-only
    STATUS      current
    DESCRIPTION
        "The value of tChassisResPool2LagBundleIdAlloc represents the number of
         Pool 2 LAG Bundle Ids that are currently allocated on this chassis."
    ::= { tChassisResEntry 68 }

tChassisResSystemBundleNumTotal  OBJECT-TYPE
    SYNTAX      Unsigned32
    MAX-ACCESS  read-only
    STATUS      current
    DESCRIPTION
        "The value of tChassisResSystemBundleNumTotal represents the total
         number of System Port Numbers that are allowed on this chassis.

         When the value of tChassisResSystemBundleNumTotal is zero, it
         indicates that this resource type is not supported on this chassis."
    ::= { tChassisResEntry 69 }

tChassisResSystemBundleNumAlloc  OBJECT-TYPE
    SYNTAX      Unsigned32
    MAX-ACCESS  read-only
    STATUS      current
    DESCRIPTION
        "The value of tChassisResSystemBundleNumAlloc represents the number of
         System Port Numbers that are currently allocated on this chassis."
    ::= { tChassisResEntry 70 }

tChassisResIOCapacityTotal       OBJECT-TYPE
    SYNTAX      Unsigned32
    UNITS       "gigabps"
    MAX-ACCESS  read-only
    STATUS      current
    DESCRIPTION
        "The value of tChassisResIOCapacityTotal represents the total
         Input/Output capacity of the system."
    ::= { tChassisResEntry 71 }

tChassisResIOCapacityAlloc       OBJECT-TYPE
    SYNTAX      Unsigned32
    UNITS       "gigabps"
    MAX-ACCESS  read-only
    STATUS      current
    DESCRIPTION
        "The value of tChassisResIOCapacityAlloc represents the current
         provisioned Input/Output capacity of the system."
    ::= { tChassisResEntry 72 }

tChassisResMtuProfileTotal       OBJECT-TYPE
    SYNTAX      Unsigned32
    MAX-ACCESS  read-only
    STATUS      current
    DESCRIPTION
        "The value of tChassisResMtuProfileTotal represents the number of mtu
         profiles that are allowed on this chassis."
    ::= { tChassisResEntry 73 }

tChassisResMtuProfileAlloc       OBJECT-TYPE
    SYNTAX      Unsigned32
    MAX-ACCESS  read-only
    STATUS      current
    DESCRIPTION
        "The value of tChassisResMtuProfileAlloc represents the number of mtu
         profiles that are allocated on this chassis."
    ::= { tChassisResEntry 74 }

tChassisResEprirTotal            OBJECT-TYPE
    SYNTAX      Unsigned32
    MAX-ACCESS  read-only
    STATUS      current
    DESCRIPTION
        "The value of tChassisResEprirTotal represents the total Egress Packet
         Re-injection Resources (EPRIR) of the system."
    ::= { tChassisResEntry 75 }

tChassisResEprirAlloc            OBJECT-TYPE
    SYNTAX      Unsigned32
    MAX-ACCESS  read-only
    STATUS      current
    DESCRIPTION
        "The value of tChassisResEprirAlloc represents the allocated Egress
         Packet Re-injection Resources (EPRIR) of the system."
    ::= { tChassisResEntry 76 }

tChassisResEprirMirrorAlloc      OBJECT-TYPE
    SYNTAX      Unsigned32
    MAX-ACCESS  read-only
    STATUS      current
    DESCRIPTION
        "The value of tChassisResEprirMirrorAlloc represents the subset of
         resources which are currently allocated to mirror out of all currently
         allocated Egress Packet Re-injection Resources (EPRIR),
         tChassisResEprirAlloc."
    ::= { tChassisResEntry 77 }

tChassisResEprirRadiusAlloc      OBJECT-TYPE
    SYNTAX      Unsigned32
    MAX-ACCESS  read-only
    STATUS      current
    DESCRIPTION
        "The value of tChassisResEprirRadiusAlloc represents the subset of
         resources which are currently allocated to radius out of all currently
         allocated Egress Packet Re-injection Resources (EPRIR),
         tChassisResEprirAlloc."
    ::= { tChassisResEntry 78 }

tChassisResEprirSatTrafGenTotal  OBJECT-TYPE
    SYNTAX      Unsigned32
    MAX-ACCESS  read-only
    STATUS      current
    DESCRIPTION
        "The value of tChassisResEprirSatTrafGenTotal represents the total
         number of Service Activation Test (SAT) traffic generator resources
         supported on this chassis.

         When the value of tChassisResEprirSatTrafGenTotal is zero, it
         indicates that this resource type is not supported on this chassis.

         The value of tChassisResEprirSatTrafGenTotal will always be less than
         or equal to tChassisResEprirTotal since SAT traffic generator
         resources are a subset of Egress Packet Re-injection Resources
         (EPRIR)."
    ::= { tChassisResEntry 79 }

tChassisResEprirSatTrafGenAlloc  OBJECT-TYPE
    SYNTAX      Unsigned32
    MAX-ACCESS  read-only
    STATUS      current
    DESCRIPTION
        "The value of tChassisResEprirSatTrafGenAlloc represents the number of
         of Service Activation Test (SAT) traffic generator resources currently
         in use on this chassis.

         The value of tChassisResEprirSatTrafGenAlloc will always be less than
         or equal to tChassisResEprirAlloc since SAT traffic generator
         resources are a subset of Egress Packet Re-injection Resources
         (EPRIR)."
    ::= { tChassisResEntry 80 }

tChassisResEprirReservedAlloc    OBJECT-TYPE
    SYNTAX      Unsigned32
    MAX-ACCESS  read-only
    STATUS      current
    DESCRIPTION
        "The value of tChassisResEprirReservedAlloc represents the subset of
         resources which are currently reserved out of currently allocated
         Egress Packet Re-injection Resources (EPRIR), tChassisResEprirAlloc."
    ::= { tChassisResEntry 81 }

tChassisResEprirFilterAlloc      OBJECT-TYPE
    SYNTAX      Unsigned32
    MAX-ACCESS  read-only
    STATUS      current
    DESCRIPTION
        "The value of tChassisResEprirFilterAlloc represents the subset of
         resources which are currently allocated to filter out of currently
         allocated Egress Packet Re-injection Resources (EPRIR),
         tChassisResEprirAlloc."
    ::= { tChassisResEntry 82 }

tChassisResEgrStat4QVVoQTotal    OBJECT-TYPE
    SYNTAX      Unsigned32
    MAX-ACCESS  read-only
    STATUS      current
    DESCRIPTION
        "The value of tChassisResEgrStatVlanVoQTotal represents the total
         number of stats enabled vlan Voq resources supported on this chassis.

         When the value of tChassisResEgrStatVlanVoQTotal is zero, it indicates
         that this resource type is not supported on this chassis."
    ::= { tChassisResEntry 83 }

tChassisResEgrStat4QVVoQAlloc    OBJECT-TYPE
    SYNTAX      Unsigned32
    MAX-ACCESS  read-only
    STATUS      current
    DESCRIPTION
        "The value of tChassisResEgrStatVlanVoQAlloc represents the total
         number of stats enabled vlan Voq resources currently in use on this
         chassis."
    ::= { tChassisResEntry 84 }

tChassisResEgrNoStat4QVVoQTotal  OBJECT-TYPE
    SYNTAX      Unsigned32
    MAX-ACCESS  read-only
    STATUS      current
    DESCRIPTION
        "The value of tChassisResEgrNoStatVlanVoQTotal represents the total
         number of stats disabled vlan Voq resources supported on this chassis.

         When the value of tChassisResEgrNoStatVlanVoQTotal is zero, it
         indicates that this resource type is not supported on this chassis."
    ::= { tChassisResEntry 85 }

tChassisResEgrNoStat4QVVoQAlloc  OBJECT-TYPE
    SYNTAX      Unsigned32
    MAX-ACCESS  read-only
    STATUS      current
    DESCRIPTION
        "The value of tChassisResEgrNoStatVlanVoQAlloc represents the total
         number of stats disabled vlan Voq resources currently in use on this
         chassis."
    ::= { tChassisResEntry 86 }

tmnxPhysChassisTable             OBJECT-TYPE
    SYNTAX      SEQUENCE OF TmnxPhysChassisEntry
    MAX-ACCESS  not-accessible
    STATUS      current
    DESCRIPTION
        "The tmnxPhysChassisTable maintains the state of the physical chassis'
         in the system."
    ::= { tmnxChassisObjs 21 }

tmnxPhysChassisEntry             OBJECT-TYPE
    SYNTAX      TmnxPhysChassisEntry
    MAX-ACCESS  not-accessible
    STATUS      current
    DESCRIPTION
        "Each row of tmnxPhysChassisEntry consists of the attributes for an
         individual physical chassis provisioned in the system. Rows are
         created and destroyed by the system."
    INDEX       {
        tmnxChassisIndex,
        tmnxPhysChassisClass,
        tmnxPhysChassisNum
    }
    ::= { tmnxPhysChassisTable 1 }

TmnxPhysChassisEntry             ::= SEQUENCE
{
    tmnxPhysChassisClass             TmnxPhysChassisClass,
    tmnxPhysChassisNum               TmnxPhysChassisIndex,
    tmnxPhysChassisRole              TmnxPhysChassisRole,
    tmnxPhysChassisState             TmnxDeviceState,
    tmnxPhysChassisHwIndex           TmnxHwIndex,
    tmnxPhysChassisNumPwrSupplies    Unsigned32,
    tmnxPhysChassisNumFanTrays       Unsigned32,
    tmnxPhysChassisNumFans           Unsigned32,
    tmnxPhysChassisName              TNamedItem,
    tmnxPhysChassisDescription       TItemDescription,
    tmnxPhysChassisMonitorFilterDoor TruthValue,
    tmnxPhysChassisFilterDoorState   INTEGER
}

tmnxPhysChassisClass             OBJECT-TYPE
    SYNTAX      TmnxPhysChassisClass
    MAX-ACCESS  not-accessible
    STATUS      current
    DESCRIPTION
        "The value of tmnxPhysChassisClass specifies the class of this physical
         chassis in the SROS system."
    ::= { tmnxPhysChassisEntry 1 }

tmnxPhysChassisNum               OBJECT-TYPE
    SYNTAX      TmnxPhysChassisIndex
    MAX-ACCESS  not-accessible
    STATUS      current
    DESCRIPTION
        "The value of tmnxPhysChassisNum specifies the unique identifier,
         within a class, for this physical chassis."
    ::= { tmnxPhysChassisEntry 2 }

tmnxPhysChassisRole              OBJECT-TYPE
    SYNTAX      TmnxPhysChassisRole
    MAX-ACCESS  read-only
    STATUS      current
    DESCRIPTION
        "The value of tmnxPhysChassisRole indicates the role of which this
         physical chassis shall perform while active in the system."
    ::= { tmnxPhysChassisEntry 3 }

tmnxPhysChassisState             OBJECT-TYPE
    SYNTAX      TmnxDeviceState
    MAX-ACCESS  read-only
    STATUS      current
    DESCRIPTION
        "The value of tmnxPhysChassisState indicates the device state of the
         physical chassis in the system."
    ::= { tmnxPhysChassisEntry 4 }

tmnxPhysChassisHwIndex           OBJECT-TYPE
    SYNTAX      TmnxHwIndex
    MAX-ACCESS  read-only
    STATUS      current
    DESCRIPTION
        "The value of tmnxPhysChassisHwIndex indicates the index into the
         tmnxHwTable for the row that represents the hardware component
         information for this physical chassis in the system."
    ::= { tmnxPhysChassisEntry 5 }

tmnxPhysChassisNumPwrSupplies    OBJECT-TYPE
    SYNTAX      Unsigned32
    MAX-ACCESS  read-only
    STATUS      current
    DESCRIPTION
        "The value of tmnxPhysChassisNumPwrSupplies indicates the total number
         of power supplies that can be installed in this physical chassis."
    ::= { tmnxPhysChassisEntry 6 }

tmnxPhysChassisNumFanTrays       OBJECT-TYPE
    SYNTAX      Unsigned32
    MAX-ACCESS  read-only
    STATUS      current
    DESCRIPTION
        "The value of tmnxPhysChassisNumFanTrays indicates the total number of
         fan trays installed in this physical chassis."
    ::= { tmnxPhysChassisEntry 7 }

tmnxPhysChassisNumFans           OBJECT-TYPE
    SYNTAX      Unsigned32
    MAX-ACCESS  read-only
    STATUS      obsolete
    DESCRIPTION
        "The value of tmnxPhysChassisNumFans indicates the total number of fans
         installed in this physical chassis.

         This object was made obsolete in release 16.0."
    ::= { tmnxPhysChassisEntry 8 }

tmnxPhysChassisName              OBJECT-TYPE
    SYNTAX      TNamedItem
    MAX-ACCESS  read-only
    STATUS      current
    DESCRIPTION
        "The value of tmnxPhysChassisName indicates the textual name for this
         physical chassis.

         Examples:
            tmnxPhysChassisName     tmnxPhysChassisClass    tmnxPhysChassisNum
            1                       'routerChassis(3)'      1"
    ::= { tmnxPhysChassisEntry 9 }

tmnxPhysChassisDescription       OBJECT-TYPE
    SYNTAX      TItemDescription
    MAX-ACCESS  read-write
    STATUS      current
    DESCRIPTION
        "The value of tmnxPhysChassisDescription specifies the description of
         the physical chassis."
    DEFVAL      { ''H }
    ::= { tmnxPhysChassisEntry 10 }

tmnxPhysChassisMonitorFilterDoor OBJECT-TYPE
    SYNTAX      TruthValue
    MAX-ACCESS  read-write
    STATUS      current
    DESCRIPTION
        "The value of tmnxPhysChassisMonitorFilterDoor specifies whether or not
         a filter door open or missing condition will be monitored by the
         system."
    DEFVAL      { false }
    ::= { tmnxPhysChassisEntry 11 }

tmnxPhysChassisFilterDoorState   OBJECT-TYPE
    SYNTAX      INTEGER {
        unknown      (0),
        notMonitored (1),
        closed       (2),
        open         (3)
    }
    MAX-ACCESS  read-only
    STATUS      current
    DESCRIPTION
        "The value of tmnxPhysChassisFilterDoorState indicates the state of the
         filter door."
    ::= { tmnxPhysChassisEntry 12 }

tmnxChassisHwEventObjs           OBJECT IDENTIFIER ::= { tmnxChassisObjs 22 }

tmnxCardHwEventTable             OBJECT-TYPE
    SYNTAX      SEQUENCE OF TmnxCardHwEventEntry
    MAX-ACCESS  not-accessible
    STATUS      current
    DESCRIPTION
        "The tmnxCardHwEventTable maintains the basic information regarding
         events detected and reported on provisioned cards on the SROS series
         system."
    ::= { tmnxChassisHwEventObjs 1 }

tmnxCardHwEventEntry             OBJECT-TYPE
    SYNTAX      TmnxCardHwEventEntry
    MAX-ACCESS  not-accessible
    STATUS      current
    DESCRIPTION
        "A tmnxCardHwEventEntry row is created by the system whenever an event
         is detected and reported on either the tmnxCpmCardEntry or
         tmnxCardEntry as specified by the index of the row.  All records are
         cleared on card resets."
    INDEX       {
        tmnxChassisIndex,
        tmnxCardHwEventSlotNum,
        tmnxCardHwEventType,
        tmnxCardHwEventComplex
    }
    ::= { tmnxCardHwEventTable 1 }

TmnxCardHwEventEntry             ::= SEQUENCE
{
    tmnxCardHwEventSlotNum           TmnxSlotNum,
    tmnxCardHwEventType              INTEGER,
    tmnxCardHwEventComplex           Unsigned32,
    tmnxCardHwEventNumOccurrences    Counter32,
    tmnxCardHwEventLastOccurTime     TimeStamp
}

tmnxCardHwEventSlotNum           OBJECT-TYPE
    SYNTAX      TmnxSlotNum
    MAX-ACCESS  not-accessible
    STATUS      current
    DESCRIPTION
        "The value of tmnxCardHwEventSlotNum specifies the slot number of the
         card to which this event is detected."
    ::= { tmnxCardHwEventEntry 1 }

tmnxCardHwEventType              OBJECT-TYPE
    SYNTAX      INTEGER {
        tChipParity (1)
    }
    MAX-ACCESS  not-accessible
    STATUS      current
    DESCRIPTION
        "The value of tmnxCardHwEventType specifies the type of event detected
         and reported against the base card (or one of its complexes).

         The detectable and reportable events supported by this system include:
             tChipParity (1) - Parity error on the switch fabric interface."
    ::= { tmnxCardHwEventEntry 2 }

tmnxCardHwEventComplex           OBJECT-TYPE
    SYNTAX      Unsigned32 (1..12)
    MAX-ACCESS  not-accessible
    STATUS      current
    DESCRIPTION
        "The value of tmnxCardHwEventComplex specifies the card complex in
         which the event occurred. If the type of event raised does not exist
         on a complex, the value of '1' will be used."
    ::= { tmnxCardHwEventEntry 3 }

tmnxCardHwEventNumOccurrences    OBJECT-TYPE
    SYNTAX      Counter32
    MAX-ACCESS  read-only
    STATUS      current
    DESCRIPTION
        "The value of tmnxCardHwEventNumOccurrences indicates the number of
         times the specified tmnxCardHwEventType has occurred on the specified
         base card (or complex) since startup, last clear, or IOM reboot."
    ::= { tmnxCardHwEventEntry 4 }

tmnxCardHwEventLastOccurTime     OBJECT-TYPE
    SYNTAX      TimeStamp
    MAX-ACCESS  read-only
    STATUS      current
    DESCRIPTION
        "The value of tmnxCardHwEventLastOccurTime indicates the last time the
         specified tmnxCardHwEventNumOccurrences incremented."
    ::= { tmnxCardHwEventEntry 5 }

tmnxMdaHwEventTable              OBJECT-TYPE
    SYNTAX      SEQUENCE OF TmnxMdaHwEventEntry
    MAX-ACCESS  not-accessible
    STATUS      current
    DESCRIPTION
        "The tmnxMdaHwEventTable maintains the basic information regarding
         events detected and reported on provisioned MDAs on the SROS series
         system."
    ::= { tmnxChassisHwEventObjs 2 }

tmnxMdaHwEventEntry              OBJECT-TYPE
    SYNTAX      TmnxMdaHwEventEntry
    MAX-ACCESS  not-accessible
    STATUS      current
    DESCRIPTION
        "A tmnxMdaHwEventEntry row is created by the system whenever an event
         is detected and reported on the tmnxMDAEntry as specified by the index
         of the row. All records are cleared whenever a CPM, IOM or MDA is
         reset or unprovisioned."
    INDEX       {
        tmnxCardSlotNum,
        tmnxMDASlotNum,
        tmnxMdaHwEventType
    }
    ::= { tmnxMdaHwEventTable 1 }

TmnxMdaHwEventEntry              ::= SEQUENCE
{
    tmnxMdaHwEventType               INTEGER,
    tmnxMdaHwEventNumOccurrences     Counter32,
    tmnxMdaHwEventLastOccurTime      TimeStamp
}

tmnxMdaHwEventType               OBJECT-TYPE
    SYNTAX      INTEGER {
        ingrXplErr (1)
    }
    MAX-ACCESS  not-accessible
    STATUS      current
    DESCRIPTION
        "The value of tmnxMdaHwEventType specifies the type of event detected
         and reported against the MDA.

         The detectable and reportable events supported by this system include:
             ingrXplErr (1) - Ingress XPL Error"
    ::= { tmnxMdaHwEventEntry 1 }

tmnxMdaHwEventNumOccurrences     OBJECT-TYPE
    SYNTAX      Counter32
    MAX-ACCESS  read-only
    STATUS      current
    DESCRIPTION
        "The value of tmnxMdaHwEventNumOccurrences indicates the number of
         times the specified tmnxMdaHwEventType has occurred on the specified
         MDA since startup, last CPM clear, or IOM reboot."
    ::= { tmnxMdaHwEventEntry 2 }

tmnxMdaHwEventLastOccurTime      OBJECT-TYPE
    SYNTAX      TimeStamp
    MAX-ACCESS  read-only
    STATUS      current
    DESCRIPTION
        "The value of tmnxMdaHwEventLastOccurTime indicates the last time the
         specified tmnxMdaHwEventNumOccurrences incremented."
    ::= { tmnxMdaHwEventEntry 3 }

tmnxHwEventTable                 OBJECT-TYPE
    SYNTAX      SEQUENCE OF TmnxHwEventEntry
    MAX-ACCESS  not-accessible
    STATUS      current
    DESCRIPTION
        "The tmnxMdaHwEventTable maintains the basic information regarding
         events detected and reported on provisioned MDAs on the SROS series
         system."
    ::= { tmnxChassisHwEventObjs 3 }

tmnxHwEventEntry                 OBJECT-TYPE
    SYNTAX      TmnxHwEventEntry
    MAX-ACCESS  not-accessible
    STATUS      current
    DESCRIPTION
        "A tmnxHwEventEntry row can be created for each supported event that
         can be detected and reported on hardware.

         Rows are created and destroyed using tmnxHwEventRowStatus."
    INDEX       {
        tmnxChassisIndex,
        tmnxHwIndex,
        tmnxHwEventType
    }
    ::= { tmnxHwEventTable 1 }

TmnxHwEventEntry                 ::= SEQUENCE
{
    tmnxHwEventType                  TmnxHwEventType,
    tmnxHwEventRowStatus             RowStatus,
    tmnxHwEventAction                TmnxHwEventAction,
    tmnxHwEventNumOccurrences        Counter32,
    tmnxHwEventLastOccurTime         TimeStamp
}

tmnxHwEventType                  OBJECT-TYPE
    SYNTAX      TmnxHwEventType
    MAX-ACCESS  not-accessible
    STATUS      current
    DESCRIPTION
        "The value of tmnxHwEventType specifies the type of event detected and
         reported against this hardware."
    ::= { tmnxHwEventEntry 1 }

tmnxHwEventRowStatus             OBJECT-TYPE
    SYNTAX      RowStatus
    MAX-ACCESS  read-create
    STATUS      current
    DESCRIPTION
        "The value of tmnxHwEventRowStatus specifies the status of this row.

         It allows entries to be created and deleted in the tmnxHwEventTable."
    ::= { tmnxHwEventEntry 2 }

tmnxHwEventAction                OBJECT-TYPE
    SYNTAX      TmnxHwEventAction
    MAX-ACCESS  read-create
    STATUS      current
    DESCRIPTION
        "The value of tmnxHwEventAction specifies the action to be taken when
         event is detected."
    ::= { tmnxHwEventEntry 3 }

tmnxHwEventNumOccurrences        OBJECT-TYPE
    SYNTAX      Counter32
    MAX-ACCESS  read-only
    STATUS      current
    DESCRIPTION
        "The value of tmnxHwEventNumOccurrences indicates the number of times
         the specified tmnxHwEventType has occurred on the specified hardware
         since startup, last CPM clear, or IOM reboot."
    ::= { tmnxHwEventEntry 4 }

tmnxHwEventLastOccurTime         OBJECT-TYPE
    SYNTAX      TimeStamp
    MAX-ACCESS  read-only
    STATUS      current
    DESCRIPTION
        "The value of tmnxHwEventLastOccurTime indicates the last time the
         specified tmnxHwEventNumOccurrences incremented."
    ::= { tmnxHwEventEntry 5 }

tmnxChassisMgmtEthRedObjs        OBJECT IDENTIFIER ::= { tmnxChassisObjs 23 }

tmnxChassisMgmtEthRed            OBJECT-TYPE
    SYNTAX      TmnxEnabledDisabled
    MAX-ACCESS  read-write
    STATUS      current
    DESCRIPTION
        "The value of tmnxChassisMgmtEthRed specifies whether or not the
         management Ethernet port redundancy feature is enabled or disabled."
    DEFVAL      { disabled }
    ::= { tmnxChassisMgmtEthRedObjs 1 }

tmnxChassisMgmtEthRedRevertTime  OBJECT-TYPE
    SYNTAX      Unsigned32 (1..300)
    UNITS       "seconds"
    MAX-ACCESS  read-write
    STATUS      current
    DESCRIPTION
        "The value of tmnxChassisMgmtEthRedRevertTime specifies the amount of
         time the system will wait before reverting the standby CPM management
         Ethernet port to the active CPM after the active CPM management
         Ethernet port becomes operationally up."
    DEFVAL      { 5 }
    ::= { tmnxChassisMgmtEthRedObjs 2 }

tmnxChassisMgmtEthRedStandby     OBJECT-TYPE
    SYNTAX      TruthValue
    MAX-ACCESS  read-only
    STATUS      current
    DESCRIPTION
        "The value of tmnxChassisMgmtEthRedStandby indicates whether or not the
         management of the node is operating from the standby CPM's management
         Ethernet port."
    ::= { tmnxChassisMgmtEthRedObjs 3 }

tmnxPhysChassisObjs              OBJECT IDENTIFIER ::= { tmnxChassisObjs 24 }

tmnxPhysChassisFanTable          OBJECT-TYPE
    SYNTAX      SEQUENCE OF TmnxPhysChassisFanEntry
    MAX-ACCESS  not-accessible
    STATUS      current
    DESCRIPTION
        "The tmnxPhysChassisFanTable contains information about fan trays on
         the physical chassis.

         Rows are created/destroyed automatically by the system."
    ::= { tmnxPhysChassisObjs 1 }

tmnxPhysChassisFanEntry          OBJECT-TYPE
    SYNTAX      TmnxPhysChassisFanEntry
    MAX-ACCESS  not-accessible
    STATUS      current
    DESCRIPTION
        "The tmnxPhysChassisFanEntry contains information regarding a fan tray
         for the physical chassis."
    INDEX       {
        tmnxPhysChassisClass,
        tmnxPhysChassisNum,
        tmnxPhysChassisFanIndex
    }
    ::= { tmnxPhysChassisFanTable 1 }

TmnxPhysChassisFanEntry          ::= SEQUENCE
{
    tmnxPhysChassisFanIndex          Unsigned32,
    tmnxPhysChassisFanOperStatus     TmnxDeviceState,
    tmnxPhysChassisFanSpeed          INTEGER,
    tmnxPhysChassisFanRevision       INTEGER,
    tmnxPhysChassisFanSpeedPercent   Unsigned32,
    tmnxPhysChassisFanType           INTEGER,
    tmnxPhysChassisFanDirection      INTEGER
}

tmnxPhysChassisFanIndex          OBJECT-TYPE
    SYNTAX      Unsigned32 (1..31)
    MAX-ACCESS  not-accessible
    STATUS      current
    DESCRIPTION
        "The value of tmnxPhysChassisFanIndex specifies a unique value which
         identifies a specific fan tray in the physical chassis."
    ::= { tmnxPhysChassisFanEntry 1 }

tmnxPhysChassisFanOperStatus     OBJECT-TYPE
    SYNTAX      TmnxDeviceState
    MAX-ACCESS  read-only
    STATUS      current
    DESCRIPTION
        "The value of tmnxPhysChassisFanOperStatus indicates the current status
         of the fan tray in the physical chassis."
    ::= { tmnxPhysChassisFanEntry 2 }

tmnxPhysChassisFanSpeed          OBJECT-TYPE
    SYNTAX      INTEGER {
        notApplicable (0),
        unknown       (1),
        halfSpeed     (2),
        fullSpeed     (3)
    }
    MAX-ACCESS  read-only
    STATUS      obsolete
    DESCRIPTION
        "The value of tmnxPhysChassisFanSpeed indicates the speed that the fan
         in the physical chassis is operating at.

         This object was made obsolete in 15.0 and replaced with
         tmnxPhysChassisFanSpeedPercent."
    ::= { tmnxPhysChassisFanEntry 3 }

tmnxPhysChassisFanRevision       OBJECT-TYPE
    SYNTAX      INTEGER {
        unknown (0),
        fan1    (1),
        hfFan2  (2)
    }
    MAX-ACCESS  read-only
    STATUS      current
    DESCRIPTION
        "The value of tmnxPhysChassisFanRevision indicates the revision of the
         fan in the physical chassis.

         Values:
             unknown (0) - revision is unknown
             fan1    (1) - represents the original fan tray
             hfFan2  (2) - represents the high-flow fan tray; second revision"
    ::= { tmnxPhysChassisFanEntry 4 }

tmnxPhysChassisFanSpeedPercent   OBJECT-TYPE
    SYNTAX      Unsigned32 (0..100)
    UNITS       "percent"
    MAX-ACCESS  read-only
    STATUS      current
    DESCRIPTION
        "The value of tmnxPhysChassisFanSpeedPercent indicates the speed of the
         fan as a percentage of maximum speed."
    ::= { tmnxPhysChassisFanEntry 5 }

tmnxPhysChassisFanType           OBJECT-TYPE
    SYNTAX      INTEGER {
        chassis (1),
        pcm     (2)
    }
    MAX-ACCESS  read-only
    STATUS      current
    DESCRIPTION
        "The value of tmnxPhysChassisFanType indicates the type of fan tray is
         represented in this row.

         Values:
            chassis (1) - The fan tray is cooling the physical chassis
            pcm     (2) - The fan tray is cooling the Power Connection Modules (PCM)"
    ::= { tmnxPhysChassisFanEntry 6 }

tmnxPhysChassisFanDirection      OBJECT-TYPE
    SYNTAX      INTEGER {
        unknown     (0),
        frontToBack (1),
        backToFront (2),
        rightToLeft (3)
    }
    MAX-ACCESS  read-only
    STATUS      current
    DESCRIPTION
        "The value of tmnxPhysChassisFanDirection indicates the airflow
         direction of the fans equipped by the tray represented in this row."
    ::= { tmnxPhysChassisFanEntry 7 }

tmnxPhysChassisPowerSupplyTable  OBJECT-TYPE
    SYNTAX      SEQUENCE OF TmnxPhysChassisPowerSupplyEntry
    MAX-ACCESS  not-accessible
    STATUS      current
    DESCRIPTION
        "The tmnxPhysChassisPowerSupplyTable contains information about power
         supply trays, also known as PEMs (Power Entry Modules) in the physical
         chassis.

         Rows are created/destroyed automatically by the system."
    ::= { tmnxPhysChassisObjs 2 }

tmnxPhysChassisPowerSupplyEntry  OBJECT-TYPE
    SYNTAX      TmnxPhysChassisPowerSupplyEntry
    MAX-ACCESS  not-accessible
    STATUS      current
    DESCRIPTION
        "The tmnxPhysChassisPowerSupplyEntry contains information regarding a
         power supply tray in the physical chassis."
    INDEX       {
        tmnxPhysChassisClass,
        tmnxPhysChassisNum,
        tmnxPhysChassPowerSupId
    }
    ::= { tmnxPhysChassisPowerSupplyTable 1 }

TmnxPhysChassisPowerSupplyEntry  ::= SEQUENCE
{
    tmnxPhysChassPowerSupId          Unsigned32,
    tmnxPhysChassPowerSupACStatus    TmnxDeviceState,
    tmnxPhysChassPowerSupDCStatus    TmnxDeviceState,
    tmnxPhysChassPowerSupTempStatus  TmnxDeviceState,
    tmnxPhysChassPowerSupTempThrshld Integer32,
    tmnxPhysChassPowerSup1Status     TmnxDeviceState,
    tmnxPhysChassPowerSup2Status     TmnxDeviceState,
    tmnxPhysChassPowerSupAssignType  TmnxPowerSupAssignType,
    tmnxPhysChassPowerSupInputStatus TmnxDeviceState,
    tmnxPhysChassPowerSupOutptStatus TmnxDeviceState,
    tmnxPhysChassPowerSupPemType     TmnxChassisPemType,
    tmnxPhysChassPowerSupPemACRect   BITS,
    tmnxPhysChassPowerSupInFeedDown  BITS,
    tmnxPhysChassPowerSupFanDir      INTEGER,
    tmnxPhysChassPSFeedAInVolt       Integer32,
    tmnxPhysChassPSFeedBInVolt       Integer32,
    tmnxPhysChassPSFanOperStatus     TmnxDeviceState
}

tmnxPhysChassPowerSupId          OBJECT-TYPE
    SYNTAX      Unsigned32 (1..31)
    MAX-ACCESS  not-accessible
    STATUS      current
    DESCRIPTION
        "The value of tmnxPhysChassPowerSupId specifies a unique identifier
         index for a power supply in the physical chassis."
    ::= { tmnxPhysChassisPowerSupplyEntry 1 }

tmnxPhysChassPowerSupACStatus    OBJECT-TYPE
    SYNTAX      TmnxDeviceState
    MAX-ACCESS  read-only
    STATUS      current
    DESCRIPTION
        "The value of tmnxPhysChassPowerSupACStatus indicates the AC status of
         the power supply in the physical chassis.

         If the value is 'deviceStateOk (3)', the input AC voltage is within
         range. If the value is 'deviceStateFailed (4)', an AC voltage out of
         range condition has been detected. A value of 'deviceNotEquipped (2)'
         indicates that the AC power supply is not present."
    ::= { tmnxPhysChassisPowerSupplyEntry 2 }

tmnxPhysChassPowerSupDCStatus    OBJECT-TYPE
    SYNTAX      TmnxDeviceState
    MAX-ACCESS  read-only
    STATUS      current
    DESCRIPTION
        "The value of tmnxPhysChassPowerSupDCStatus indicates the DC status of
         the power supply in the physical chassis.

         If the value is 'deviceStateOk (3)', the output DC voltage is within
         range. If the value is 'deviceStateFailed (4)', a DC voltage out of
         range condition has been detected. A value of 'deviceNotEquipped (2)'
         indicates that the DC power supply is not present or the equipped
         power supply does not support the reporting of this status."
    ::= { tmnxPhysChassisPowerSupplyEntry 3 }

tmnxPhysChassPowerSupTempStatus  OBJECT-TYPE
    SYNTAX      TmnxDeviceState
    MAX-ACCESS  read-only
    STATUS      current
    DESCRIPTION
        "The value of tmnxPhysChassPowerSupTempStatus indicates the status of
         the power supply's temperature in the physical chassis.

         If the value is 'deviceStateOk (3)', the current temperature is within
         acceptable range. If the value is 'deviceStateFailed (4)', a
         temperature too high condition has been detected."
    ::= { tmnxPhysChassisPowerSupplyEntry 4 }

tmnxPhysChassPowerSupTempThrshld OBJECT-TYPE
    SYNTAX      Integer32
    UNITS       "degrees celsius"
    MAX-ACCESS  read-only
    STATUS      current
    DESCRIPTION
        "The value of tmnxPhysChassPowerSupTempThrshld indicates the
         temperature threshold in degrees celsius of the power supply in the
         physical chassis.

         When the temperature of the power supply raises above
         tmnxPhysChassPowerSupTempThrshld, a 'temperature too high' event will
         be generated."
    ::= { tmnxPhysChassisPowerSupplyEntry 5 }

tmnxPhysChassPowerSup1Status     OBJECT-TYPE
    SYNTAX      TmnxDeviceState
    MAX-ACCESS  read-only
    STATUS      current
    DESCRIPTION
        "The value of tmnxPhysChassPowerSup1Status indicates the overall status
         of the equipped power supply in the physical chassis.

         For AC multiple power supplies, this represents the overall status of
         the first power supply in the tray. For DC multiple power supplies,
         this represents the status of the first input feed. For any other
         type, this represents the overall status of the power supply.

         If the value is 'deviceStateOk (3)', then all monitored statuses are
         'deviceStateOk (3)'. A value of 'deviceStateFailed (4)' represents a
         condition where at least one monitored status is in a failed state."
    ::= { tmnxPhysChassisPowerSupplyEntry 6 }

tmnxPhysChassPowerSup2Status     OBJECT-TYPE
    SYNTAX      TmnxDeviceState
    MAX-ACCESS  read-only
    STATUS      current
    DESCRIPTION
        "The value of tmnxPhysChassPowerSup2Status indicates the overall status
         of the equipped power supply in the physical chassis.

         For AC multiple power supplies, this represents the overall status of
         the second power supply in the tray. For DC multiple power supplies,
         this represents the status of the second input feed. For any other
         type, this object is not applicable and set to 'deviceNotEquipped
         (2)'.

         If the value is 'deviceStateOk (3)', then all monitored statuses are
         'deviceStateOk (3)'. A value of 'deviceStateFailed (4)' represents a
         condition where at least one monitored status is in a failed state."
    ::= { tmnxPhysChassisPowerSupplyEntry 7 }

tmnxPhysChassPowerSupAssignType  OBJECT-TYPE
    SYNTAX      TmnxPowerSupAssignType
    MAX-ACCESS  read-write
    STATUS      current
    DESCRIPTION
        "The value of tmnxPhysChassPowerSupAssignType specifies the type of
         power supply that is assigned to the physical chassis. Based on the
         value assigned to this object, various power supply monitoring signals
         will be interpreted. For example, if a platform is provisioned to use
         DC power supplies, then the signal that indicates an AC power supply
         is missing can be ignored. The configuration of this object away from
         'default (4)' is required for proper generation of traps and LED
         management."
    ::= { tmnxPhysChassisPowerSupplyEntry 8 }

tmnxPhysChassPowerSupInputStatus OBJECT-TYPE
    SYNTAX      TmnxDeviceState
    MAX-ACCESS  read-only
    STATUS      current
    DESCRIPTION
        "The value of tmnxPhysChassPowerSupInputStatus indicates the status of
         the input voltage of the power supply in the physical chassis.

         If the value is 'deviceStateOk (3)', the input voltage of the power
         supply is within range. If the value is 'deviceStateFailed (4)', an
         input voltage out of range condition has been detected. A value of
         'deviceNotEquipped (2)' indicates that the power supply is not present
         in the physical chassis."
    ::= { tmnxPhysChassisPowerSupplyEntry 9 }

tmnxPhysChassPowerSupOutptStatus OBJECT-TYPE
    SYNTAX      TmnxDeviceState
    MAX-ACCESS  read-only
    STATUS      current
    DESCRIPTION
        "The value of tmnxPhysChassPowerSupOutptStatus indicates the status of
         the output voltage of the power supply in the physical chassis.

         If the value is 'deviceStateOk (3)', the output voltage of the power
         supply is within range. If the value is 'deviceStateFailed (4)', an
         output voltage out of range condition has been detected. A value of
         'deviceNotEquipped (2)' indicates that the power supply is not present
         in the physical chassis."
    ::= { tmnxPhysChassisPowerSupplyEntry 10 }

tmnxPhysChassPowerSupPemType     OBJECT-TYPE
    SYNTAX      TmnxChassisPemType
    MAX-ACCESS  read-only
    STATUS      current
    DESCRIPTION
        "The value of tmnxPhysChassPowerSupPemType indicates the Power Entry
         Module (PEM) type installed in the PEM slot for the physical chassis."
    ::= { tmnxPhysChassisPowerSupplyEntry 11 }

tmnxPhysChassPowerSupPemACRect   OBJECT-TYPE
    SYNTAX      BITS {
        acRect1 (0),
        acRect2 (1)
    }
    MAX-ACCESS  read-only
    STATUS      current
    DESCRIPTION
        "The value of tmnxPhysChassPowerSupPemACRect indicates which Power
         Entry Module AC rectifiers installed in the PEM slot are in a failed
         state or are missing for the physical chassis.

         Values:
            acRect1 (0) - the first PEM AC rectifier has failed or is missing
            acRect2 (1) - The second PEM AC rectifier has failed or is missing"
    ::= { tmnxPhysChassisPowerSupplyEntry 12 }

tmnxPhysChassPowerSupInFeedDown  OBJECT-TYPE
    SYNTAX      BITS {
        inputFeedA (0),
        inputFeedB (1)
    }
    MAX-ACCESS  read-only
    STATUS      current
    DESCRIPTION
        "The value of tmnxPhysChassPowerSupInFeedDown indicates which input
         feeds are not supplying power.

         Values:
            inputFeedA (0) - input feed A is not supplying power
            inputFeedB (1) - input feed B is not supplying power"
    ::= { tmnxPhysChassisPowerSupplyEntry 13 }

tmnxPhysChassPowerSupFanDir      OBJECT-TYPE
    SYNTAX      INTEGER {
        unknown     (0),
        frontToBack (1),
        backToFront (2)
    }
    MAX-ACCESS  read-only
    STATUS      current
    DESCRIPTION
        "The value of tmnxPhysChassPowerSupFanDir indicates the direction of
         the power supply's fan in the physical chassis.

         Values:
             unknown     (0) - fan direction is unknown
             frontToBack (1) - fan direction is from front of chassis to back
             backToFront (2) - fan direction is from back of chassis to front"
    ::= { tmnxPhysChassisPowerSupplyEntry 14 }

tmnxPhysChassPSFeedAInVolt       OBJECT-TYPE
    SYNTAX      Integer32
    MAX-ACCESS  read-only
    STATUS      current
    DESCRIPTION
        "The value of tmnxPhysChassPSFeedAInVolt indicates the input voltage,
         in millivolts (mV), of the power supply at input feed A."
    ::= { tmnxPhysChassisPowerSupplyEntry 15 }

tmnxPhysChassPSFeedBInVolt       OBJECT-TYPE
    SYNTAX      Integer32
    MAX-ACCESS  read-only
    STATUS      current
    DESCRIPTION
        "The value of tmnxPhysChassPSFeedBInVolt indicates the input voltage,
         in millivolts (mV), of the power supply at input feed B. If a second
         input feed is not applicable to this power supply, a value of '0' will
         be reported."
    ::= { tmnxPhysChassisPowerSupplyEntry 16 }

tmnxPhysChassPSFanOperStatus     OBJECT-TYPE
    SYNTAX      TmnxDeviceState
    MAX-ACCESS  read-only
    STATUS      current
    DESCRIPTION
        "The value of tmnxPhysChassPSFanOperStatus indicates the operational
         status of the fan element(s) present on the power supply."
    ::= { tmnxPhysChassisPowerSupplyEntry 17 }

tmnxPhysChassisPEQTableLastChg   OBJECT-TYPE
    SYNTAX      TimeStamp
    MAX-ACCESS  read-only
    STATUS      current
    DESCRIPTION
        "The value of tmnxPhysChassisPEQTableLastChg indicates the time, since
         system startup, that a row in the tmnxPhysChassisPEQTable last changed
         configuration."
    ::= { tmnxPhysChassisObjs 3 }

tmnxPhysChassisPEQTable          OBJECT-TYPE
    SYNTAX      SEQUENCE OF TmnxPhysChassisPEQEntry
    MAX-ACCESS  not-accessible
    STATUS      current
    DESCRIPTION
        "The tmnxPhysChassisPEQTable contains information about Power Equalizer
         type in the physical chassis.

         This table replaces tmnxChassisPEQTable in release 15.0 of SROS series
         systems."
    ::= { tmnxPhysChassisObjs 4 }

tmnxPhysChassisPEQEntry          OBJECT-TYPE
    SYNTAX      TmnxPhysChassisPEQEntry
    MAX-ACCESS  not-accessible
    STATUS      current
    DESCRIPTION
        "Each row entry represents a Nokia SROS series PEQ slot.

         Rows in this table are created by the agent at initialization and
         cannot be created or destroyed by SNMP Get or Set requests."
    INDEX       {
        tmnxPhysChassisClass,
        tmnxPhysChassisNum,
        tmnxPhysChassPowerSupId
    }
    ::= { tmnxPhysChassisPEQTable 1 }

TmnxPhysChassisPEQEntry          ::= SEQUENCE
{
    tmnxPhysChassisPEQLastChangeTime TimeStamp,
    tmnxPhysChassisPEQAssignedType   TmnxPEQType,
    tmnxPhysChassisPEQEquippedType   TmnxPEQType,
    tmnxPhysChassisPEQSupportedTypes TmnxPEQSuppType,
    tmnxPhysChassisPEQAvailableWatt  Unsigned32,
    tmnxPhysChassisPEQInputPowerMode Unsigned32
}

tmnxPhysChassisPEQLastChangeTime OBJECT-TYPE
    SYNTAX      TimeStamp
    MAX-ACCESS  read-only
    STATUS      current
    DESCRIPTION
        "The value of tmnxPhysChassisPEQLastChangeTime indicates the time,
         since system startup, that an object in this row changed
         configuration."
    ::= { tmnxPhysChassisPEQEntry 1 }

tmnxPhysChassisPEQAssignedType   OBJECT-TYPE
    SYNTAX      TmnxPEQType
    MAX-ACCESS  read-write
    STATUS      current
    DESCRIPTION
        "The value of tmnxPhysChassisPEQAssignedType specifies the
         administratively assigned (pre-provisioned) PEQ type defined in the
         tmnxPEQTypeTable that should occupy this PEQ slot in the chassis.  If
         tmnxPhysChassisPEQAssignedType has a value of 1 (unassigned), this slot
         has not yet been pre-provisioned."
    DEFVAL      { 1 }
    ::= { tmnxPhysChassisPEQEntry 2 }

tmnxPhysChassisPEQEquippedType   OBJECT-TYPE
    SYNTAX      TmnxPEQType
    MAX-ACCESS  read-only
    STATUS      current
    DESCRIPTION
        "The value of tmnxPhysChassisPEQEquippedType indicates the PEQ type of
         the PEQ that is physically inserted into this PEQ slot in the chassis.
         If the slot has been pre-provisioned, tmnxPhysChassisPEQAssignedType
         is not equal to 1 (unassigned), and the value of
         tmnxPhysChassisPEQEquippedType is not the same as
         tmnxPhysChassisPEQAssignedType, a mismatch alarm will be raised.

         A value of 0 indicates the PEQ type is not recognized by the SROS."
    ::= { tmnxPhysChassisPEQEntry 3 }

tmnxPhysChassisPEQSupportedTypes OBJECT-TYPE
    SYNTAX      TmnxPEQSuppType
    MAX-ACCESS  read-only
    STATUS      current
    DESCRIPTION
        "The value of tmnxPhysChassisPEQSupportedTypes is a bit-mask that
         indicates what PEQ types can be physically supported in this PEQ slot
         in this chassis."
    ::= { tmnxPhysChassisPEQEntry 4 }

tmnxPhysChassisPEQAvailableWatt  OBJECT-TYPE
    SYNTAX      Unsigned32
    UNITS       "watts"
    MAX-ACCESS  read-only
    STATUS      current
    DESCRIPTION
        "The value of tmnxPhysChassisPEQAvailableWatt indicates the reported
         available wattage of the PEQ."
    ::= { tmnxPhysChassisPEQEntry 5 }

tmnxPhysChassisPEQInputPowerMode OBJECT-TYPE
    SYNTAX      Unsigned32 (0 | 60 | 80)
    UNITS       "amperes"
    MAX-ACCESS  read-write
    STATUS      current
    DESCRIPTION
        "The value of tmnxPhysChassisPEQInputPowerMode specifies the input
         power mode of the PEQ.

         A value of zero indicates that the input power mode is not applicable
         for the PEQ. An SNMP SET request with a value of zero is not
         permitted."
    ::= { tmnxPhysChassisPEQEntry 6 }

tmnxPhysChassisPCMTableLastChg   OBJECT-TYPE
    SYNTAX      TimeStamp
    MAX-ACCESS  read-only
    STATUS      current
    DESCRIPTION
        "The value of tmnxPhysChassisPCMTableLastChg indicates the time, since
         system startup, that a row in the tmnxPhysChassisPCMTable last changed
         configuration."
    ::= { tmnxPhysChassisObjs 5 }

tmnxPhysChassisPCMTable          OBJECT-TYPE
    SYNTAX      SEQUENCE OF TmnxPhysChassisPCMEntry
    MAX-ACCESS  not-accessible
    STATUS      current
    DESCRIPTION
        "The tmnxPhysChassisPCMTable contains information about Power
         Connection Modules (PCM) in the physical chassis."
    ::= { tmnxPhysChassisObjs 6 }

tmnxPhysChassisPCMEntry          OBJECT-TYPE
    SYNTAX      TmnxPhysChassisPCMEntry
    MAX-ACCESS  not-accessible
    STATUS      current
    DESCRIPTION
        "Each row entry represents a Nokia SROS series PCM slot.

         Rows in this table are created by the agent at initialization and
         cannot be created or destroyed by SNMP Get or Set requests."
    INDEX       {
        tmnxPhysChassisClass,
        tmnxPhysChassisNum,
        tmnxPhysChassisPCMId
    }
    ::= { tmnxPhysChassisPCMTable 1 }

TmnxPhysChassisPCMEntry          ::= SEQUENCE
{
    tmnxPhysChassisPCMId             Unsigned32,
    tmnxPhysChassisPCMEntryLastChg   TimeStamp,
    tmnxPhysChassisPCMEquippedType   TmnxPCMType,
    tmnxPhysChassisPCMAssignedType   TmnxPCMType,
    tmnxPhysChassisPCMInFeedDown     BITS
}

tmnxPhysChassisPCMId             OBJECT-TYPE
    SYNTAX      Unsigned32 (1..31)
    MAX-ACCESS  not-accessible
    STATUS      current
    DESCRIPTION
        "The value of tmnxPhysChassisPCMId specifies a unique identifier index
         for a PCM in the physical chassis."
    ::= { tmnxPhysChassisPCMEntry 1 }

tmnxPhysChassisPCMEntryLastChg   OBJECT-TYPE
    SYNTAX      TimeStamp
    MAX-ACCESS  read-only
    STATUS      current
    DESCRIPTION
        "The value of tmnxPhysChassisPCMEntryLastChg indicates the time, since
         system startup, that an object in this row changed configuration."
    ::= { tmnxPhysChassisPCMEntry 2 }

tmnxPhysChassisPCMEquippedType   OBJECT-TYPE
    SYNTAX      TmnxPCMType
    MAX-ACCESS  read-only
    STATUS      current
    DESCRIPTION
        "The value of tmnxPhysChassisPCMEquippedType indicates the PCM type of
         the PCM that is physically inserted into the equivalent PEQ slot in
         the chassis.

         The following PEQ type(s) support PCM:

            apeq-dc-4275 (10)

         If the equipped PEQ does not have a type in this list, then the value
         of tmnxPhysChassisPCMEquippedType can only take on the values
         unassigned (1), or dual (2)."
    ::= { tmnxPhysChassisPCMEntry 3 }

tmnxPhysChassisPCMAssignedType   OBJECT-TYPE
    SYNTAX      TmnxPCMType
    MAX-ACCESS  read-write
    STATUS      current
    DESCRIPTION
        "The value of tmnxPhysChassisPCMAssignedType specifies the
         administratively assigned (pre-provisioned) PCM type that should
         occupy this PCM slot in the chassis. If tmnxPhysChassisPCMAssignedType
         has a value of unassigned (1), this slot has not yet been
         pre-provisioned.

         The following PEQ type(s) support PCM:

            apeq-dc-4275 (10)"
    DEFVAL      { unassigned }
    ::= { tmnxPhysChassisPCMEntry 4 }

tmnxPhysChassisPCMInFeedDown     OBJECT-TYPE
    SYNTAX      BITS {
        inputFeedA  (0),
        inputFeedB2 (1),
        inputFeedA2 (2),
        inputFeedB  (3)
    }
    MAX-ACCESS  read-only
    STATUS      current
    DESCRIPTION
        "The value of tmnxPhysChassisPCMInFeedDown indicates which input feeds
         are not supplying power.

         Values:
            inputFeedA  (0) - input feed A is not supplying power
            inputFeedB2 (1) - input feed B2 is not supplying power
            inputFeedA2 (2) - input feed A2 is not supplying power
            inputFeedB  (3) - input feed B is not supplying power"
    ::= { tmnxPhysChassisPCMEntry 5 }

tmnxPhysChassisPMTypeTable       OBJECT-TYPE
    SYNTAX      SEQUENCE OF TmnxPhysChassisPMTypeEntry
    MAX-ACCESS  not-accessible
    STATUS      current
    DESCRIPTION
        "The tmnxPhysChassisPMTypeTable has an entry for each Power Module (PM)
         type supported by the system. Some example PM types are:
         'apeq-dc-2000', 'apeq-ac-3000', 'ac-single', 'dc-multiple'."
    ::= { tmnxPhysChassisObjs 7 }

tmnxPhysChassisPMTypeEntry       OBJECT-TYPE
    SYNTAX      TmnxPhysChassisPMTypeEntry
    MAX-ACCESS  not-accessible
    STATUS      current
    DESCRIPTION
        "Each row entry represents an Nokia SROS series Power Module type. Rows
         in this table are created by the agent at initialization and cannot be
         created or destroyed by SNMP Set requests."
    INDEX       { tmnxPhysChassisPMTypeIndex }
    ::= { tmnxPhysChassisPMTypeTable 1 }

TmnxPhysChassisPMTypeEntry       ::= SEQUENCE
{
    tmnxPhysChassisPMTypeIndex       TmnxPMType,
    tmnxPhysChassisPMTypeName        TNamedItemOrEmpty,
    tmnxPhysChassisPMTypeDescription TItemDescription,
    tmnxPhysChassisPMTypeNumInFeed   Unsigned32
}

tmnxPhysChassisPMTypeIndex       OBJECT-TYPE
    SYNTAX      TmnxPMType
    MAX-ACCESS  not-accessible
    STATUS      current
    DESCRIPTION
        "The value of tmnxPhysChassisPMTypeIndex specifies the unique index
         which identifies the type of Nokia SROS series Power Module (PM)."
    ::= { tmnxPhysChassisPMTypeEntry 1 }

tmnxPhysChassisPMTypeName        OBJECT-TYPE
    SYNTAX      TNamedItemOrEmpty
    MAX-ACCESS  read-only
    STATUS      current
    DESCRIPTION
        "The value of tmnxPhysChassisPMTypeName indicates the administrative
         name that identifies the type of Nokia SROS series PM. This name
         string is used in CLI commands to specify a particular PM type."
    ::= { tmnxPhysChassisPMTypeEntry 2 }

tmnxPhysChassisPMTypeDescription OBJECT-TYPE
    SYNTAX      TItemDescription
    MAX-ACCESS  read-only
    STATUS      current
    DESCRIPTION
        "The value of tmnxPhysChassisPMTypeDescription indicates the detailed
         description of this Nokia SROS series PM type."
    ::= { tmnxPhysChassisPMTypeEntry 3 }

tmnxPhysChassisPMTypeNumInFeed   OBJECT-TYPE
    SYNTAX      Unsigned32
    MAX-ACCESS  read-only
    STATUS      current
    DESCRIPTION
        "The value of tmnxPhysChassisPMTypeNumInFeed indicates the number of
         input feeds that this PM type has."
    ::= { tmnxPhysChassisPMTypeEntry 4 }

tmnxPhysChassisPMTableLastChange OBJECT-TYPE
    SYNTAX      TimeStamp
    MAX-ACCESS  read-only
    STATUS      current
    DESCRIPTION
        "The value of tmnxPhysChassisPMTableLastChange indicates the time,
         since system startup, that a row in the tmnxPhysChassisPMTable last
         changed configuration."
    ::= { tmnxPhysChassisObjs 8 }

tmnxPhysChassisPMTable           OBJECT-TYPE
    SYNTAX      SEQUENCE OF TmnxPhysChassisPMEntry
    MAX-ACCESS  not-accessible
    STATUS      current
    DESCRIPTION
        "The tmnxPhysChassisPMTable contains information about Power Modules
         (PM)."
    ::= { tmnxPhysChassisObjs 9 }

tmnxPhysChassisPMEntry           OBJECT-TYPE
    SYNTAX      TmnxPhysChassisPMEntry
    MAX-ACCESS  not-accessible
    STATUS      current
    DESCRIPTION
        "Each row entry represents a Nokia SROS series PM slot.

         Rows in this table are created by the agent at initialization and
         cannot be created or destroyed by SNMP Get or Set requests."
    INDEX       { tmnxPowerModuleHwIndex }
    ::= { tmnxPhysChassisPMTable 1 }

TmnxPhysChassisPMEntry           ::= SEQUENCE
{
    tmnxPowerModuleHwIndex           TmnxHwIndex,
    tmnxPhysChassisPMEntryLastChange TimeStamp,
    tmnxPhysChassisPMAssignedType    TmnxPMType,
    tmnxPhysChassisPMEquippedType    TmnxPMType,
    tmnxPhysChassisPMSupportedTypes  TmnxPMSuppType,
    tmnxPhysChassisPMAvailableWatt   Unsigned32,
    tmnxPhysChassisPMOutputStatus    INTEGER,
    tmnxPhysChassisPMInputFeedDown   BITS,
    tmnxPhysChassisPMFeedAInVolt     Integer32,
    tmnxPhysChassisPMFeedBInVolt     Integer32
}

tmnxPowerModuleHwIndex           OBJECT-TYPE
    SYNTAX      TmnxHwIndex
    MAX-ACCESS  not-accessible
    STATUS      current
    DESCRIPTION
        "The value of tmnxPowerModuleHwIndex specifies a unique value which
         identifies the PM."
    ::= { tmnxPhysChassisPMEntry 1 }

tmnxPhysChassisPMEntryLastChange OBJECT-TYPE
    SYNTAX      TimeStamp
    MAX-ACCESS  read-only
    STATUS      current
    DESCRIPTION
        "The value of tmnxPhysChassisPMEntryLastChange indicates the time,
         since system startup, that an object in this row changed
         configuration."
    ::= { tmnxPhysChassisPMEntry 2 }

tmnxPhysChassisPMAssignedType    OBJECT-TYPE
    SYNTAX      TmnxPMType
    MAX-ACCESS  read-write
    STATUS      current
    DESCRIPTION
        "The value of tmnxPhysChassisPMAssignedType specifies the
         administratively assigned (provisioned) PM type defined in the
         tmnxPhysChassisPMTypeTable that should occupy this PM slot. If
         tmnxPhysChassisPMAssignedType has a value of 1 (unassigned), this slot
         has not yet been provisioned."
    DEFVAL      { 1 }
    ::= { tmnxPhysChassisPMEntry 3 }

tmnxPhysChassisPMEquippedType    OBJECT-TYPE
    SYNTAX      TmnxPMType
    MAX-ACCESS  read-only
    STATUS      current
    DESCRIPTION
        "The value of tmnxPhysChassisPMEquippedType indicates the PM type of
         the PM that is physically inserted into this PM slot. If the slot has
         been provisioned, and tmnxPhysChassisPMAssignedType is not equal to 1
         (unassigned), and the value of tmnxPhysChassisPMEquippedType is not
         the same as tmnxPhysChassisPMAssignedType, a mismatch alarm will be
         raised.

         A value of 0 indicates the PM type is not recognized by the SROS."
    ::= { tmnxPhysChassisPMEntry 4 }

tmnxPhysChassisPMSupportedTypes  OBJECT-TYPE
    SYNTAX      TmnxPMSuppType
    MAX-ACCESS  read-only
    STATUS      current
    DESCRIPTION
        "The value of tmnxPhysChassisPMSupportedTypes is a bit-mask that
         indicates what PM types can be physically supported in this PM slot."
    ::= { tmnxPhysChassisPMEntry 5 }

tmnxPhysChassisPMAvailableWatt   OBJECT-TYPE
    SYNTAX      Unsigned32
    UNITS       "watts"
    MAX-ACCESS  read-only
    STATUS      current
    DESCRIPTION
        "The value of tmnxPhysChassisPMAvailableWatt indicates the reported
         available wattage of the PM."
    ::= { tmnxPhysChassisPMEntry 6 }

tmnxPhysChassisPMOutputStatus    OBJECT-TYPE
    SYNTAX      INTEGER {
        unknown     (0),
        ok          (1),
        failed      (2),
        disabled    (3),
        notEquipped (4)
    }
    MAX-ACCESS  read-only
    STATUS      current
    DESCRIPTION
        "The value of tmnxPhysChassisPMOutputStatus indicates the status of the
         PM output."
    ::= { tmnxPhysChassisPMEntry 7 }

tmnxPhysChassisPMInputFeedDown   OBJECT-TYPE
    SYNTAX      BITS {
        inputFeedA (0),
        inputFeedB (1)
    }
    MAX-ACCESS  read-only
    STATUS      current
    DESCRIPTION
        "The value of tmnxPhysChassisPMInputFeedDown indicates which input
         feeds are not supplying power.

         Values:
            inputFeedA (0) - input feed A is not supplying power
            inputFeedB (1) - input feed B is not supplying power"
    ::= { tmnxPhysChassisPMEntry 8 }

tmnxPhysChassisPMFeedAInVolt     OBJECT-TYPE
    SYNTAX      Integer32
    MAX-ACCESS  read-only
    STATUS      current
    DESCRIPTION
        "The value of tmnxPhysChassisPMFeedAInVolt indicates the input voltage
         of the power module from input feed A."
    ::= { tmnxPhysChassisPMEntry 9 }

tmnxPhysChassisPMFeedBInVolt     OBJECT-TYPE
    SYNTAX      Integer32
    MAX-ACCESS  read-only
    STATUS      current
    DESCRIPTION
        "The value of tmnxPhysChassisPMFeedBInVolt indicates the input voltage
         of the power module from input feed B. If a second feed is not
         applicable to this power module, a value of '0' will be reported."
    ::= { tmnxPhysChassisPMEntry 10 }

tmnxBluetoothTableLastChange     OBJECT-TYPE
    SYNTAX      TimeStamp
    MAX-ACCESS  read-only
    STATUS      obsolete
    DESCRIPTION
        "The value of tmnxBluetoothTableLastChange indicates the time, since
         system startup, when tmnxBluetoothTable last changed configuration."
    ::= { tmnxChassisObjs 25 }

tmnxBluetoothTable               OBJECT IDENTIFIER ::= { tmnxChassisObjs 26 }

tmnxBluetoothPasskey             OBJECT-TYPE
    SYNTAX      DisplayString (SIZE (6))
    MAX-ACCESS  read-write
    STATUS      obsolete
    DESCRIPTION
        "The value of tmnxBluetoothPasskey specifies the Bluetooth pairing
         passkey for the Bluetooth module(s)."
    DEFVAL      { "123456" }
    ::= { tmnxBluetoothTable 1 }

tmnxBluetoothAdvertisingTimeout  OBJECT-TYPE
    SYNTAX      Unsigned32 (0 | 30..3600)
    UNITS       "seconds"
    MAX-ACCESS  read-write
    STATUS      obsolete
    DESCRIPTION
        "The value of tmnxBluetoothAdvertisingTimeout specifies the amount of
         time the Bluetooth module(s) will spend advertising after a button
         press."
    DEFVAL      { 30 }
    ::= { tmnxBluetoothTable 2 }

tmnxBluetoothPowerState          OBJECT-TYPE
    SYNTAX      INTEGER {
        off               (0),
        enabled-manual    (1),
        enabled-automatic (2)
    }
    MAX-ACCESS  read-write
    STATUS      obsolete
    DESCRIPTION
        "The value of tmnxBluetoothPowerState specifies the power state of the
         Bluetooth Bluetooth module(s). The states are defined as follows:

            off (0)                 - The Bluetooth module(s) are disabled.
            enabled-manual (1)      - The Bluetooth module(s) are enabled, but not
                                      automatically advertising.
            enabled-automatic (2)   - The Bluetooth module(s) are enabled and
                                      automatically advertising."
    DEFVAL      { off }
    ::= { tmnxBluetoothTable 3 }

tmnxBluetoothPairingButton       OBJECT-TYPE
    SYNTAX      TmnxEnabledDisabled
    MAX-ACCESS  read-write
    STATUS      obsolete
    DESCRIPTION
        "The value of tmnxBluetoothPairingButton specifies whether the
         Bluetooth pairing button on the Bluetooth module(s) are enabled (1) or
         disabled (2)."
    DEFVAL      { disabled }
    ::= { tmnxBluetoothTable 4 }

tmnxBluetoothDeviceTableLastChg  OBJECT-TYPE
    SYNTAX      TimeStamp
    MAX-ACCESS  read-only
    STATUS      obsolete
    DESCRIPTION
        "The value of tmnxBluetoothDeviceTableLastChg indicates the time, since
         system startup, when tmnxBluetoothDeviceTable last changed
         configuration."
    ::= { tmnxChassisObjs 27 }

tmnxBluetoothDeviceTable         OBJECT-TYPE
    SYNTAX      SEQUENCE OF TmnxBluetoothDeviceEntry
    MAX-ACCESS  not-accessible
    STATUS      obsolete
    DESCRIPTION
        "The tmnxBluetoothDeviceTable contains information regarding the
         Bluetooth capable devices that are allowed to connect with the system."
    ::= { tmnxChassisObjs 28 }

tmnxBluetoothDeviceEntry         OBJECT-TYPE
    SYNTAX      TmnxBluetoothDeviceEntry
    MAX-ACCESS  not-accessible
    STATUS      obsolete
    DESCRIPTION
        "Each row entry represents a Bluetooth capable device that is allowed
         to connect with the system.

         Rows are created and destroyed using tmnxBluetoothDeviceRowStatus."
    INDEX       { tmnxBluetoothDeviceMacAddress }
    ::= { tmnxBluetoothDeviceTable 1 }

TmnxBluetoothDeviceEntry         ::= SEQUENCE
{
    tmnxBluetoothDeviceMacAddress    MacAddress,
    tmnxBluetoothDeviceRowStatus     RowStatus,
    tmnxBluetoothDeviceEntryLastChg  TimeStamp,
    tmnxBluetoothDeviceDescription   TItemDescription
}

tmnxBluetoothDeviceMacAddress    OBJECT-TYPE
    SYNTAX      MacAddress
    MAX-ACCESS  not-accessible
    STATUS      obsolete
    DESCRIPTION
        "The value of tmnxBluetoothDeviceMacAddress specifies the MAC address
         of the Bluetooth capable client device that is allowed to connect with
         the system."
    ::= { tmnxBluetoothDeviceEntry 1 }

tmnxBluetoothDeviceRowStatus     OBJECT-TYPE
    SYNTAX      RowStatus
    MAX-ACCESS  read-create
    STATUS      obsolete
    DESCRIPTION
        "The value of tmnxBluetoothDeviceRowStatus specifies the status of this
         row.

         It allows entries to be created and deleted in the
         tmnxBluetoothDeviceTable."
    ::= { tmnxBluetoothDeviceEntry 2 }

tmnxBluetoothDeviceEntryLastChg  OBJECT-TYPE
    SYNTAX      TimeStamp
    MAX-ACCESS  read-only
    STATUS      obsolete
    DESCRIPTION
        "The value of tmnxBluetoothDeviceEntryLastChg indicates the time, since
         system startup, that the configuration of the row was last modified."
    ::= { tmnxBluetoothDeviceEntry 3 }

tmnxBluetoothDeviceDescription   OBJECT-TYPE
    SYNTAX      TItemDescription
    MAX-ACCESS  read-create
    STATUS      obsolete
    DESCRIPTION
        "The value of tmnxBluetoothDeviceDescription specifies the description
         of the Bluetooth capable client device that is allowed to connect with
         the system."
    DEFVAL      { ''H }
    ::= { tmnxBluetoothDeviceEntry 4 }

tmnxBluetoothModuleTableLastChg  OBJECT-TYPE
    SYNTAX      TimeStamp
    MAX-ACCESS  read-only
    STATUS      obsolete
    DESCRIPTION
        "The value of tmnxBluetoothModuleTableLastChg indicates the time, since
         system startup, when tmnxBluetoothModuleTable last changed
         configuration."
    ::= { tmnxChassisObjs 29 }

tmnxBluetoothModuleTable         OBJECT-TYPE
    SYNTAX      SEQUENCE OF TmnxBluetoothModuleEntry
    MAX-ACCESS  not-accessible
    STATUS      obsolete
    DESCRIPTION
        "The tmnxBluetoothModuleTable contains information regarding the
         Bluetooth modules in the system."
    ::= { tmnxChassisObjs 30 }

tmnxBluetoothModuleEntry         OBJECT-TYPE
    SYNTAX      TmnxBluetoothModuleEntry
    MAX-ACCESS  not-accessible
    STATUS      obsolete
    DESCRIPTION
        "Each row entry represents a Bluetooth module in the system.

         Rows in this table are created by the agent at initialization and
         cannot be created or destroyed by SNMP Set requests."
    INDEX       { tmnxCpmCardSlotNum }
    ::= { tmnxBluetoothModuleTable 1 }

TmnxBluetoothModuleEntry         ::= SEQUENCE
{
    tmnxBluetoothModuleEntryLastChg  TimeStamp,
    tmnxBluetoothModuleCfgIdentifier DisplayString,
    tmnxBluetoothModuleIdentifier    DisplayString,
    tmnxBluetoothModuleConnected     TruthValue,
    tmnxBluetoothModuleConnectedMac  MacAddress
}

tmnxBluetoothModuleEntryLastChg  OBJECT-TYPE
    SYNTAX      TimeStamp
    MAX-ACCESS  read-only
    STATUS      obsolete
    DESCRIPTION
        "The value of tmnxBluetoothModuleEntryLastChg indicates the time, since
         system startup, that the configuration of the row was last modified."
    ::= { tmnxBluetoothModuleEntry 1 }

tmnxBluetoothModuleCfgIdentifier OBJECT-TYPE
    SYNTAX      DisplayString (SIZE (0|1..32))
    MAX-ACCESS  read-write
    STATUS      obsolete
    DESCRIPTION
        "The value of tmnxBluetoothModuleCfgIdentifier specifies the identifier
         of the Bluetooth module. This is the identifier which is advertised to
         Bluetooth capable devices when they attempt to pair/connect with the
         module. If this object is set to its default value, then the value
         indicated by tmnxBluetoothModuleIdentifier is advertised to bluetooth
         capable devices."
    DEFVAL      { ''H }
    ::= { tmnxBluetoothModuleEntry 2 }

tmnxBluetoothModuleIdentifier    OBJECT-TYPE
    SYNTAX      DisplayString (SIZE (0|1..32))
    MAX-ACCESS  read-only
    STATUS      obsolete
    DESCRIPTION
        "The value of tmnxBluetoothModuleIdentifier indicates the identifier of
         the Bluetooth module, determined by the system. This is the identifier
         which is advertised to Bluetooth capable devices when they attempt to
         pair/connect with the module, unless a value for
         tmnxBluetoothModuleCfgIdentifier has been set."
    ::= { tmnxBluetoothModuleEntry 3 }

tmnxBluetoothModuleConnected     OBJECT-TYPE
    SYNTAX      TruthValue
    MAX-ACCESS  read-only
    STATUS      obsolete
    DESCRIPTION
        "The value of tmnxBluetoothModuleConnected indicates whether the
         Bluetooth module is currently connected to a remote Bluetooth client
         device. If 'true', then the remote client device MAC address will be
         indicated by the value of tmnxBluetoothModuleConnectedMac"
    ::= { tmnxBluetoothModuleEntry 4 }

tmnxBluetoothModuleConnectedMac  OBJECT-TYPE
    SYNTAX      MacAddress
    MAX-ACCESS  read-only
    STATUS      obsolete
    DESCRIPTION
        "The value of tmnxBluetoothModuleConnectedMac indicates the MAC address
         of the remote Bluetooth client device. This value is only valid in the
         value of tmnxBluetoothModuleConnected is set to 'true'."
    ::= { tmnxBluetoothModuleEntry 5 }

tmnxChassisPowerMgmtStatsTable   OBJECT-TYPE
    SYNTAX      SEQUENCE OF TmnxChassisPowerMgmtStatsEntry
    MAX-ACCESS  not-accessible
    STATUS      current
    DESCRIPTION
        "The tmnxChassisPowerMgmtStatsTable specifies power statistics per
         power-zone on the SROS series system."
    ::= { tmnxChassisObjs 31 }

tmnxChassisPowerMgmtStatsEntry   OBJECT-TYPE
    SYNTAX      TmnxChassisPowerMgmtStatsEntry
    MAX-ACCESS  not-accessible
    STATUS      current
    DESCRIPTION
        "Each row in the tmnxChassisPowerMgmtStatsTable represents a managed
         power-zone on an SROS series system.

         Rows in this table are created by the agent at initialization and
         cannot be created or destroyed by SNMP Get or Set requests."
    INDEX       {
        tmnxChassisIndex,
        tmnxChassisPwrMgmtZone
    }
    ::= { tmnxChassisPowerMgmtStatsTable 1 }

TmnxChassisPowerMgmtStatsEntry   ::= SEQUENCE
{
    tmnxChassisPwrMgmtPeakPower      Unsigned32,
    tmnxChassisPwrMgmtReservedPower  Unsigned32,
    tmnxChassisPwrMgmtRqdRestPower   Integer32,
    tmnxChassisPwrMgmtUtilRestPower  Integer32,
    tmnxChassisPwrMgmtOperSafetyLvl  Unsigned32,
    tmnxChassisPwrMgmtOperSafetyAlrt Unsigned32,
    tmnxChassisPwrMgmtActiveConds    BITS,
    tmnxChassisPwrMgmtTotalWattage   Unsigned32,
    tChassisPwrMgmtLowPwrFabOprState TmnxOperState,
    tChassisPwrMgmtLowPwrFabLstChgd  TimeStamp
}

tmnxChassisPwrMgmtPeakPower      OBJECT-TYPE
    SYNTAX      Unsigned32
    UNITS       "watts"
    MAX-ACCESS  read-only
    STATUS      current
    DESCRIPTION
        "The value of tmnxChassisPwrMgmtPeakPower indicates the maximum power,
         in Watts (W), consumed by the power zone."
    ::= { tmnxChassisPowerMgmtStatsEntry 1 }

tmnxChassisPwrMgmtReservedPower  OBJECT-TYPE
    SYNTAX      Unsigned32
    UNITS       "watts"
    MAX-ACCESS  read-only
    STATUS      current
    DESCRIPTION
        "The value of tmnxChassisPwrMgmtReservedPower indicates the greatest
         rated power, in Watts (W), among equipped power supplies."
    ::= { tmnxChassisPowerMgmtStatsEntry 2 }

tmnxChassisPwrMgmtRqdRestPower   OBJECT-TYPE
    SYNTAX      Integer32
    UNITS       "watts"
    MAX-ACCESS  read-only
    STATUS      current
    DESCRIPTION
        "The value of tmnxChassisPwrMgmtRqdRestPower indicates the difference
         between the power required by the system and its configured reserved
         power threshold."
    ::= { tmnxChassisPowerMgmtStatsEntry 3 }

tmnxChassisPwrMgmtUtilRestPower  OBJECT-TYPE
    SYNTAX      Integer32
    UNITS       "watts"
    MAX-ACCESS  read-only
    STATUS      current
    DESCRIPTION
        "The value of tmnxChassisPwrMgmtUtilRestPower indicates the difference
         between the power utilized by the system and its configured reserved
         power threshold."
    ::= { tmnxChassisPowerMgmtStatsEntry 4 }

tmnxChassisPwrMgmtOperSafetyLvl  OBJECT-TYPE
    SYNTAX      Unsigned32
    UNITS       "watts"
    MAX-ACCESS  read-only
    STATUS      current
    DESCRIPTION
        "The value of tmnxChassisPwrMgmtOperSafetyLvl indicates the operational
         safety level."
    ::= { tmnxChassisPowerMgmtStatsEntry 5 }

tmnxChassisPwrMgmtOperSafetyAlrt OBJECT-TYPE
    SYNTAX      Unsigned32
    UNITS       "watts"
    MAX-ACCESS  read-only
    STATUS      current
    DESCRIPTION
        "The value of tmnxChassisPwrMgmtOperSafetyAlrt indicates the
         operational safety alert."
    ::= { tmnxChassisPowerMgmtStatsEntry 6 }

tmnxChassisPwrMgmtActiveConds    OBJECT-TYPE
    SYNTAX      BITS {
        capacityExceeded (0),
        lostCapacity     (1),
        insufCapacity    (2),
        overload         (3),
        safetyAlert      (4),
        safetyLevel      (5)
    }
    MAX-ACCESS  read-only
    STATUS      current
    DESCRIPTION
        "The value of tmnxChassisPwrMgmtActiveConds indicates the active
         conditions present on a given power zone. When the bit is set, the
         condition is active.

         Possible values include:
            capacityExceeded (0) - a device in the power-zone requires power to
                boot, but there is insufficient capacity to support it
            lostCapacity     (1) - system power capacity is insufficient to
                satisfy the safety level while maintaining any applicable
                power reserve
            insufCapacity    (2) - the provisioned capacity of the power-zone can
                not support the requirements of the system and provisioned equipment,
                while maintaining any applicable power reserve
            overload         (3) - the system power capacity is insufficient to power
                essential equipment while maintaining any applicable power reserve.
            safetyAlert      (4) - the system power capacity has dropped below the
                safety alert threshold configured by tmnxChassisPwrMgmtSafetyAlert
            safetyLevel      (5) - the peak power consumption has exceeded the safety
                level threshold configured by tmnxChassisPwrMgmtSafetyLevel"
    ::= { tmnxChassisPowerMgmtStatsEntry 7 }

tmnxChassisPwrMgmtTotalWattage   OBJECT-TYPE
    SYNTAX      Unsigned32
    UNITS       "milliwatts"
    MAX-ACCESS  read-only
    STATUS      current
    DESCRIPTION
        "The value of tmnxChassisPwrMgmtTotalWattage indicates the current
         wattage in use by all the managed hardware components in the power
         zone. The value is in units of milli-Watts (mW)"
    ::= { tmnxChassisPowerMgmtStatsEntry 8 }

tChassisPwrMgmtLowPwrFabOprState OBJECT-TYPE
    SYNTAX      TmnxOperState
    MAX-ACCESS  read-only
    STATUS      current
    DESCRIPTION
        "The value of tChassisPwrMgmtLowPwrFabOprState indicates the low power
         switch fabric mode operational status."
    ::= { tmnxChassisPowerMgmtStatsEntry 9 }

tChassisPwrMgmtLowPwrFabLstChgd  OBJECT-TYPE
    SYNTAX      TimeStamp
    MAX-ACCESS  read-only
    STATUS      current
    DESCRIPTION
        "The value of tChassisPwrMgmtLowPwrFabLstChgd indicates the date and
         time when the low power switch fabric mode operational status last
         changed."
    ::= { tmnxChassisPowerMgmtStatsEntry 10 }

tChassisIxrResourceTable         OBJECT-TYPE
    SYNTAX      SEQUENCE OF TChassisIxrResourceEntry
    MAX-ACCESS  not-accessible
    STATUS      current
    DESCRIPTION
        "The tChassisIxrResourceTable contains information about chassis
         resource utilization for resources specific to the Nokia IXR systems."
    ::= { tmnxChassisObjs 32 }

tChassisIxrResourceEntry         OBJECT-TYPE
    SYNTAX      TChassisIxrResourceEntry
    MAX-ACCESS  not-accessible
    STATUS      current
    DESCRIPTION
        "Each row in the tChassisIxrResourceEntry contains information about
         resource utilization on the chassis specified by the indices.

         Rows in this table are created by the system and cannot be created or
         destroyed by SNMP Get or Set requests."
    INDEX       { tmnxChassisIndex }
    ::= { tChassisIxrResourceTable 1 }

TChassisIxrResourceEntry         ::= SEQUENCE
{
    tChassisIxrResCommonLifTotal     Unsigned32,
    tChassisIxrResCommonLifAlloc     Unsigned32,
    tChassisIxrResCommonLifFree      Unsigned32,
    tChassisIxrResArpLifTotal        Unsigned32,
    tChassisIxrResArpLifAlloc        Unsigned32,
    tChassisIxrResArpLifFree         Unsigned32,
    tChassisIxrResMplsLifTotal       Unsigned32,
    tChassisIxrResMplsLifAlloc       Unsigned32,
    tChassisIxrResMplsLifFree        Unsigned32,
    tChassisIxrResL3VsiRifTotal      Unsigned32,
    tChassisIxrResL3VsiRifAlloc      Unsigned32,
    tChassisIxrResL3VsiRifFree       Unsigned32,
    tChassisIxrResFecUnpairedTotal   Unsigned32,
    tChassisIxrResFecUnpairedAlloc   Unsigned32,
    tChassisIxrResFecUnpairedFree    Unsigned32,
    tChassisIxrResFecPairedTotal     Unsigned32,
    tChassisIxrResFecPairedAlloc     Unsigned32,
    tChassisIxrResFecPairedFree      Unsigned32,
    tChassisIxrResOamLmCtrTotal      Unsigned32,
    tChassisIxrResOamLmCtrAlloc      Unsigned32,
    tChassisIxrResOamLmCtrFree       Unsigned32,
    tChassisIxrResAcLifTotal         Unsigned32,
    tChassisIxrResAcLifAlloc         Unsigned32,
    tChassisIxrResAcLifFree          Unsigned32,
    tChassisIxrResMplsNhlfeLifTotal  Unsigned32,
    tChassisIxrResMplsNhlfeLifAlloc  Unsigned32,
    tChassisIxrResMplsNhlfeLifFree   Unsigned32,
    tChassisIxrResBgpLblRtLifTotal   Unsigned32,
    tChassisIxrResBgpLblRtLifAlloc   Unsigned32,
    tChassisIxrResBgpLblRtLifFree    Unsigned32,
    tChassisIxrResSdpBndMplsLifTotal Unsigned32,
    tChassisIxrResSdpBndMplsLifAlloc Unsigned32,
    tChassisIxrResSdpBndMplsLifFree  Unsigned32,
    tChassisIxrResSdpBndGreLifTotal  Unsigned32,
    tChassisIxrResSdpBndGreLifAlloc  Unsigned32,
    tChassisIxrResSdpBndGreLifFree   Unsigned32,
    tChassisIxrResSsidLifTotal       Unsigned32,
    tChassisIxrResSsidLifAlloc       Unsigned32,
    tChassisIxrResSsidLifFree        Unsigned32,
    tChassisIxrResSrv6TunnelLifTotal Unsigned32,
    tChassisIxrResSrv6TunnelLifAlloc Unsigned32,
    tChassisIxrResSrv6TunnelLifFree  Unsigned32,
    tChassisIxrResL2ServiceTotal     Unsigned32,
    tChassisIxrResL2ServiceAlloc     Unsigned32,
    tChassisIxrResL2ServiceFree      Unsigned32,
    tChassisIxrResStationIdTotal     Unsigned32,
    tChassisIxrResStationIdAlloc     Unsigned32,
    tChassisIxrResStationIdFree      Unsigned32,
    tChassisIxrResVxlanLifTotal      Unsigned32,
    tChassisIxrResVxlanLifAlloc      Unsigned32,
    tChassisIxrResVxlanLifFree       Unsigned32
}

tChassisIxrResCommonLifTotal     OBJECT-TYPE
    SYNTAX      Unsigned32
    MAX-ACCESS  read-only
    STATUS      current
    DESCRIPTION
        "The value of the object tChassisIxrResCommonLifTotal indicates the
         maximum number of shared Common LIF entries on this chassis.

         Common LIF pool is used by variety of applications including BGP-LU,
         SAPs, SDP-Bindings, EVPN Service, IP interfaces, RTM, Sync/PTP and
         BFD.

         Total allocatable is typically platform hardware independent and is a
         representation of Control Plane allocation."
    ::= { tChassisIxrResourceEntry 1 }

tChassisIxrResCommonLifAlloc     OBJECT-TYPE
    SYNTAX      Unsigned32
    MAX-ACCESS  read-only
    STATUS      current
    DESCRIPTION
        "The value of the object tChassisIxrResCommonLifAlloc indicates the
         number of shared Common LIF entries that are currently in use on this
         chassis.

         Common LIF pool is used by variety of applications including BGP-LU,
         SAPs, SDP-Bindings, EVPN Service, IP interfaces, RTM, Sync/PTP and
         BFD.

         Total allocatable is typically platform hardware independent and is a
         representation of Control Plane allocation."
    ::= { tChassisIxrResourceEntry 2 }

tChassisIxrResCommonLifFree      OBJECT-TYPE
    SYNTAX      Unsigned32
    MAX-ACCESS  read-only
    STATUS      current
    DESCRIPTION
        "The value of the object tChassisIxrResCommonLifFree indicates the
         number of free shared Common LIF entries that are currently available
         on this chassis.

         Common LIF pool is used by variety of applications including BGP-LU,
         SAPs, SDP-Bindings, EVPN Service, IP interfaces, RTM, Sync/PTP and
         BFD.

         Total allocatable is typically platform hardware independent and is a
         representation of Control Plane allocation."
    ::= { tChassisIxrResourceEntry 3 }

tChassisIxrResArpLifTotal        OBJECT-TYPE
    SYNTAX      Unsigned32
    MAX-ACCESS  read-only
    STATUS      current
    DESCRIPTION
        "The value of the object tChassisIxrResArpLifTotal indicates the
         maximum number of LIF entries for ARP and ND on this chassis.

         Every IPv4 and IPv6 IP-MAC resolution, ARP and ND respectively
         requires an ARP LIF entry.

         Total allocatable is typically platform hardware independent and is a
         representation of Control Plane allocation."
    ::= { tChassisIxrResourceEntry 4 }

tChassisIxrResArpLifAlloc        OBJECT-TYPE
    SYNTAX      Unsigned32
    MAX-ACCESS  read-only
    STATUS      current
    DESCRIPTION
        "The value of the object tChassisIxrResArpLifAlloc indicates the number
         of LIF entries that are currently in use by ARP and ND on this
         chassis.

         Every IPv4 and IPv6 IP-MAC resolution, ARP and ND respectively
         requires an ARP LIF entry.

         Total allocatable is typically platform hardware independent and is a
         representation of Control Plane allocation."
    ::= { tChassisIxrResourceEntry 5 }

tChassisIxrResArpLifFree         OBJECT-TYPE
    SYNTAX      Unsigned32
    MAX-ACCESS  read-only
    STATUS      current
    DESCRIPTION
        "The value of the object tChassisIxrResArpLifFree indicates the number
         of free LIF entries that are currently available for ARP and ND on
         this chassis.

         Every IPv4 and IPv6 IP-MAC resolution, ARP and ND respectively
         requires an ARP LIF entry.

         Total allocatable is typically platform hardware independent and is a
         representation of Control Plane allocation."
    ::= { tChassisIxrResourceEntry 6 }

tChassisIxrResMplsLifTotal       OBJECT-TYPE
    SYNTAX      Unsigned32
    MAX-ACCESS  read-only
    STATUS      current
    DESCRIPTION
        "The value of the object tChassisIxrResMplsLifTotal indicates the
         maximum number of LIF entries for Transport tunnel use cases on this
         chassis.

         BGP-LU, RSVP-TE LSPs, LDP, SR Tree SID and GRE encap SDPs are among
         the tunneling options that require an entry in MPLS LIF table.

         Total allocatable is typically platform hardware independent and is a
         representation of Control Plane allocation."
    ::= { tChassisIxrResourceEntry 7 }

tChassisIxrResMplsLifAlloc       OBJECT-TYPE
    SYNTAX      Unsigned32
    MAX-ACCESS  read-only
    STATUS      current
    DESCRIPTION
        "The value of the object tChassisIxrResMplsLifAlloc indicates the
         number of free LIF entries that are currently in use by Transport
         tunnel use cases on this chassis.

         BGP-LU, RSVP-TE LSPs, LDP, SR Tree SID and GRE encap SDPs are among
         the tunneling options that require an entry in MPLS LIF table.

         Total allocatable is typically platform hardware independent and is a
         representation of Control Plane allocation."
    ::= { tChassisIxrResourceEntry 8 }

tChassisIxrResMplsLifFree        OBJECT-TYPE
    SYNTAX      Unsigned32
    MAX-ACCESS  read-only
    STATUS      current
    DESCRIPTION
        "The value of the object tChassisIxrResMplsLifFree indicates the number
         of free LIF entries that are currently available for Transport tunnel
         use cases on this chassis.

         BGP-LU, RSVP-TE LSPs, LDP, SR Tree SID and GRE encap SDPs are among
         the tunneling options that require an entry in MPLS LIF table.

         Total allocatable is typically platform hardware independent and is a
         representation of Control Plane allocation."
    ::= { tChassisIxrResourceEntry 9 }

tChassisIxrResL3VsiRifTotal      OBJECT-TYPE
    SYNTAX      Unsigned32
    MAX-ACCESS  read-only
    STATUS      current
    DESCRIPTION
        "The value of the object tChassisIxrResL3VsiRifTotal indicates the
         maximum number of LIF entries that are allowed for Layer-3
         applications on this chassis.

         Layer-3 VSI-RIF stake-holder list includes Services, IP interfaces,
         Sync/PTP and FP based BFD/uBFD.

         Total allocatable is typically platform hardware independent and is a
         representation of Control Plane allocation."
    ::= { tChassisIxrResourceEntry 10 }

tChassisIxrResL3VsiRifAlloc      OBJECT-TYPE
    SYNTAX      Unsigned32
    MAX-ACCESS  read-only
    STATUS      current
    DESCRIPTION
        "The value of the object tChassisIxrResL3VsiRifAlloc indicates the
         number of LIF entries that are currently in use on by Layer-3
         applications on this chassis.

         Layer-3 VSI-RIF stake-holder list includes Services, IP interfaces,
         Sync/PTP and FP based BFD/uBFD.

         Total allocatable is typically platform hardware independent and is a
         representation of Control Plane allocation."
    ::= { tChassisIxrResourceEntry 11 }

tChassisIxrResL3VsiRifFree       OBJECT-TYPE
    SYNTAX      Unsigned32
    MAX-ACCESS  read-only
    STATUS      current
    DESCRIPTION
        "The value of the object tChassisIxrResL3VsiRifFree indicates the
         number of free LIF entries that are currently available for Layer-3
         applications on this chassis.

         Layer-3 VSI-RIF stake-holder list includes Services, IP interfaces,
         Sync/PTP and FP based BFD/uBFD.

         Total allocatable is typically platform hardware independent and is a
         representation of Control Plane allocation."
    ::= { tChassisIxrResourceEntry 12 }

tChassisIxrResFecUnpairedTotal   OBJECT-TYPE
    SYNTAX      Unsigned32
    MAX-ACCESS  read-only
    STATUS      current
    DESCRIPTION
        "The value of the object tChassisIxrResFecUnpairedTotal indicates the
         maximum number of FEC System-wide Unpaired (Standalone) entries that
         are allowed on this chassis.

         SDP bindings and VPLS services mapped to shared vlan-qos on LAG are
         among use cases that share unprotected FEC pool.

         Total allocatable is typically platform hardware independent and is a
         representation of Control Plane allocation."
    ::= { tChassisIxrResourceEntry 13 }

tChassisIxrResFecUnpairedAlloc   OBJECT-TYPE
    SYNTAX      Unsigned32
    MAX-ACCESS  read-only
    STATUS      current
    DESCRIPTION
        "The value of the object tChassisIxrResFecUnpairedAlloc indicates the
         number of FEC System-wide Unpaired (Standalone) entries that are
         currently in use on this chassis.

         SDP bindings and VPLS services mapped to shared vlan-qos on LAG are
         among use cases that share unprotected FEC pool.

         Total allocatable is typically platform hardware independent and is a
         representation of Control Plane allocation."
    ::= { tChassisIxrResourceEntry 14 }

tChassisIxrResFecUnpairedFree    OBJECT-TYPE
    SYNTAX      Unsigned32
    MAX-ACCESS  read-only
    STATUS      current
    DESCRIPTION
        "The value of the object tChassisIxrResFecUnpairedFree indicates the
         number of free FEC System-wide Unpaired(Standalone) entries that are
         currently available on this chassis.

         SDP bindings and VPLS services mapped to shared vlan-qos on LAG are
         among use cases that share unprotected FEC pool.

         Total allocatable is typically platform hardware independent and is a
         representation of Control Plane allocation."
    ::= { tChassisIxrResourceEntry 15 }

tChassisIxrResFecPairedTotal     OBJECT-TYPE
    SYNTAX      Unsigned32
    MAX-ACCESS  read-only
    STATUS      current
    DESCRIPTION
        "The value of the object tChassisIxrResFecPairedTotal indicates the
         maximum number of FEC System-wide Paired entries that are allowed on
         this chassis.

         Eth-Ring (G.8032) SAP is the main stake holder.

         Total allocatable is typically platform hardware independent and is a
         representation of Control Plane allocation."
    ::= { tChassisIxrResourceEntry 16 }

tChassisIxrResFecPairedAlloc     OBJECT-TYPE
    SYNTAX      Unsigned32
    MAX-ACCESS  read-only
    STATUS      current
    DESCRIPTION
        "The value of the object tChassisIxrResFecPairedAlloc indicates the
         number of FEC System-wide Paired entries that are currently in use on
         this chassis.

         Eth-Ring (G.8032) SAP is the main stake holder.

         Total allocatable is typically platform hardware independent and is a
         representation of Control Plane allocation."
    ::= { tChassisIxrResourceEntry 17 }

tChassisIxrResFecPairedFree      OBJECT-TYPE
    SYNTAX      Unsigned32
    MAX-ACCESS  read-only
    STATUS      current
    DESCRIPTION
        "The value of the object tChassisIxrResFecPairedFree indicates the
         number of free FEC System-wide Paired entries that are currently
         available on this chassis.

         Eth-Ring (G.8032) SAP is the main stake holder.

         Total allocatable is typically platform hardware independent and is a
         representation of Control Plane allocation."
    ::= { tChassisIxrResourceEntry 18 }

tChassisIxrResOamLmCtrTotal      OBJECT-TYPE
    SYNTAX      Unsigned32
    MAX-ACCESS  read-only
    STATUS      current
    DESCRIPTION
        "The value of the object tChassisIxrResOamLmCtrTotal indicates the
         maximum number of OAM LM CTR ID entries that are allowed to be
         provisioned on this chassis."
    ::= { tChassisIxrResourceEntry 19 }

tChassisIxrResOamLmCtrAlloc      OBJECT-TYPE
    SYNTAX      Unsigned32
    MAX-ACCESS  read-only
    STATUS      current
    DESCRIPTION
        "The value of the object tChassisIxrResOamLmCtrAlloc indicates the
         number of OAM LM CTR ID entries that are currently in use on this
         chassis."
    ::= { tChassisIxrResourceEntry 20 }

tChassisIxrResOamLmCtrFree       OBJECT-TYPE
    SYNTAX      Unsigned32
    MAX-ACCESS  read-only
    STATUS      current
    DESCRIPTION
        "The value of the object tChassisIxrResOamLmCtrFree indicates the
         number of free OAM LM CTR ID entries that are currently available on
         this chassis."
    ::= { tChassisIxrResourceEntry 21 }

tChassisIxrResAcLifTotal         OBJECT-TYPE
    SYNTAX      Unsigned32
    MAX-ACCESS  read-only
    STATUS      current
    DESCRIPTION
        "The value of the object tChassisIxrResAcLifTotal indicates the maximum
         number of AC LIF entries that are allowed to be provisioned on this
         chassis.

         Wide variety of applications including BFD, Interfaces, Ports, PTP,
         EVPN service, SAPs, Services over GRE SDP and Services over MPLS/SR
         transport are among the users of AC LIF"
    ::= { tChassisIxrResourceEntry 22 }

tChassisIxrResAcLifAlloc         OBJECT-TYPE
    SYNTAX      Unsigned32
    MAX-ACCESS  read-only
    STATUS      current
    DESCRIPTION
        "The value of the object tChassisIxrResAcLifAlloc indicates the number
         of AC LIF entries that are currently in use on this chassis.

         Wide variety of applications including BFD, Interfaces, Ports, PTP,
         EVPN service, SAPs, Services over GRE SDP and Services over MPLS/SR
         transport are among the users of AC LIF"
    ::= { tChassisIxrResourceEntry 23 }

tChassisIxrResAcLifFree          OBJECT-TYPE
    SYNTAX      Unsigned32
    MAX-ACCESS  read-only
    STATUS      current
    DESCRIPTION
        "The value of the object tChassisIxrResAcLifFree indicates the number
         of free AC LIF entries that are currently available on this chassis.

         Wide variety of applications including BFD, Interfaces, Ports, PTP,
         EVPN service, SAPs, Services over GRE SDP and Services over MPLS/SR
         transport are among the users of AC LIF"
    ::= { tChassisIxrResourceEntry 24 }

tChassisIxrResMplsNhlfeLifTotal  OBJECT-TYPE
    SYNTAX      Unsigned32
    MAX-ACCESS  read-only
    STATUS      current
    DESCRIPTION
        "The value of the object tChassisIxrResMplsNhlfeLifTotal indicates the
         maximum number of MPLS Next-Hop Label Forwarding LIF entries that are
         allowed to be provisioned on this chassis.

         Transport options like BGP-LU, LDP, RSVP-TE, Segment Routing, Services
         over GRE SDP and Tree SID are among the users of MPLS NHLFE LIF"
    ::= { tChassisIxrResourceEntry 25 }

tChassisIxrResMplsNhlfeLifAlloc  OBJECT-TYPE
    SYNTAX      Unsigned32
    MAX-ACCESS  read-only
    STATUS      current
    DESCRIPTION
        "The value of the object tChassisIxrResMplsNhlfeLifAlloc indicates the
         number of MPLS Next-Hop Label Forwarding LIF entries that are
         currently in use on this chassis.

         Transport options like BGP-LU, LDP, RSVP-TE, Segment Routing, Services
         over GRE SDP and Tree SID are among the users of MPLS NHLFE LIF"
    ::= { tChassisIxrResourceEntry 26 }

tChassisIxrResMplsNhlfeLifFree   OBJECT-TYPE
    SYNTAX      Unsigned32
    MAX-ACCESS  read-only
    STATUS      current
    DESCRIPTION
        "The value of the object tChassisIxrResMplsNhlfeLifFree indicates the
         number of free MPLS Next-Hop Label Forwarding LIF entries that are
         currently available on this chassis.

         Transport options like BGP-LU, LDP, RSVP-TE, Segment Routing, Services
         over GRE SDP and Tree SID are among the users of MPLS NHLFE LIF"
    ::= { tChassisIxrResourceEntry 27 }

tChassisIxrResBgpLblRtLifTotal   OBJECT-TYPE
    SYNTAX      Unsigned32
    MAX-ACCESS  read-only
    STATUS      current
    DESCRIPTION
        "The value of the object tChassisIxrResBgpLblRtLifTotal indicates the
         maximum number of BGP Label Route LIF entries that are allowed to be
         provisioned on this chassis.

         BGP Labeled Unicast (rfc-3107) and BGP routes stored in Route Table
         Mgr are among the users of this resource."
    ::= { tChassisIxrResourceEntry 28 }

tChassisIxrResBgpLblRtLifAlloc   OBJECT-TYPE
    SYNTAX      Unsigned32
    MAX-ACCESS  read-only
    STATUS      current
    DESCRIPTION
        "The value of the object tChassisIxrResBgpLblRtLifAlloc indicates the
         number of BGP Label Route LIF entries that are currently in use on
         this chassis.

         BGP Labeled Unicast (rfc-3107) and BGP routes stored in Route Table
         Mgr are among the users of this resource."
    ::= { tChassisIxrResourceEntry 29 }

tChassisIxrResBgpLblRtLifFree    OBJECT-TYPE
    SYNTAX      Unsigned32
    MAX-ACCESS  read-only
    STATUS      current
    DESCRIPTION
        "The value of the object tChassisIxrResBgpLblRtLifFree indicates the
         number of free BGP Label Route LIF entries that are currently
         available on this chassis.

         BGP Labeled Unicast (rfc-3107) and BGP routes stored in Route Table
         Mgr are among the users of this resource."
    ::= { tChassisIxrResourceEntry 30 }

tChassisIxrResSdpBndMplsLifTotal OBJECT-TYPE
    SYNTAX      Unsigned32
    MAX-ACCESS  read-only
    STATUS      current
    DESCRIPTION
        "The value of the object tChassisIxrResSdpBndMplsLifTotal indicates the
         maximum number of SDP Bind MPLS LIF entries that are allowed to be
         provisioned on this chassis.

         EVPN MPLS/SR tunnels and SDP bindings are among the users of this
         resource"
    ::= { tChassisIxrResourceEntry 31 }

tChassisIxrResSdpBndMplsLifAlloc OBJECT-TYPE
    SYNTAX      Unsigned32
    MAX-ACCESS  read-only
    STATUS      current
    DESCRIPTION
        "The value of the object tChassisIxrResSdpBndMplsLifAlloc indicates the
         number of SDP Bind MPLS LIF entries that are currently in use on this
         chassis.

         EVPN MPLS/SR tunnels and SDP bindings are among the users of this
         resource"
    ::= { tChassisIxrResourceEntry 32 }

tChassisIxrResSdpBndMplsLifFree  OBJECT-TYPE
    SYNTAX      Unsigned32
    MAX-ACCESS  read-only
    STATUS      current
    DESCRIPTION
        "The value of the object tChassisIxrResSdpBndMplsLifFree indicates the
         number of free SDP Bind MPLS LIF entries that are currently available
         on this chassis.

         EVPN MPLS/SR tunnels and SDP bindings are among the users of this
         resource"
    ::= { tChassisIxrResourceEntry 33 }

tChassisIxrResSdpBndGreLifTotal  OBJECT-TYPE
    SYNTAX      Unsigned32
    MAX-ACCESS  read-only
    STATUS      current
    DESCRIPTION
        "The value of the object tChassisIxrResSdpBndGreLifTotal indicates the
         maximum number of SDP Bind GRE LIF entries that are allowed to be
         provisioned on this chassis.

         SDP bindings with GRE encap is the main stake-holder of this resource"
    ::= { tChassisIxrResourceEntry 34 }

tChassisIxrResSdpBndGreLifAlloc  OBJECT-TYPE
    SYNTAX      Unsigned32
    MAX-ACCESS  read-only
    STATUS      current
    DESCRIPTION
        "The value of the object tChassisIxrResSdpBndGreLifAlloc indicates the
         number of SDP Bind GRE LIF entries that are currently in use on this
         chassis.

         SDP bindings with GRE encap is the main stake-holder of this resource"
    ::= { tChassisIxrResourceEntry 35 }

tChassisIxrResSdpBndGreLifFree   OBJECT-TYPE
    SYNTAX      Unsigned32
    MAX-ACCESS  read-only
    STATUS      current
    DESCRIPTION
        "The value of the object tChassisIxrResSdpBndGreLifFree indicates the
         number of free SDP Bind GRE LIF entries that are currently available
         on this chassis.

         SDP bindings with GRE encap is the main stake-holder of this resource"
    ::= { tChassisIxrResourceEntry 36 }

tChassisIxrResSsidLifTotal       OBJECT-TYPE
    SYNTAX      Unsigned32
    MAX-ACCESS  read-only
    STATUS      current
    DESCRIPTION
        "The value of the object tChassisIxrResSsidLifTotal indicates the
         maximum number of SSID LIF entries that are allowed to be provisioned
         on this chassis.

         SRv6 SIDs are the main user of this resource."
    ::= { tChassisIxrResourceEntry 37 }

tChassisIxrResSsidLifAlloc       OBJECT-TYPE
    SYNTAX      Unsigned32
    MAX-ACCESS  read-only
    STATUS      current
    DESCRIPTION
        "The value of the object tChassisIxrResSsidLifAlloc indicates the
         number of SSID LIF entries that are currently in use on this chassis.

         SRv6 SIDs are the main user of this resource."
    ::= { tChassisIxrResourceEntry 38 }

tChassisIxrResSsidLifFree        OBJECT-TYPE
    SYNTAX      Unsigned32
    MAX-ACCESS  read-only
    STATUS      current
    DESCRIPTION
        "The value of the object tChassisIxrResSsidLifFree indicates the number
         of free SSID LIF entries that are currently available on this chassis.

         SRv6 SIDs are the main user of this resource."
    ::= { tChassisIxrResourceEntry 39 }

tChassisIxrResSrv6TunnelLifTotal OBJECT-TYPE
    SYNTAX      Unsigned32
    MAX-ACCESS  read-only
    STATUS      current
    DESCRIPTION
        "The value of the object tChassisIxrResSrv6TunnelLifTotal indicates the
         maximum number of SRv6 Tunnel LIF entries that are allowed to be
         provisioned on this chassis.

         SRv6 tunnels is the main user of this resource."
    ::= { tChassisIxrResourceEntry 40 }

tChassisIxrResSrv6TunnelLifAlloc OBJECT-TYPE
    SYNTAX      Unsigned32
    MAX-ACCESS  read-only
    STATUS      current
    DESCRIPTION
        "The value of the object tChassisIxrResSrv6TunnelLifAlloc indicates the
         number of SRv6 Tunnel LIF entries that are currently in use on this
         chassis.

         SRv6 tunnels is the main user of this resource."
    ::= { tChassisIxrResourceEntry 41 }

tChassisIxrResSrv6TunnelLifFree  OBJECT-TYPE
    SYNTAX      Unsigned32
    MAX-ACCESS  read-only
    STATUS      current
    DESCRIPTION
        "The value of the object tChassisIxrResSrv6TunnelLifFree indicates the
         number of free SRv6 Tunnel LIF entries that are currently available on
         this chassis.

         SRv6 tunnels is the main user of this resource."
    ::= { tChassisIxrResourceEntry 42 }

tChassisIxrResL2ServiceTotal     OBJECT-TYPE
    SYNTAX      Unsigned32
    MAX-ACCESS  read-only
    STATUS      current
    DESCRIPTION
        "The value of the object tChassisIxrResL2ServiceTotal indicates the
         maximum number of Layer-2 Service LIF entries that are allowed to be
         provisioned on this chassis.

         EPIPE and VPLS services are the main user of this resource."
    ::= { tChassisIxrResourceEntry 43 }

tChassisIxrResL2ServiceAlloc     OBJECT-TYPE
    SYNTAX      Unsigned32
    MAX-ACCESS  read-only
    STATUS      current
    DESCRIPTION
        "The value of the object tChassisIxrResL2ServiceAlloc indicates the
         number of Layer-2 Service LIF entries that are currently in use on
         this chassis.

         EPIPE and VPLS services are the main user of this resource."
    ::= { tChassisIxrResourceEntry 44 }

tChassisIxrResL2ServiceFree      OBJECT-TYPE
    SYNTAX      Unsigned32
    MAX-ACCESS  read-only
    STATUS      current
    DESCRIPTION
        "The value of the object tChassisIxrResL2ServiceFree indicates the
         number of free Layer-2 Service LIF entries that are currently
         available on this chassis.

         EPIPE and VPLS services are the main user of this resource."
    ::= { tChassisIxrResourceEntry 45 }

tChassisIxrResStationIdTotal     OBJECT-TYPE
    SYNTAX      Unsigned32
    MAX-ACCESS  read-only
    STATUS      current
    DESCRIPTION
        "The value of the object tChassisIxrResStationIdTotal indicates the
         maximum number of Station ID entries that are allowed to be
         provisioned on this chassis.

         BFD session identifier is the main user of this resource."
    ::= { tChassisIxrResourceEntry 46 }

tChassisIxrResStationIdAlloc     OBJECT-TYPE
    SYNTAX      Unsigned32
    MAX-ACCESS  read-only
    STATUS      current
    DESCRIPTION
        "The value of the object tChassisIxrResStationIdAlloc indicates the
         number of Station ID entries that are currently in use on this
         chassis.

         BFD session identifier is the main user of this resource."
    ::= { tChassisIxrResourceEntry 47 }

tChassisIxrResStationIdFree      OBJECT-TYPE
    SYNTAX      Unsigned32
    MAX-ACCESS  read-only
    STATUS      current
    DESCRIPTION
        "The value of the object tChassisIxrResStationIdFree indicates the
         number of free Station ID entries that are currently available on this
         chassis.

         BFD session identifier is the main user of this resource."
    ::= { tChassisIxrResourceEntry 48 }

tChassisIxrResVxlanLifTotal      OBJECT-TYPE
    SYNTAX      Unsigned32
    MAX-ACCESS  read-only
    STATUS      current
    DESCRIPTION
        "The value of the object tChassisIxrResVxlanLifTotal indicates the
         maximum number of VXLAN LIF entries that are allowed to be provisioned
         on this chassis.

         VXLAN tunnels are the main user of this resource."
    ::= { tChassisIxrResourceEntry 49 }

tChassisIxrResVxlanLifAlloc      OBJECT-TYPE
    SYNTAX      Unsigned32
    MAX-ACCESS  read-only
    STATUS      current
    DESCRIPTION
        "The value of the object tChassisIxrResVxlanLifAlloc indicates the
         number of VXLAN LIF entries that are currently in use on this chassis.

         VXLAN tunnels are the main user of this resource."
    ::= { tChassisIxrResourceEntry 50 }

tChassisIxrResVxlanLifFree       OBJECT-TYPE
    SYNTAX      Unsigned32
    MAX-ACCESS  read-only
    STATUS      current
    DESCRIPTION
        "The value of the object tChassisIxrResVxlanLifFree indicates the
         number of free VXLAN LIF entries that are currently available on this
         chassis.

         VXLAN tunnels are the main user of this resource."
    ::= { tChassisIxrResourceEntry 51 }

tChassisIxrResourceOwnerTable    OBJECT-TYPE
    SYNTAX      SEQUENCE OF TChassisIxrResourceOwnerEntry
    MAX-ACCESS  not-accessible
    STATUS      current
    DESCRIPTION
        "The tChassisIxrResourceTable contains information about a chassis
         resource utilization by resource owners for resources specific to the
         Nokia IXR systems."
    ::= { tmnxChassisObjs 33 }

tChassisIxrResourceOwnerEntry    OBJECT-TYPE
    SYNTAX      TChassisIxrResourceOwnerEntry
    MAX-ACCESS  not-accessible
    STATUS      current
    DESCRIPTION
        "Each row in the tChassisIxrResourceOwnerEntry contains information
         about resource utilization for the chassis and resource owner
         specified by the indexes.

         Rows in this table are created by the system and cannot be created or
         destroyed by SNMP Get or Set requests."
    INDEX       {
        tmnxChassisIndex,
        tmnxChassisIxrResourceOwner
    }
    ::= { tChassisIxrResourceOwnerTable 1 }

TChassisIxrResourceOwnerEntry    ::= SEQUENCE
{
    tmnxChassisIxrResourceOwner      TmnxIxrResourceOwner,
    tChassisIxrResOwnCommonLifTotal  Unsigned32,
    tChassisIxrResOwnCommonLifAlloc  Unsigned32,
    tChassisIxrResOwnCommonLifFree   Unsigned32,
    tChassisIxrResOwnArpLifAlloc     Unsigned32,
    tChassisIxrResOwnMplsLifAlloc    Unsigned32,
    tChassisIxrResOwnL3VsiRifAlloc   Unsigned32,
    tChassisIxrResOwnFecUnpairAlloc  Unsigned32,
    tChassisIxrResOwnFecPairedAlloc  Unsigned32,
    tChassisIxrResOwnOamLmCtrAlloc   Unsigned32,
    tChasIxrResOwnAcLifAlloc         Unsigned32,
    tChasIxrResOwnMplsNhlfeLifAlloc  Unsigned32,
    tChasIxrResOwnBgpLblRtLifTotal   Unsigned32,
    tChasIxrResOwnBgpLblRtLifAlloc   Unsigned32,
    tChasIxrResOwnBgpLblRtLifFree    Unsigned32,
    tChasIxrResOwnSdpBndMplsLifAlloc Unsigned32,
    tChasIxrResOwnSdpBndGreLifAlloc  Unsigned32,
    tChasIxrResOwnSsidLifAlloc       Unsigned32,
    tChasIxrResOwnSrv6TunnelLifAlloc Unsigned32,
    tChasIxrResOwnL2ServiceAlloc     Unsigned32,
    tChasIxrResOwnStationIdAlloc     Unsigned32,
    tChasIxrResOwnVxlanLifAlloc      Unsigned32,
    tChasIxrResOwnAcLifTotal         Unsigned32,
    tChasIxrResOwnAcLifFree          Unsigned32
}

tmnxChassisIxrResourceOwner      OBJECT-TYPE
    SYNTAX      TmnxIxrResourceOwner
    MAX-ACCESS  not-accessible
    STATUS      current
    DESCRIPTION
        "The value of the object tmnxChassisIxrResourceOwner identifies an
         application that owns the resources."
    ::= { tChassisIxrResourceOwnerEntry 1 }

tChassisIxrResOwnCommonLifTotal  OBJECT-TYPE
    SYNTAX      Unsigned32
    MAX-ACCESS  read-only
    STATUS      current
    DESCRIPTION
        "The value of the object tChassisIxrResOwnCommonLifTotal indicates the
         maximum number of Common LIF entries that can be owned by the
         application specified by tmnxChassisIxrResourceOwner on this chassis.

         The value 4294967295 indicates that the value is not applicable."
    ::= { tChassisIxrResourceOwnerEntry 2 }

tChassisIxrResOwnCommonLifAlloc  OBJECT-TYPE
    SYNTAX      Unsigned32
    MAX-ACCESS  read-only
    STATUS      current
    DESCRIPTION
        "The value of the object tChassisIxrResOwnCommonLifAlloc indicates the
         number of Common LIF entries that are currently owned by the
         application specified by tmnxChassisIxrResourceOwner on this chassis.

         The value 4294967295 indicates that the value is not applicable."
    ::= { tChassisIxrResourceOwnerEntry 3 }

tChassisIxrResOwnCommonLifFree   OBJECT-TYPE
    SYNTAX      Unsigned32
    MAX-ACCESS  read-only
    STATUS      current
    DESCRIPTION
        "The value of the object tChassisIxrResOwnCommonLifFree indicates the
         maximum number of free Common LIF entries that are available for the
         application specified by tmnxChassisIxrResourceOwner on this chassis.

         The value 4294967295 indicates that the value is not applicable."
    ::= { tChassisIxrResourceOwnerEntry 4 }

tChassisIxrResOwnArpLifAlloc     OBJECT-TYPE
    SYNTAX      Unsigned32
    MAX-ACCESS  read-only
    STATUS      current
    DESCRIPTION
        "The value of the object tChassisIxrResOwnArpLifAlloc indicates the
         number of ARP LIF entries that are currently owned by the application
         specified by tmnxChassisIxrResourceOwner on this chassis.

         The value 4294967295 indicates that the value is not applicable."
    ::= { tChassisIxrResourceOwnerEntry 5 }

tChassisIxrResOwnMplsLifAlloc    OBJECT-TYPE
    SYNTAX      Unsigned32
    MAX-ACCESS  read-only
    STATUS      current
    DESCRIPTION
        "The value of the object tChassisIxrResOwnMplsLifAlloc indicates the
         number of MPLS LIF entries that are currently owned by the application
         specified by tmnxChassisIxrResourceOwner on this chassis.

         The value 4294967295 indicates that the value is not applicable."
    ::= { tChassisIxrResourceOwnerEntry 6 }

tChassisIxrResOwnL3VsiRifAlloc   OBJECT-TYPE
    SYNTAX      Unsigned32
    MAX-ACCESS  read-only
    STATUS      current
    DESCRIPTION
        "The value of the object tChassisIxrResOwnL3VsiRifAlloc indicates the
         number of L3 VSI RIF entries that are currently owned by the
         application specified by tmnxChassisIxrResourceOwner on this chassis.

         The value 4294967295 indicates that the value is not applicable."
    ::= { tChassisIxrResourceOwnerEntry 7 }

tChassisIxrResOwnFecUnpairAlloc  OBJECT-TYPE
    SYNTAX      Unsigned32
    MAX-ACCESS  read-only
    STATUS      current
    DESCRIPTION
        "The value of the object tChassisIxrResOwnFecUnpairAlloc indicates the
         number of FEC Unpaired entries that are currently owned by the
         application specified by tmnxChassisIxrResourceOwner on this chassis.

         The value 4294967295 indicates that the value is not applicable."
    ::= { tChassisIxrResourceOwnerEntry 8 }

tChassisIxrResOwnFecPairedAlloc  OBJECT-TYPE
    SYNTAX      Unsigned32
    MAX-ACCESS  read-only
    STATUS      current
    DESCRIPTION
        "The value of the object tChassisIxrResOwnFecPairedAlloc indicates the
         number of FEC Paired Protected entries that are currently owned by
         tmnxChassisIxrResourceOwner on this chassis.

         The value 4294967295 indicates that the value is not applicable."
    ::= { tChassisIxrResourceOwnerEntry 9 }

tChassisIxrResOwnOamLmCtrAlloc   OBJECT-TYPE
    SYNTAX      Unsigned32
    MAX-ACCESS  read-only
    STATUS      current
    DESCRIPTION
        "The value of the object tChassisIxrResOwnOamLmCtrAlloc indicates the
         number of OAM LM CTR entries that are currently owned by the
         application specified by tmnxChassisIxrResourceOwner on this chassis.

         The value 4294967295 indicates that the value is not applicable."
    ::= { tChassisIxrResourceOwnerEntry 10 }

tChasIxrResOwnAcLifAlloc         OBJECT-TYPE
    SYNTAX      Unsigned32
    MAX-ACCESS  read-only
    STATUS      current
    DESCRIPTION
        "The value of the object tChasIxrResOwnAcLifAlloc indicates the number
         of AC LIF entries that are currently in use on this chassis."
    ::= { tChassisIxrResourceOwnerEntry 11 }

tChasIxrResOwnMplsNhlfeLifAlloc  OBJECT-TYPE
    SYNTAX      Unsigned32
    MAX-ACCESS  read-only
    STATUS      current
    DESCRIPTION
        "The value of the object tChasIxrResOwnMplsNhlfeLifAlloc indicates the
         number of MPLS NHLFE LIF entries that are currently in use on this
         chassis."
    ::= { tChassisIxrResourceOwnerEntry 12 }

tChasIxrResOwnBgpLblRtLifTotal   OBJECT-TYPE
    SYNTAX      Unsigned32
    MAX-ACCESS  read-only
    STATUS      current
    DESCRIPTION
        "The value of the object tChasIxrResOwnBgpLblRtLifTotal indicates the
         maximum number of BGP Label Route LIF entries that are allowed to be
         provisioned on this chassis."
    ::= { tChassisIxrResourceOwnerEntry 13 }

tChasIxrResOwnBgpLblRtLifAlloc   OBJECT-TYPE
    SYNTAX      Unsigned32
    MAX-ACCESS  read-only
    STATUS      current
    DESCRIPTION
        "The value of the object tChasIxrResOwnBgpLblRtLifAlloc indicates the
         number of BGP Label Route LIF entries that are currently in use on
         this chassis."
    ::= { tChassisIxrResourceOwnerEntry 14 }

tChasIxrResOwnBgpLblRtLifFree    OBJECT-TYPE
    SYNTAX      Unsigned32
    MAX-ACCESS  read-only
    STATUS      current
    DESCRIPTION
        "The value of the object tChasIxrResOwnBgpLblRtLifFree indicates the
         number of free BGP Label Route LIF entries that are currently
         available on this chassis."
    ::= { tChassisIxrResourceOwnerEntry 15 }

tChasIxrResOwnSdpBndMplsLifAlloc OBJECT-TYPE
    SYNTAX      Unsigned32
    MAX-ACCESS  read-only
    STATUS      current
    DESCRIPTION
        "The value of the object tChasIxrResOwnSdpBndMplsLifAlloc indicates the
         number of SDP BIND MPLS LIF entries that are currently in use on this
         chassis."
    ::= { tChassisIxrResourceOwnerEntry 16 }

tChasIxrResOwnSdpBndGreLifAlloc  OBJECT-TYPE
    SYNTAX      Unsigned32
    MAX-ACCESS  read-only
    STATUS      current
    DESCRIPTION
        "The value of the object tChasIxrResOwnSdpBndGreLifAlloc indicates the
         number of SDP BIND GRE LIF entries that are currently in use on this
         chassis."
    ::= { tChassisIxrResourceOwnerEntry 17 }

tChasIxrResOwnSsidLifAlloc       OBJECT-TYPE
    SYNTAX      Unsigned32
    MAX-ACCESS  read-only
    STATUS      current
    DESCRIPTION
        "The value of the object tChasIxrResOwnSsidLifAlloc indicates the
         number of SSID LIF entries that are currently in use on this chassis."
    ::= { tChassisIxrResourceOwnerEntry 18 }

tChasIxrResOwnSrv6TunnelLifAlloc OBJECT-TYPE
    SYNTAX      Unsigned32
    MAX-ACCESS  read-only
    STATUS      current
    DESCRIPTION
        "The value of the object tChasIxrResOwnSrv6TunnelLifAlloc indicates the
         number of SRv6 Tunnel LIF entries that are currently in use on this
         chassis."
    ::= { tChassisIxrResourceOwnerEntry 19 }

tChasIxrResOwnL2ServiceAlloc     OBJECT-TYPE
    SYNTAX      Unsigned32
    MAX-ACCESS  read-only
    STATUS      current
    DESCRIPTION
        "The value of the object tChasIxrResOwnL2ServiceAlloc indicates the
         number of L2 Service entries that are currently in use on this
         chassis."
    ::= { tChassisIxrResourceOwnerEntry 20 }

tChasIxrResOwnStationIdAlloc     OBJECT-TYPE
    SYNTAX      Unsigned32
    MAX-ACCESS  read-only
    STATUS      current
    DESCRIPTION
        "The value of the object tChasIxrResOwnStationIdAlloc indicates the
         number of Station ID entries that are currently in use on this
         chassis."
    ::= { tChassisIxrResourceOwnerEntry 21 }

tChasIxrResOwnVxlanLifAlloc      OBJECT-TYPE
    SYNTAX      Unsigned32
    MAX-ACCESS  read-only
    STATUS      current
    DESCRIPTION
        "The value of the object tChasIxrResOwnVxlanLifAlloc indicates the
         number of VXLAN LIF entries that are currently in use on this chassis."
    ::= { tChassisIxrResourceOwnerEntry 22 }

tChasIxrResOwnAcLifTotal         OBJECT-TYPE
    SYNTAX      Unsigned32
    MAX-ACCESS  read-only
    STATUS      current
    DESCRIPTION
        "The value of the object tChasIxrResOwnAcLifTotal indicates the maximum
         number of AC-LIF LIF entries that can be owned by the application
         specified by tmnxChassisIxrResourceOwner on this chassis.

         The value 4294967295 indicates that the value is not applicable."
    ::= { tChassisIxrResourceOwnerEntry 23 }

tChasIxrResOwnAcLifFree          OBJECT-TYPE
    SYNTAX      Unsigned32
    MAX-ACCESS  read-only
    STATUS      current
    DESCRIPTION
        "The value of the object tChasIxrResOwnAcLifFree indicates the maximum
         number of free AC-LIF LIF entries that are available for the
         application specified by tmnxChassisIxrResourceOwner on this chassis.

         The value 4294967295 indicates that the value is not applicable."
    ::= { tChassisIxrResourceOwnerEntry 24 }

tmnxFlashTable                   OBJECT-TYPE
    SYNTAX      SEQUENCE OF TmnxFlashEntry
    MAX-ACCESS  not-accessible
    STATUS      current
    DESCRIPTION
        "This table contains information about flash devices"
    ::= { tmnxChassisObjs 34 }

tmnxFlashEntry                   OBJECT-TYPE
    SYNTAX      TmnxFlashEntry
    MAX-ACCESS  not-accessible
    STATUS      current
    DESCRIPTION
        "Contains information regarding a flash unit."
    INDEX       {
        tmnxChassisIndex,
        tmnxHwIndex
    }
    ::= { tmnxFlashTable 1 }

TmnxFlashEntry                   ::= SEQUENCE
{
    tmnxFlashOperStatus              TmnxDeviceState,
    tmnxFlashSerialNumber            TItemDescription,
    tmnxFlashFirmwareRevision        TItemDescription,
    tmnxFlashModelNumber             TItemDescription,
    tmnxFlashCapacity                Unsigned32,
    tmnxFlashUsed                    Unsigned32,
    tmnxFlashPercentageUsed          Unsigned32
}

tmnxFlashOperStatus              OBJECT-TYPE
    SYNTAX      TmnxDeviceState
    MAX-ACCESS  read-only
    STATUS      current
    DESCRIPTION
        "Current status of this flash unit."
    ::= { tmnxFlashEntry 1 }

tmnxFlashSerialNumber            OBJECT-TYPE
    SYNTAX      TItemDescription
    MAX-ACCESS  read-only
    STATUS      current
    DESCRIPTION
        "The serial number for this flash unit."
    ::= { tmnxFlashEntry 2 }

tmnxFlashFirmwareRevision        OBJECT-TYPE
    SYNTAX      TItemDescription
    MAX-ACCESS  read-only
    STATUS      current
    DESCRIPTION
        "The firmware revision number for this flash unit."
    ::= { tmnxFlashEntry 3 }

tmnxFlashModelNumber             OBJECT-TYPE
    SYNTAX      TItemDescription
    MAX-ACCESS  read-only
    STATUS      current
    DESCRIPTION
        "The model number for this flash unit."
    ::= { tmnxFlashEntry 4 }

tmnxFlashCapacity                OBJECT-TYPE
    SYNTAX      Unsigned32
    UNITS       "sectors"
    MAX-ACCESS  read-only
    STATUS      current
    DESCRIPTION
        "The value of tmnxFlashCapacity indicates the maximum size of this
         flash unit in 512-byte sectors."
    ::= { tmnxFlashEntry 5 }

tmnxFlashUsed                    OBJECT-TYPE
    SYNTAX      Unsigned32
    UNITS       "sectors"
    MAX-ACCESS  read-only
    STATUS      current
    DESCRIPTION
        "The value of tmnxFlashUsed indicates the amount used, in 512-byte
         sectors, of this flash unit's total capacity."
    ::= { tmnxFlashEntry 6 }

tmnxFlashPercentageUsed          OBJECT-TYPE
    SYNTAX      Unsigned32
    UNITS       "percent"
    MAX-ACCESS  read-only
    STATUS      current
    DESCRIPTION
        "The value of tmnxFlashPercentageUsed indicates the amount used for
         this flash unit as a percentage of total capacity."
    ::= { tmnxFlashEntry 7 }

tmnxSlotObjs                     OBJECT IDENTIFIER ::= { tmnxHwObjs 2 }

tmnxCardObjs                     OBJECT IDENTIFIER ::= { tmnxHwObjs 3 }

tmnxCardLastChange               OBJECT-TYPE
    SYNTAX      TimeStamp
    MAX-ACCESS  read-only
    STATUS      current
    DESCRIPTION
        "The value of sysUpTime when the tmnxCardTable was last changed."
    ::= { tmnxCardObjs 1 }

tmnxCardTable                    OBJECT-TYPE
    SYNTAX      SEQUENCE OF TmnxCardEntry
    MAX-ACCESS  not-accessible
    STATUS      current
    DESCRIPTION
        "The tmnxCardTable has an entry for each IOM card slot in each chassis
         in the TMNX system."
    ::= { tmnxCardObjs 2 }

tmnxCardEntry                    OBJECT-TYPE
    SYNTAX      TmnxCardEntry
    MAX-ACCESS  not-accessible
    STATUS      current
    DESCRIPTION
        "Each row entry represents an IOM card slot in a chassis in the
         system.  Entries cannot be created and deleted via SNMP SET
         operations.  When a tmnxChassisEntry is created, a tmnxCardEntry
         is created for each IOM card slot in that chassis.  Before a
         tmnxChassisEntry can be deleted, each tmnxCardEntry for that
         chassis must be in the proper state for removal."
    INDEX       {
        tmnxChassisIndex,
        tmnxCardSlotNum
    }
    ::= { tmnxCardTable 1 }

TmnxCardEntry                    ::= SEQUENCE
{
    tmnxCardSlotNum                  TmnxSlotNum,
    tmnxCardSupportedTypes           TmnxCardSuppType,
    tmnxCardAllowedTypes             TmnxCardType,
    tmnxCardAssignedType             TmnxCardType,
    tmnxCardEquippedType             TmnxCardType,
    tmnxCardHwIndex                  TmnxHwIndex,
    tmnxCardClockSource              TItemDescription,
    tmnxCardNumMdaSlots              Unsigned32,
    tmnxCardNumMdas                  Unsigned32,
    tmnxCardReboot                   TmnxCardRebootType,
    tmnxCardMemorySize               Unsigned32,
    tmnxCardNamedPoolAdminMode       TmnxAdminState,
    tmnxCardNamedPoolOperMode        TmnxAdminState,
    tmnxCardSoftReset                TmnxActionType,
    tmnxCardLastBootupReason         INTEGER,
    tmnxCardCmplx1IngrFcsOccur       Counter32,
    tmnxCardCmplx1IngrFcsOccurTime   TimeStamp,
    tmnxCardCmplx1EgrFcsOccur        Counter32,
    tmnxCardCmplx1EgrFcsOccurTime    TimeStamp,
    tmnxCardCmplx2IngrFcsOccur       Counter32,
    tmnxCardCmplx2IngrFcsOccurTime   TimeStamp,
    tmnxCardCmplx2EgrFcsOccur        Counter32,
    tmnxCardCmplx2EgrFcsOccurTime    TimeStamp,
    tmnxCardCmplx1MemParityOccur     Counter32,
    tmnxCardCmplx1MemParityOccurTime TimeStamp,
    tmnxCardCmplx2MemParityOccur     Counter32,
    tmnxCardCmplx2MemParityOccurTime TimeStamp,
    tmnxCardCapability               BITS,
    tmnxCardCmplx1CAMErrorOccur      Counter32,
    tmnxCardCmplx1CAMErrorOccurTime  TimeStamp,
    tmnxCardCmplx2CAMErrorOccur      Counter32,
    tmnxCardCmplx2CAMErrorOccurTime  TimeStamp,
    tmnxCardFailOnError              BITS,
    tmnxCardCmplx1EgrFcsSrcSlots     TmnxCardSlotBitMap,
    tmnxCardCmplx2EgrFcsSrcSlots     TmnxCardSlotBitMap,
    tmnxCardHardResetUnsupMdas       TruthValue,
    tmnxCardCmpl1BufMemErrOccur      Counter32,
    tmnxCardCmpl1BufMemErrOccurTime  TimeStamp,
    tmnxCardCmpl2BufMemErrOccur      Counter32,
    tmnxCardCmpl2BufMemErrOccurTime  TimeStamp,
    tmnxCardCmpl1StatMemErrOccur     Counter32,
    tmnxCardCmpl1StatMemErrOccurTime TimeStamp,
    tmnxCardCmpl2StatMemErrOccur     Counter32,
    tmnxCardCmpl2StatMemErrOccurTime TimeStamp,
    tmnxCardCmpl1IntMemErrOccur      Counter32,
    tmnxCardCmpl1IntMemErrOccurTime  TimeStamp,
    tmnxCardCmpl2IntMemErrOccur      Counter32,
    tmnxCardCmpl2IntMemErrOccurTime  TimeStamp,
    tmnxCardCmpl1ChipIfDownOcc       Counter32,
    tmnxCardCmpl1ChipIfDownOccTime   TimeStamp,
    tmnxCardCmpl2ChipIfDownOcc       Counter32,
    tmnxCardCmpl2ChipIfDownOccTime   TimeStamp,
    tmnxCardCmpl1ChipIfCellOcc       Counter32,
    tmnxCardCmpl1ChipIfCellOccTime   TimeStamp,
    tmnxCardCmpl2ChipIfCellOcc       Counter32,
    tmnxCardCmpl2ChipIfCellOccTime   TimeStamp,
    tmnxCardResetOnRecoverableError  TruthValue,
    tmnxCardVmHypervisor             TItemDescription,
    tmnxCardVmCpu                    TItemDescription,
    tmnxCardVmNumCores               Unsigned32,
    tmnxCardAssignedLevel            TmnxCardFunctionalLevel,
    tmnxCardEquippedLevel            TmnxCardFunctionalLevel,
    tmnxCardLicensedLevel            TmnxCardFunctionalLevel,
    tmnxCardLicensedBandwidth        Unsigned32,
    tmnxCardFilterScaleProfile       TmnxCardFilterProfile,
    tmnxCardPowerSave                TruthValue,
    tmnxCardHashSeedShift            Unsigned32,
    tmnxCardNumEquippedXioms         Unsigned32
}

tmnxCardSlotNum                  OBJECT-TYPE
    SYNTAX      TmnxSlotNum
    MAX-ACCESS  not-accessible
    STATUS      current
    DESCRIPTION
        "The unique value which identifies this IOM slot within a chassis in
         the system."
    ::= { tmnxCardEntry 1 }

tmnxCardSupportedTypes           OBJECT-TYPE
    SYNTAX      TmnxCardSuppType
    MAX-ACCESS  read-only
    STATUS      current
    DESCRIPTION
        "A bit-mask that indicates what card types can be physically supported
         in this IOM slot in this chassis."
    ::= { tmnxCardEntry 2 }

tmnxCardAllowedTypes             OBJECT-TYPE
    SYNTAX      TmnxCardType
    MAX-ACCESS  read-write
    STATUS      obsolete
    DESCRIPTION
        "A bit-mask that specifies what IOM card types the administrator
         has designated be allowed to be inserted into this slot.
         If the slot has not been pre-provisioned and a card that
         does not match one of the allowed types is inserted into
         this slot, a mismatch alarm will be raised.  If a specific
         value has not yet been SET by the manager, tmnxCardAllowedTypes
         will return the same value to a GET request as
         tmnxCardSupportedTypes.

         The object was made obsolete in the 3.0 release."
    ::= { tmnxCardEntry 3 }

tmnxCardAssignedType             OBJECT-TYPE
    SYNTAX      TmnxCardType
    MAX-ACCESS  read-write
    STATUS      current
    DESCRIPTION
        "The tmnxCardAssignedType specifies the administratively assigned
         (pre-provisioned) IOM card type defined in the tmnxCardTypeTable that
         should occupy this slot in this chassis.  If tmnxCardAssignedType has
         a value of 1 (unassigned), this slot has not yet been pre-provisioned."
    DEFVAL      { 1 }
    ::= { tmnxCardEntry 4 }

tmnxCardEquippedType             OBJECT-TYPE
    SYNTAX      TmnxCardType
    MAX-ACCESS  read-only
    STATUS      current
    DESCRIPTION
        "The tmnxCardEquippedType indicates the IOM card type that is physically
         inserted into this slot in this chassis.  If the slot has been
         pre-provisioned, tmnxCardAssignedType is not equal to 1 (unassigned),
         and the value of tmnxCardEquippedType is not the same as
         tmnxCardAssignedType, a mismatch alarm will be raised.

         A value of 0 indicates the IOM card type is not recognized by the
         software."
    ::= { tmnxCardEntry 5 }

tmnxCardHwIndex                  OBJECT-TYPE
    SYNTAX      TmnxHwIndex
    MAX-ACCESS  read-only
    STATUS      current
    DESCRIPTION
        "The value of tmnxCardHwIndex is the index into the tmnxHwTable for the
         row entry that represents the hardware component information for this
         IOM card."
    ::= { tmnxCardEntry 6 }

tmnxCardClockSource              OBJECT-TYPE
    SYNTAX      TItemDescription
    MAX-ACCESS  read-only
    STATUS      current
    DESCRIPTION
        "The clock source used by the IOM card in this slot."
    ::= { tmnxCardEntry 10 }

tmnxCardNumMdaSlots              OBJECT-TYPE
    SYNTAX      Unsigned32
    MAX-ACCESS  read-only
    STATUS      current
    DESCRIPTION
        "The number of Media Dependent Adapter (MDA) slots available on this
         IOM card."
    ::= { tmnxCardEntry 11 }

tmnxCardNumMdas                  OBJECT-TYPE
    SYNTAX      Unsigned32
    MAX-ACCESS  read-only
    STATUS      current
    DESCRIPTION
        "The number of Media Dependent Adapters installed on this IOM card."
    ::= { tmnxCardEntry 12 }

tmnxCardReboot                   OBJECT-TYPE
    SYNTAX      TmnxCardRebootType
    MAX-ACCESS  read-write
    STATUS      current
    DESCRIPTION
        "Setting this variable to 'cardReset' causes the IOM card to execute a
         soft-reboot. Setting this variable to 'cardPowerCycle' causes the IOM
         to turn off and turn on power to the card initiating a hard-reboot."
    DEFVAL      { notApplicable }
    ::= { tmnxCardEntry 13 }

tmnxCardMemorySize               OBJECT-TYPE
    SYNTAX      Unsigned32
    UNITS       "Megabytes"
    MAX-ACCESS  read-only
    STATUS      current
    DESCRIPTION
        "The value of tmnxCardMemorySize indicates the amount of memory, in
         megabytes, populated on this IOM card."
    ::= { tmnxCardEntry 14 }

tmnxCardNamedPoolAdminMode       OBJECT-TYPE
    SYNTAX      TmnxAdminState
    MAX-ACCESS  read-write
    STATUS      obsolete
    DESCRIPTION
        "The value of tmnxCardNamedPoolAdminMode specifies whether or not an
         IOM is provisioned for the configuration of named pools. If the value
         of tmnxCardNamedPoolAdminMode is 'inService(2)', the system will
         change the way default pools are created and allow for the creation of
         MDA and port level named buffer pools. If the value of
         tmnxCardNamedPoolAdminMode is 'outOfService(3)', the system will not
         create per port pools, instead a default network and access pool is
         created for ingress and egress and is shared by queues on all ports.
         This object is used in conjunction with tmnxCardNamedPoolOperMode."
    DEFVAL      { outOfService }
    ::= { tmnxCardEntry 15 }

tmnxCardNamedPoolOperMode        OBJECT-TYPE
    SYNTAX      TmnxAdminState
    MAX-ACCESS  read-only
    STATUS      obsolete
    DESCRIPTION
        "The value of tmnxCardNamedPoolOperMode indicates whether or not an IOM
         provisioned with tmnxCardNamedPoolAdminMode to a value of
         'inService(2)' will actively use named pools or not. A value of
         'outOfService(3) means that the named pool configurations will not be
         downloaded to the IOM until after a reset of the IOM is performed. A
         value of 'inService(2)' means that the named pool configurations are
         programmed by the IOM. On systems using a separate CPM and IOM
         combination the value of tmnxCardNamedPoolOperMode and
         tmnxCardNamedPoolAdminMode will always be in sync due to a mandatory
         reboot of the IOM. On systems using a combined image (CFM) these
         values will be out-of-sync until the chassis is rebooted."
    DEFVAL      { outOfService }
    ::= { tmnxCardEntry 16 }

tmnxCardSoftReset                OBJECT-TYPE
    SYNTAX      TmnxActionType
    MAX-ACCESS  read-write
    STATUS      current
    DESCRIPTION
        "The value of tmnxCardSoftReset, when set to 'doAction(1)', causes the
         IOM card to re-initialize the applications and protocols running on
         the card with limited traffic impact."
    DEFVAL      { notApplicable }
    ::= { tmnxCardEntry 17 }

tmnxCardLastBootupReason         OBJECT-TYPE
    SYNTAX      INTEGER {
        hardReboot           (0),
        softReset            (1),
        powerCycle           (2),
        clearCard            (3),
        activitySwitch       (4),
        configChange         (5),
        runtimeFail          (6),
        bootFail             (7),
        unexpected           (8),
        issuTimeout          (9),
        reinserted           (10),
        issuHardReboot       (11),
        ccmFail              (12),
        powerChange          (13),
        levelChange          (14),
        sfmFailRecovery      (15),
        osSecAntiTheftChange (16)
    }
    MAX-ACCESS  read-only
    STATUS      current
    DESCRIPTION
        "The value of tmnxCardLastBootupReason indicates the type of the last
         reboot/reset of the IOM card.

         Not all reasons exist in all software versions.

         hardReboot      - new/different card inserted for first time
         softReset       - user initiated soft reset
         powerCycle      - user initiated power cycle
         clearCard       - user initiated clear card
         activitySwitch  - card rebooted during activity switch
         configChange    - configuration change forced a reboot
         runtimeFail     - card failed while running and was rebooted
         bootFail        - card failed during boot and was rebooted
         unexpected      - card unexpectedly rebooted
         issuTimeout     - ISSU timeout timer expired
         reinserted      - card was removed and reinserted
         issuHardReboot  - card rebooted during ISSU upgrade
                              (soft reset ineligible)
         ccmFail         - Chassis Control Module (CCM) failed.
         powerChange     - Power availability changed.
         levelChange     - Licensed level changed.
         sfmFailRecovery - SFM failure recovery rebooted the card.
         osSecAntiTheftChange - card rebooted during os-security/anti-theft change."
    ::= { tmnxCardEntry 18 }

tmnxCardCmplx1IngrFcsOccur       OBJECT-TYPE
    SYNTAX      Counter32
    MAX-ACCESS  read-only
    STATUS      obsolete
    DESCRIPTION
        "The value of tmnxCardCmplx1IngrFcsOccur indicates the number of times
         the first complex experienced an occurrence of an FCS error in the
         ingress direction since startup, last clear, or IOM reboot.

         This object was obsoleted in release 16.0. A replacement was added to
         tmnxCardComplexStatsTable."
    ::= { tmnxCardEntry 19 }

tmnxCardCmplx1IngrFcsOccurTime   OBJECT-TYPE
    SYNTAX      TimeStamp
    MAX-ACCESS  read-only
    STATUS      obsolete
    DESCRIPTION
        "The value of tmnxCardCmplx1IngrFcsOccurTime indicates the last time
         tmnxCardCmplx1IngrFcsOccur incremented.

         This object was obsoleted in release 16.0. A replacement was added to
         tmnxCardComplexStatsTable."
    ::= { tmnxCardEntry 20 }

tmnxCardCmplx1EgrFcsOccur        OBJECT-TYPE
    SYNTAX      Counter32
    MAX-ACCESS  read-only
    STATUS      obsolete
    DESCRIPTION
        "The value of tmnxCardCmplx1EgrFcsOccur indicates the number of times
         the first complex experienced an occurrence of an FCS error in the
         egress direction since startup, last clear, or IOM reboot.

         This object was obsoleted in release 16.0. A replacement was added to
         tmnxCardComplexStatsTable."
    ::= { tmnxCardEntry 21 }

tmnxCardCmplx1EgrFcsOccurTime    OBJECT-TYPE
    SYNTAX      TimeStamp
    MAX-ACCESS  read-only
    STATUS      obsolete
    DESCRIPTION
        "The value of tmnxCardCmplx1EgrFcsOccurTime indicates the last time
         tmnxCardCmplx1EgrFcsOccur incremented.

         This object was obsoleted in release 16.0. A replacement was added to
         tmnxCardComplexStatsTable."
    ::= { tmnxCardEntry 22 }

tmnxCardCmplx2IngrFcsOccur       OBJECT-TYPE
    SYNTAX      Counter32
    MAX-ACCESS  read-only
    STATUS      obsolete
    DESCRIPTION
        "The value of tmnxCardCmplx2IngrFcsOccur indicates the number of times
         the second complex experienced an occurrence of an FCS error in the
         ingress direction since startup, last clear, or IOM reboot.

         This object was obsoleted in release 16.0. A replacement was added to
         tmnxCardComplexStatsTable."
    ::= { tmnxCardEntry 23 }

tmnxCardCmplx2IngrFcsOccurTime   OBJECT-TYPE
    SYNTAX      TimeStamp
    MAX-ACCESS  read-only
    STATUS      obsolete
    DESCRIPTION
        "The value of tmnxCardCmplx2IngrFcsOccurTime indicates the last time
         tmnxCardCmplx2IngrFcsOccur incremented.

         This object was obsoleted in release 16.0. A replacement was added to
         tmnxCardComplexStatsTable."
    ::= { tmnxCardEntry 24 }

tmnxCardCmplx2EgrFcsOccur        OBJECT-TYPE
    SYNTAX      Counter32
    MAX-ACCESS  read-only
    STATUS      obsolete
    DESCRIPTION
        "The value of tmnxCardCmplx2EgrFcsOccur indicates the number of times
         the second complex experienced an occurrence of an FCS error in the
         egress direction since startup, last clear, or IOM reboot.

         This object was obsoleted in release 16.0. A replacement was added to
         tmnxCardComplexStatsTable."
    ::= { tmnxCardEntry 25 }

tmnxCardCmplx2EgrFcsOccurTime    OBJECT-TYPE
    SYNTAX      TimeStamp
    MAX-ACCESS  read-only
    STATUS      obsolete
    DESCRIPTION
        "The value of tmnxCardCmplx2EgrFcsOccurTime indicates the last time
         tmnxCardCmplx2EgrFcsOccur incremented.

         This object was obsoleted in release 16.0. A replacement was added to
         tmnxCardComplexStatsTable."
    ::= { tmnxCardEntry 26 }

tmnxCardCmplx1MemParityOccur     OBJECT-TYPE
    SYNTAX      Counter32
    MAX-ACCESS  read-only
    STATUS      obsolete
    DESCRIPTION
        "The value of tmnxCardCmplx1MemParityOccur indicates the number of
         times the first complex experienced an occurrence of a memory parity
         error since startup, last clear, or IOM reboot.

         This object was obsoleted in release 16.0. A replacement was added to
         tmnxCardComplexStatsTable."
    ::= { tmnxCardEntry 27 }

tmnxCardCmplx1MemParityOccurTime OBJECT-TYPE
    SYNTAX      TimeStamp
    MAX-ACCESS  read-only
    STATUS      obsolete
    DESCRIPTION
        "The value of tmnxCardCmplx1MemParityOccurTime indicates the last time
         tmnxCardCmplx1MemParityOccur incremented.

         This object was obsoleted in release 16.0. A replacement was added to
         tmnxCardComplexStatsTable."
    ::= { tmnxCardEntry 28 }

tmnxCardCmplx2MemParityOccur     OBJECT-TYPE
    SYNTAX      Counter32
    MAX-ACCESS  read-only
    STATUS      obsolete
    DESCRIPTION
        "The value of tmnxCardCmplx2MemParityOccur indicates the number of
         times the second complex experienced an occurrence of a memory parity
         error since startup, last clear, or IOM reboot.

         This object was obsoleted in release 16.0. A replacement was added to
         tmnxCardComplexStatsTable."
    ::= { tmnxCardEntry 29 }

tmnxCardCmplx2MemParityOccurTime OBJECT-TYPE
    SYNTAX      TimeStamp
    MAX-ACCESS  read-only
    STATUS      obsolete
    DESCRIPTION
        "The value of tmnxCardCmplx2MemParityOccurTime indicates the last time
         tmnxCardCmplx2MemParityOccur incremented.

         This object was obsoleted in release 16.0. A replacement was added to
         tmnxCardComplexStatsTable."
    ::= { tmnxCardEntry 30 }

tmnxCardCapability               OBJECT-TYPE
    SYNTAX      BITS {
        sr (0)
    }
    MAX-ACCESS  read-write
    STATUS      obsolete
    DESCRIPTION
        "The value of tmnxCardCapability indicates special capabilities that
         are set on this card.

         tmnxCardCapability is a bitmap with the following values:
            'sr': Enable SR capabilities on this card. "
    ::= { tmnxCardEntry 31 }

tmnxCardCmplx1CAMErrorOccur      OBJECT-TYPE
    SYNTAX      Counter32
    MAX-ACCESS  read-only
    STATUS      obsolete
    DESCRIPTION
        "The value of tmnxCardCmplx1CAMErrorOccur indicates the number of times
         the first complex experienced an occurrence of a CAM error since
         startup, last clear, or IOM reboot.

         This object was obsoleted in release 16.0. A replacement was added to
         tmnxCardComplexStatsTable."
    ::= { tmnxCardEntry 32 }

tmnxCardCmplx1CAMErrorOccurTime  OBJECT-TYPE
    SYNTAX      TimeStamp
    MAX-ACCESS  read-only
    STATUS      obsolete
    DESCRIPTION
        "The value of tmnxCardCmplx1CAMErrorOccurTime indicates the last time
         tmnxCardCmplx1CAMErrorOccur incremented.

         This object was obsoleted in release 16.0. A replacement was added to
         tmnxCardComplexStatsTable."
    ::= { tmnxCardEntry 33 }

tmnxCardCmplx2CAMErrorOccur      OBJECT-TYPE
    SYNTAX      Counter32
    MAX-ACCESS  read-only
    STATUS      obsolete
    DESCRIPTION
        "The value of tmnxCardCmplx2CAMErrorOccur indicates the number of times
         the second complex experienced an occurrence of a CAM error since
         startup, last clear, or IOM reboot.

         This object was obsoleted in release 16.0. A replacement was added to
         tmnxCardComplexStatsTable."
    ::= { tmnxCardEntry 34 }

tmnxCardCmplx2CAMErrorOccurTime  OBJECT-TYPE
    SYNTAX      TimeStamp
    MAX-ACCESS  read-only
    STATUS      obsolete
    DESCRIPTION
        "The value of tmnxCardCmplx2CAMErrorOccurTime indicates the last time
         tmnxCardCmplx2CAMErrorOccur incremented.

         This object was obsoleted in release 16.0. A replacement was added to
         tmnxCardComplexStatsTable."
    ::= { tmnxCardEntry 35 }

tmnxCardFailOnError              OBJECT-TYPE
    SYNTAX      BITS {
        memoryEventGroupA (0)
    }
    MAX-ACCESS  read-write
    STATUS      current
    DESCRIPTION
        "The value of tmnxCardFailOnError specifies the set of events that, if
         triggered, will cause the card to fail. The suppression or generation
         of the NOTIFICATION-TYPE event is independent of the card failing.

         The following set of events are configurable:
              memoryEventGroupA (0) - tmnxEqCardPChipMemoryEvent
                                      tmnxEqCardPChipCamEvent
                                      tmnxEqCardPChipError
                                      tmnxEqCardQChipBufMemoryEvent
                                      tmnxEqCardQChipStatsMemoryEvent
                                      tmnxEqCardQChipIntMemoryEvent
                                      tmnxEqCardChipIfCellEvent

         tmnxEqCardPChipError will only cause a card failure if all MDAs(s) on
         the complex are Ethernet or ISAs."
    DEFVAL      { {} }
    ::= { tmnxCardEntry 36 }

tmnxCardCmplx1EgrFcsSrcSlots     OBJECT-TYPE
    SYNTAX      TmnxCardSlotBitMap
    MAX-ACCESS  read-only
    STATUS      obsolete
    DESCRIPTION
        "The value of tmnxCardCmplx1EgrFcsSrcSlots indicates the source slots
         reported from the last time tmnxCardCmplx1EgrFcsOccur incremented.

         This object was obsoleted in release 16.0. A replacement was added to
         tmnxCardComplexStatsTable."
    ::= { tmnxCardEntry 37 }

tmnxCardCmplx2EgrFcsSrcSlots     OBJECT-TYPE
    SYNTAX      TmnxCardSlotBitMap
    MAX-ACCESS  read-only
    STATUS      obsolete
    DESCRIPTION
        "The value of tmnxCardCmplx2EgrFcsSrcSlots indicates the source slots
         reported from the last time tmnxCardCmplx2EgrFcsOccur incremented.

         This object was obsoleted in release 16.0. A replacement was added to
         tmnxCardComplexStatsTable."
    ::= { tmnxCardEntry 38 }

tmnxCardHardResetUnsupMdas       OBJECT-TYPE
    SYNTAX      TruthValue
    MAX-ACCESS  read-write
    STATUS      current
    DESCRIPTION
        "The value of tmnxCardHardResetUnsupMdas specifies whether to do hard
         reset of the soft reset incapable MDAs as part setting 'doAction' to
         tmnxCardSoftReset object."
    DEFVAL      { false }
    ::= { tmnxCardEntry 39 }

tmnxCardCmpl1BufMemErrOccur      OBJECT-TYPE
    SYNTAX      Counter32
    MAX-ACCESS  read-only
    STATUS      obsolete
    DESCRIPTION
        "The value of tmnxCardCmpl1BufMemErrOccur indicates the number of times
         the first complex experienced an occurrence of a buffer memory error
         since startup, last clear, or IOM reboot.

         This object was obsoleted in release 16.0. A replacement was added to
         tmnxCardComplexStatsTable."
    ::= { tmnxCardEntry 40 }

tmnxCardCmpl1BufMemErrOccurTime  OBJECT-TYPE
    SYNTAX      TimeStamp
    MAX-ACCESS  read-only
    STATUS      obsolete
    DESCRIPTION
        "The value of tmnxCardCmpl1BufMemErrOccurTime indicates the last time
         tmnxCardCmpl1BufMemErrOccur incremented.

         This object was obsoleted in release 16.0. A replacement was added to
         tmnxCardComplexStatsTable."
    ::= { tmnxCardEntry 41 }

tmnxCardCmpl2BufMemErrOccur      OBJECT-TYPE
    SYNTAX      Counter32
    MAX-ACCESS  read-only
    STATUS      obsolete
    DESCRIPTION
        "The value of tmnxCardCmpl2BufMemErrOccur indicates the number of times
         the second complex experienced an occurrence of a buffer memory error
         since startup, last clear, or IOM reboot.

         This object was obsoleted in release 16.0. A replacement was added to
         tmnxCardComplexStatsTable."
    ::= { tmnxCardEntry 42 }

tmnxCardCmpl2BufMemErrOccurTime  OBJECT-TYPE
    SYNTAX      TimeStamp
    MAX-ACCESS  read-only
    STATUS      obsolete
    DESCRIPTION
        "The value of tmnxCardCmpl2BufMemErrOccurTime indicates the last time
         tmnxCardCmpl2BufMemErrOccur incremented.

         This object was obsoleted in release 16.0. A replacement was added to
         tmnxCardComplexStatsTable."
    ::= { tmnxCardEntry 43 }

tmnxCardCmpl1StatMemErrOccur     OBJECT-TYPE
    SYNTAX      Counter32
    MAX-ACCESS  read-only
    STATUS      obsolete
    DESCRIPTION
        "The value of tmnxCardCmpl1StatMemErrOccur indicates the number of
         times the first complex experienced an occurrence of a statistics
         memory error since startup, last clear, or IOM reboot.

         This object was obsoleted in release 16.0. A replacement was added to
         tmnxCardComplexStatsTable."
    ::= { tmnxCardEntry 44 }

tmnxCardCmpl1StatMemErrOccurTime OBJECT-TYPE
    SYNTAX      TimeStamp
    MAX-ACCESS  read-only
    STATUS      obsolete
    DESCRIPTION
        "The value of tmnxCardCmpl1StatMemErrOccurTime indicates the last time
         tmnxCardCmpl1StatMemErrOccur incremented.

         This object was obsoleted in release 16.0. A replacement was added to
         tmnxCardComplexStatsTable."
    ::= { tmnxCardEntry 45 }

tmnxCardCmpl2StatMemErrOccur     OBJECT-TYPE
    SYNTAX      Counter32
    MAX-ACCESS  read-only
    STATUS      obsolete
    DESCRIPTION
        "The value of tmnxCardCmpl2StatMemErrOccur indicates the number of
         times the second complex experienced an occurrence of a statistics
         memory error since startup, last clear, or IOM reboot.

         This object was obsoleted in release 16.0. A replacement was added to
         tmnxCardComplexStatsTable."
    ::= { tmnxCardEntry 46 }

tmnxCardCmpl2StatMemErrOccurTime OBJECT-TYPE
    SYNTAX      TimeStamp
    MAX-ACCESS  read-only
    STATUS      obsolete
    DESCRIPTION
        "The value of tmnxCardCmpl2StatMemErrOccurTime indicates the last time
         tmnxCardCmpl2StatMemErrOccur incremented.

         This object was obsoleted in release 16.0. A replacement was added to
         tmnxCardComplexStatsTable."
    ::= { tmnxCardEntry 47 }

tmnxCardCmpl1IntMemErrOccur      OBJECT-TYPE
    SYNTAX      Counter32
    MAX-ACCESS  read-only
    STATUS      obsolete
    DESCRIPTION
        "The value of tmnxCardCmpl1IntMemErrOccur indicates the number of times
         the first complex experienced an occurrence of an internal memory
         error since startup, last clear, or IOM reboot.

         This object was obsoleted in release 16.0. A replacement was added to
         tmnxCardComplexStatsTable."
    ::= { tmnxCardEntry 48 }

tmnxCardCmpl1IntMemErrOccurTime  OBJECT-TYPE
    SYNTAX      TimeStamp
    MAX-ACCESS  read-only
    STATUS      obsolete
    DESCRIPTION
        "The value of tmnxCardCmpl1IntMemErrOccurTime indicates the last time
         tmnxCardCmpl1IntMemErrOccur incremented.

         This object was obsoleted in release 16.0. A replacement was added to
         tmnxCardComplexStatsTable."
    ::= { tmnxCardEntry 49 }

tmnxCardCmpl2IntMemErrOccur      OBJECT-TYPE
    SYNTAX      Counter32
    MAX-ACCESS  read-only
    STATUS      obsolete
    DESCRIPTION
        "The value of tmnxCardCmpl2IntMemErrOccur indicates the number of times
         the second complex experienced an occurrence of an internal memory
         error since startup, last clear, or IOM reboot.

         This object was obsoleted in release 16.0. A replacement was added to
         tmnxCardComplexStatsTable."
    ::= { tmnxCardEntry 50 }

tmnxCardCmpl2IntMemErrOccurTime  OBJECT-TYPE
    SYNTAX      TimeStamp
    MAX-ACCESS  read-only
    STATUS      obsolete
    DESCRIPTION
        "The value of tmnxCardCmpl2IntMemErrOccurTime indicates the last time
         tmnxCardCmpl2IntMemErrOccur incremented.

         This object was obsoleted in release 16.0. A replacement was added to
         tmnxCardComplexStatsTable."
    ::= { tmnxCardEntry 51 }

tmnxCardCmpl1ChipIfDownOcc       OBJECT-TYPE
    SYNTAX      Counter32
    MAX-ACCESS  read-only
    STATUS      obsolete
    DESCRIPTION
        "The value of tmnxCardCmpl1ChipIfDownOcc indicates the number of times
         the first complex experienced an occurrence of an internal datapath
         problem.

         This object was obsoleted in release 16.0. A replacement was added to
         tmnxCardComplexStatsTable."
    ::= { tmnxCardEntry 52 }

tmnxCardCmpl1ChipIfDownOccTime   OBJECT-TYPE
    SYNTAX      TimeStamp
    MAX-ACCESS  read-only
    STATUS      obsolete
    DESCRIPTION
        "The value of tmnxCardCmpl1ChipIfDownOccTime indicates the last time
         tmnxCardCmpl1ChipIfDownOcc incremented.

         This object was obsoleted in release 16.0. A replacement was added to
         tmnxCardComplexStatsTable."
    ::= { tmnxCardEntry 53 }

tmnxCardCmpl2ChipIfDownOcc       OBJECT-TYPE
    SYNTAX      Counter32
    MAX-ACCESS  read-only
    STATUS      obsolete
    DESCRIPTION
        "The value of tmnxCardCmpl2ChipIfDownOcc indicates the number of times
         the second complex experienced an occurrence of an internal datapath
         problem.

         This object was obsoleted in release 16.0. A replacement was added to
         tmnxCardComplexStatsTable."
    ::= { tmnxCardEntry 54 }

tmnxCardCmpl2ChipIfDownOccTime   OBJECT-TYPE
    SYNTAX      TimeStamp
    MAX-ACCESS  read-only
    STATUS      obsolete
    DESCRIPTION
        "The value of tmnxCardCmpl2ChipIfDownOccTime indicates the last time
         tmnxCardCmpl2ChipIfDownOcc incremented.

         This object was obsoleted in release 16.0. A replacement was added to
         tmnxCardComplexStatsTable."
    ::= { tmnxCardEntry 55 }

tmnxCardCmpl1ChipIfCellOcc       OBJECT-TYPE
    SYNTAX      Counter32
    MAX-ACCESS  read-only
    STATUS      obsolete
    DESCRIPTION
        "The value of tmnxCardCmpl1ChipIfCellOcc indicates the number of times
         the first complex experienced an occurrence of internal datapath cell
         errors.

         This object was obsoleted in release 16.0. A replacement was added to
         tmnxCardComplexStatsTable."
    ::= { tmnxCardEntry 56 }

tmnxCardCmpl1ChipIfCellOccTime   OBJECT-TYPE
    SYNTAX      TimeStamp
    MAX-ACCESS  read-only
    STATUS      obsolete
    DESCRIPTION
        "The value of tmnxCardCmpl1ChipIfCellOccTime indicates the last time
         tmnxCardCmpl1ChipIfCellOcc incremented.

         This object was obsoleted in release 16.0. A replacement was added to
         tmnxCardComplexStatsTable."
    ::= { tmnxCardEntry 57 }

tmnxCardCmpl2ChipIfCellOcc       OBJECT-TYPE
    SYNTAX      Counter32
    MAX-ACCESS  read-only
    STATUS      obsolete
    DESCRIPTION
        "The value of tmnxCardCmpl2ChipIfCellOcc indicates the number of times
         the second complex experienced an occurrence of internal datapath cell
         errors.

         This object was obsoleted in release 16.0. A replacement was added to
         tmnxCardComplexStatsTable."
    ::= { tmnxCardEntry 58 }

tmnxCardCmpl2ChipIfCellOccTime   OBJECT-TYPE
    SYNTAX      TimeStamp
    MAX-ACCESS  read-only
    STATUS      obsolete
    DESCRIPTION
        "The value of tmnxCardCmpl2ChipIfCellOccTime indicates the last time
         tmnxCardCmpl2ChipIfCellOcc incremented.

         This object was obsoleted in release 16.0. A replacement was added to
         tmnxCardComplexStatsTable."
    ::= { tmnxCardEntry 59 }

tmnxCardResetOnRecoverableError  OBJECT-TYPE
    SYNTAX      TruthValue
    MAX-ACCESS  read-write
    STATUS      current
    DESCRIPTION
        "The value of tmnxCardResetOnRecoverableError specifies whether or not
         the system resets the card when there are fatal memory parity errors
         on one of the Q-chips on that card.

         If the value of tmnxCardResetOnRecoverableError is 'true (1)' and
         there is a fatal memory parity error on a Q-chip, the system will
         reset the card but not fail it, even if tmnxCardFailOnError is 'true
         (1)'."
    DEFVAL      { false }
    ::= { tmnxCardEntry 60 }

tmnxCardVmHypervisor             OBJECT-TYPE
    SYNTAX      TItemDescription
    MAX-ACCESS  read-only
    STATUS      obsolete
    DESCRIPTION
        "The value of tmnxCardVmHypervisor indicates the name of the
         hypervisor.

         The value of this object is only relevant in a virtual machine
         implementation."
    DEFVAL      { "" }
    ::= { tmnxCardEntry 61 }

tmnxCardVmCpu                    OBJECT-TYPE
    SYNTAX      TItemDescription
    MAX-ACCESS  read-only
    STATUS      obsolete
    DESCRIPTION
        "The value of tmnxCardVmCpu indicates the description of the CPU.

         The value of this object is only relevant in a virtual machine
         implementation."
    DEFVAL      { "" }
    ::= { tmnxCardEntry 62 }

tmnxCardVmNumCores               OBJECT-TYPE
    SYNTAX      Unsigned32
    MAX-ACCESS  read-only
    STATUS      obsolete
    DESCRIPTION
        "The value of tmnxCardVmNumCores indicates the number of processor
         cores available.

         The value of this object is only relevant in a virtual machine
         implementation."
    ::= { tmnxCardEntry 63 }

tmnxCardAssignedLevel            OBJECT-TYPE
    SYNTAX      TmnxCardFunctionalLevel
    MAX-ACCESS  read-write
    STATUS      current
    DESCRIPTION
        "An integer that specifies the administratively assigned
         (pre-provisioned) Card functional level variant that should occupy
         this slot in this chassis."
    DEFVAL      { unrestricted }
    ::= { tmnxCardEntry 64 }

tmnxCardEquippedLevel            OBJECT-TYPE
    SYNTAX      TmnxCardFunctionalLevel
    MAX-ACCESS  read-only
    STATUS      current
    DESCRIPTION
        "An integer that indicates the card functional-level variant that is
         physically inserted into this slot in this chassis.  If the value of
         tmnxCardAssignedLevel is not equal to the value of
         tmnxCardEquippedLevel, a mismatch alarm will be raised."
    ::= { tmnxCardEntry 65 }

tmnxCardLicensedLevel            OBJECT-TYPE
    SYNTAX      TmnxCardFunctionalLevel
    MAX-ACCESS  read-only
    STATUS      current
    DESCRIPTION
        "An integer that indicates the card functional-level that is licensed
         for this slot in this chassis."
    ::= { tmnxCardEntry 66 }

tmnxCardLicensedBandwidth        OBJECT-TYPE
    SYNTAX      Unsigned32
    UNITS       "gigabps"
    MAX-ACCESS  read-only
    STATUS      current
    DESCRIPTION
        "Indicates the amount of licensed bandwidth that is used on the
         card for this slot in this chassis. Bandwidth becomes licensed as
         physical connectors are provisioned or physical ports are enabled.
         Licensed bandwidth on cards that have multiple functional levels
         supported.  The system enforces that the licensed bandwidth does
         not exceed any bandwidth restriction associated with this card's
         licensed level."
    ::= { tmnxCardEntry 67 }

tmnxCardFilterScaleProfile       OBJECT-TYPE
    SYNTAX      TmnxCardFilterProfile
    MAX-ACCESS  read-write
    STATUS      current
    DESCRIPTION
        "The value of tmnxCardFilterScaleProfile specifies the filter
         allocation profile for the card. A profiles modifies the IPv4 and IPv6
         ingress/egress filter allocation."
    DEFVAL      { none }
    ::= { tmnxCardEntry 68 }

tmnxCardPowerSave                OBJECT-TYPE
    SYNTAX      TruthValue
    MAX-ACCESS  read-write
    STATUS      current
    DESCRIPTION
        "The value of tmnxCardPowerSave specifies whether or not the system
         prevents the card from loading and keeps it in a low power mode. If
         the value of tmnxCardPowerSave is 'true (1)', the system will reset
         the card and keep it in a low power mode."
    DEFVAL      { false }
    ::= { tmnxCardEntry 69 }

tmnxCardHashSeedShift            OBJECT-TYPE
    SYNTAX      Unsigned32 (1..16)
    MAX-ACCESS  read-write
    STATUS      current
    DESCRIPTION
        "The value of tmnxCardHashSeedShift specifies the number of bits
         the hash seed result is shifted.  The hash seed result obtained
         by shifting up to 16 bits is used by the hash polynomial
         tmnxLoadBalancingHashEcmpPoly and tmnxLoadBalancingHashLagPoly,
         to optimize the load balancing distribution of packet flows
         under ECMP and LAG."
    DEFVAL      { 2 }
    ::= { tmnxCardEntry 70 }

tmnxCardNumEquippedXioms         OBJECT-TYPE
    SYNTAX      Unsigned32
    MAX-ACCESS  read-only
    STATUS      current
    DESCRIPTION
        "The value of tmnxCardNumEquippedXioms indicates the number of xioms
         equipped on this slot."
    ::= { tmnxCardEntry 71 }

tmnxCpmCardLastChange            OBJECT-TYPE
    SYNTAX      TimeStamp
    MAX-ACCESS  read-only
    STATUS      current
    DESCRIPTION
        "The value of sysUpTime when the tmnxCpmCardTable was last changed."
    ::= { tmnxCardObjs 3 }

tmnxCpmCardTable                 OBJECT-TYPE
    SYNTAX      SEQUENCE OF TmnxCpmCardEntry
    MAX-ACCESS  not-accessible
    STATUS      current
    DESCRIPTION
        "The tmnxCpmCardTable has an entry for each CPM card or module in each
         chassis in the TMNX system."
    ::= { tmnxCardObjs 4 }

tmnxCpmCardEntry                 OBJECT-TYPE
    SYNTAX      TmnxCpmCardEntry
    MAX-ACCESS  not-accessible
    STATUS      current
    DESCRIPTION
        "Each row entry represents a CPM card or module in a chassis in the
         system.  Entries cannot be created and deleted via SNMP SET
         operations.  When a tmnxChassisEntry is created, a tmnxCpmCardEntry
         is created for each CPM card or module in that chassis.  Before a
         tmnxChassisEntry can be deleted, each tmnxCpmCardEntry for that
         chassis must be in the proper state for removal."
    INDEX       {
        tmnxChassisIndex,
        tmnxCpmCardSlotNum,
        tmnxCpmCardNum
    }
    ::= { tmnxCpmCardTable 1 }

TmnxCpmCardEntry                 ::= SEQUENCE
{
    tmnxCpmCardSlotNum               TmnxSlotNum,
    tmnxCpmCardNum                   Unsigned32,
    tmnxCpmCardSupportedTypes        TmnxCardSuppType,
    tmnxCpmCardAllowedTypes          TmnxCardType,
    tmnxCpmCardAssignedType          TmnxCardType,
    tmnxCpmCardEquippedType          TmnxCardType,
    tmnxCpmCardHwIndex               TmnxHwIndex,
    tmnxCpmCardBootOptionVersion     TItemDescription,
    tmnxCpmCardBootOptionLastModified DateAndTime,
    tmnxCpmCardConfigBootedVersion   TItemDescription,
    tmnxCpmCardIndexBootedVersion    TItemDescription,
    tmnxCpmCardConfigLastModified    DateAndTime,
    tmnxCpmCardConfigLastSaved       DateAndTime,
    tmnxCpmCardRedundant             INTEGER,
    tmnxCpmCardClockSource           TItemDescription,
    tmnxCpmCardNumCpus               Unsigned32,
    tmnxCpmCardCpuType               INTEGER,
    tmnxCpmCardMemorySize            Unsigned32,
    tmnxCpmCardSwitchToRedundantCard TmnxActionType,
    tmnxCpmCardReboot                TmnxActionType,
    tmnxCpmCardRereadBootOptions     TmnxActionType,
    tmnxCpmCardConfigFileLastBooted  DisplayString,
    tmnxCpmCardConfigFileLastSaved   DisplayString,
    tmnxCpmCardConfigFileLastBootedHeader OCTET STRING,
    tmnxCpmCardIndexFileLastBootedHeader OCTET STRING,
    tmnxCpmCardBootOptionSource      DisplayString,
    tmnxCpmCardConfigSource          INTEGER,
    tmnxCpmCardBootOptionLastSaved   DateAndTime,
    tmnxCpmCardMasterSlaveRefState   INTEGER,
    tmnxCpmCardConfigUserLastModified SnmpAdminString,
    tmnxCpmCardCmplxCAMErrOccur      Counter32,
    tmnxCpmCardCmplxCAMErrOccurTime  TimeStamp,
    tmnxCpmCardOscillatorType        INTEGER,
    tmnxCpmCardCmplxMemErrOccur      Counter32,
    tmnxCpmCardCmplxMemErrOccurTime  TimeStamp,
    tmnxCpmCardCmplBufMemErrOcc      Counter32,
    tmnxCpmCardCmplBufMemErrOccTime  TimeStamp,
    tmnxCpmCardCmplStatMemErrOcc     Counter32,
    tmnxCpmCardCmplStatMemErrOccTime TimeStamp,
    tmnxCpmCardCmplIntMemErrOcc      Counter32,
    tmnxCpmCardCmplIntMemErrOccTime  TimeStamp,
    tmnxCpmCardCmplChipIfDownOcc     Counter32,
    tmnxCpmCardCmplChipIfDownOccTime TimeStamp,
    tmnxCpmCardCmplChipIfCellOcc     Counter32,
    tmnxCpmCardCmplChipIfCellOccTime TimeStamp,
    tmnxCpmCardRebootHold            TruthValue,
    tmnxCpmCardUuid                  TmnxUuid,
    tmnxCpmCardCmplxIngrFcsOccur     Counter32,
    tmnxCpmCardCmplxIngrFcsOccurTime TimeStamp,
    tmnxCpmCardCmplxEgrFcsOccur      Counter32,
    tmnxCpmCardCmplxEgrFcsOccurTime  TimeStamp,
    tmnxCpmCardCmplxEgrFcsSrcSlots   TmnxCardSlotBitMap,
    tmnxCpmCardVmHypervisor          TItemDescription,
    tmnxCpmCardVmCpu                 TItemDescription,
    tmnxCpmCardVmNumCores            Unsigned32,
    tmnxCpmCardAntiTheft             TmnxEnabledDisabled,
    tmnxCpmCardPwdPendingActivation  TruthValue
}

tmnxCpmCardSlotNum               OBJECT-TYPE
    SYNTAX      TmnxSlotNum
    MAX-ACCESS  not-accessible
    STATUS      current
    DESCRIPTION
        "The unique value which identifies this slot within a chassis in
         the system.  Depending upon the value of tmnxChassisType, this may
         represent a fabric slot or a regular card slot.  If this CPM module
         resides on a fabric card, tmnxCpmCardSlotNum has the value the
         corresponding tmnxFabricSlotNum.  If this is a CPM module on a
         fabric card, tmnxCpmCardSlotNum is the fabric slot number in the
         chassis where this CPM module is located.  Else if this is a
         CPM card, tmnxCpmCardSlotNum is a regular card slot number."
    ::= { tmnxCpmCardEntry 1 }

tmnxCpmCardNum                   OBJECT-TYPE
    SYNTAX      Unsigned32
    MAX-ACCESS  not-accessible
    STATUS      current
    DESCRIPTION
        "The unique value which identifies this CPM module within a specific
         card slot within a chassis in the system."
    ::= { tmnxCpmCardEntry 2 }

tmnxCpmCardSupportedTypes        OBJECT-TYPE
    SYNTAX      TmnxCardSuppType
    MAX-ACCESS  read-only
    STATUS      current
    DESCRIPTION
        "A bit-mask that indicates what CPM card types can be physically
         supported in this slot in this chassis."
    ::= { tmnxCpmCardEntry 3 }

tmnxCpmCardAllowedTypes          OBJECT-TYPE
    SYNTAX      TmnxCardType
    MAX-ACCESS  read-write
    STATUS      obsolete
    DESCRIPTION
        "A bit-mask that specifies what CPM card types the administrator
         has designated be allowed to be inserted into this slot.  If the
         slot has not been pre-provisioned and a card that does not match
         one of the allowed types is inserted into this slot, a mismatch
         alarm will be raised.  If a specific value has not yet been SET by
         the manager, tmnxCpmCardAllowedTypes will return the same value to
         a GET request as tmnxCpmCardSupportedTypes.

         The object was made obsolete in the 3.0 release."
    ::= { tmnxCpmCardEntry 4 }

tmnxCpmCardAssignedType          OBJECT-TYPE
    SYNTAX      TmnxCardType
    MAX-ACCESS  read-write
    STATUS      current
    DESCRIPTION
        "The tmnxCpmCardAssignedType specifies the administratively assigned
         (pre-provisioned) CPM card type defined in tmnxCardTypeTable that
         should occupy this slot in this chassis.  If tmnxCpmCardAssignedType
         has a value of 1 (unassigned), this slot has not yet been
         pre-provisioned."
    DEFVAL      { 1 }
    ::= { tmnxCpmCardEntry 5 }

tmnxCpmCardEquippedType          OBJECT-TYPE
    SYNTAX      TmnxCardType
    MAX-ACCESS  read-only
    STATUS      current
    DESCRIPTION
        "The tmnxCpmCardEquippedType indicates the CPM card type that is
         physically inserted into this slot in this chassis.  If the slot has
         been pre-provisioned, tmnxCpmCardAssignedType is not equal to 1
         (unassigned), and the value of tmnxCpmCardEquippedType is not the same
         as tmnxCpmCardAssignedType, a mismatch alarm will be raised."
    ::= { tmnxCpmCardEntry 6 }

tmnxCpmCardHwIndex               OBJECT-TYPE
    SYNTAX      TmnxHwIndex
    MAX-ACCESS  read-only
    STATUS      current
    DESCRIPTION
        "The value of tmnxCpmCardHwIndex is the index into the tmnxHwTable for
         the row entry that represents the hardware component information for
         this CPM card or module."
    ::= { tmnxCpmCardEntry 7 }

tmnxCpmCardBootOptionVersion     OBJECT-TYPE
    SYNTAX      TItemDescription
    MAX-ACCESS  read-only
    STATUS      current
    DESCRIPTION
        "The version number of boot option file (BOF) read by the CPM card in
         this slot."
    ::= { tmnxCpmCardEntry 8 }

tmnxCpmCardBootOptionLastModified OBJECT-TYPE
    SYNTAX      DateAndTime
    MAX-ACCESS  read-only
    STATUS      current
    DESCRIPTION
        "The date and time the boot options file (BOF) for this card was last
         modified.  If tmnxCpmCardBootOptionLastModified is more recent than
         tmnxHwSwLastBoot, the boot options file has been edited since
         the software was booted and different software images or configuration
         will likely be used when this card is next rebooted."
    ::= { tmnxCpmCardEntry 9 }

tmnxCpmCardConfigBootedVersion   OBJECT-TYPE
    SYNTAX      TItemDescription
    MAX-ACCESS  read-only
    STATUS      current
    DESCRIPTION
        "The version of the configuration file read when this CPM card was last
         rebooted."
    ::= { tmnxCpmCardEntry 10 }

tmnxCpmCardIndexBootedVersion    OBJECT-TYPE
    SYNTAX      TItemDescription
    MAX-ACCESS  read-only
    STATUS      current
    DESCRIPTION
        "The version of the index file read when this CPM card was last
         rebooted."
    ::= { tmnxCpmCardEntry 11 }

tmnxCpmCardConfigLastModified    OBJECT-TYPE
    SYNTAX      DateAndTime
    MAX-ACCESS  read-only
    STATUS      current
    DESCRIPTION
        "The date and time the running configuration was last modified. If
         tmnxCpmCardConfigLastModified is more recent than tmnxHwSwLastBoot,
         the current configuration may be different than that in the
         configuration file read upon system initialization."
    ::= { tmnxCpmCardEntry 12 }

tmnxCpmCardConfigLastSaved       OBJECT-TYPE
    SYNTAX      DateAndTime
    MAX-ACCESS  read-only
    STATUS      current
    DESCRIPTION
        "The date and time the current configuration was last saved. If
         tmnxCpmCardConfigLastSaved is more recent the value of
         tmnxHwSwLastBoot, the initial configuration is likely to be different
         the next time the system is rebooted."
    ::= { tmnxCpmCardEntry 13 }

tmnxCpmCardRedundant             OBJECT-TYPE
    SYNTAX      INTEGER {
        singleton           (1),
        redundantActive     (2),
        redundantStandby    (3),
        redundantSplit      (4),
        redundantDisabled   (5),
        redundantSyncing    (6),
        redundantExtActive  (7),
        redundantExtStandby (8)
    }
    MAX-ACCESS  read-only
    STATUS      current
    DESCRIPTION
        "The value of tmnxCpmCardRedundant indicates the role of the CPM card
         for the redundant pair.

         The possible values are:
         singleton           (1) - standalone CPM, no redundant pair
         redundantActive     (2) - the active CPM in the redundant pair
         redundantStandby    (3) - the standby CPM in the redundant pair
         redundantSplit      (4) - not implemented
         redundantDisabled   (5) - tmnxHwOperState indicates the specific
                                   reason why this redundant CPM is not
                                   available
         redundantSyncing    (6) - the redundant pair is syncing
         redundantExtActive  (7) - the active CPM in the redundant pair
                                   for the extension chassis
         redundantExtStandby (8) - the standby CPM in the redundant pair
                                   for the extension chassis"
    ::= { tmnxCpmCardEntry 14 }

tmnxCpmCardClockSource           OBJECT-TYPE
    SYNTAX      TItemDescription
    MAX-ACCESS  read-only
    STATUS      current
    DESCRIPTION
        "The clock source used by the CPM card in this slot."
    ::= { tmnxCpmCardEntry 15 }

tmnxCpmCardNumCpus               OBJECT-TYPE
    SYNTAX      Unsigned32
    MAX-ACCESS  read-only
    STATUS      current
    DESCRIPTION
        "The value of tmnxCpmCardNumCpus indicates the number of CPU chips
         populated on this CPM module."
    ::= { tmnxCpmCardEntry 16 }

tmnxCpmCardCpuType               OBJECT-TYPE
    SYNTAX      INTEGER {
        unknown    (1),
        mips       (2),
        pentium-pc (3),
        arm        (4)
    }
    MAX-ACCESS  read-only
    STATUS      current
    DESCRIPTION
        "The value of tmnxCpmCardCpuType indicates the type of CPU chips
         populated on this CPM module."
    ::= { tmnxCpmCardEntry 17 }

tmnxCpmCardMemorySize            OBJECT-TYPE
    SYNTAX      Unsigned32
    UNITS       "Megabytes"
    MAX-ACCESS  read-only
    STATUS      current
    DESCRIPTION
        "The value of tmnxCpmCardMemorySize indicates the amount of memory, in
         megabytes, populated on this CPM module."
    ::= { tmnxCpmCardEntry 18 }

tmnxCpmCardSwitchToRedundantCard OBJECT-TYPE
    SYNTAX      TmnxActionType
    MAX-ACCESS  read-write
    STATUS      current
    DESCRIPTION
        "Setting this variable to doAction causes the switchover to the
         redundant CPM card."
    DEFVAL      { notApplicable }
    ::= { tmnxCpmCardEntry 19 }

tmnxCpmCardReboot                OBJECT-TYPE
    SYNTAX      TmnxActionType
    MAX-ACCESS  read-write
    STATUS      current
    DESCRIPTION
        "Setting this variable to 'doAction' causes the CPM card to execute a
         soft-reboot."
    DEFVAL      { notApplicable }
    ::= { tmnxCpmCardEntry 20 }

tmnxCpmCardRereadBootOptions     OBJECT-TYPE
    SYNTAX      TmnxActionType
    MAX-ACCESS  read-write
    STATUS      current
    DESCRIPTION
        "Setting this variable to 'doAction' causes the Boot Options File (BOF)
         to be reread and applied."
    DEFVAL      { notApplicable }
    ::= { tmnxCpmCardEntry 21 }

tmnxCpmCardConfigFileLastBooted  OBJECT-TYPE
    SYNTAX      DisplayString
    MAX-ACCESS  read-only
    STATUS      current
    DESCRIPTION
        "tmnxCpmCardConfigFileLastBooted indicates the location and name of the
         configuration file from which the system last rebooted."
    ::= { tmnxCpmCardEntry 22 }

tmnxCpmCardConfigFileLastSaved   OBJECT-TYPE
    SYNTAX      DisplayString
    MAX-ACCESS  read-only
    STATUS      current
    DESCRIPTION
        "tmnxCpmCardConfigFileLastSaved indicates the location and name of the
         file to which the configuration was last saved."
    ::= { tmnxCpmCardEntry 23 }

tmnxCpmCardConfigFileLastBootedHeader OBJECT-TYPE
    SYNTAX      OCTET STRING (SIZE (0..512))
    MAX-ACCESS  read-only
    STATUS      current
    DESCRIPTION
        "tmnxCpmCardConfigFileLastBootedHeader contains the header of the
         configuration file from which the system last rebooted."
    ::= { tmnxCpmCardEntry 24 }

tmnxCpmCardIndexFileLastBootedHeader OBJECT-TYPE
    SYNTAX      OCTET STRING (SIZE (0..512))
    MAX-ACCESS  read-only
    STATUS      current
    DESCRIPTION
        "tmnxCpmCardIndexFileLastBootedHeader contains the header of the index
         file from which the system last rebooted."
    ::= { tmnxCpmCardEntry 25 }

tmnxCpmCardBootOptionSource      OBJECT-TYPE
    SYNTAX      DisplayString
    MAX-ACCESS  read-only
    STATUS      current
    DESCRIPTION
        "tmnxCpmCardBootOptionSource indicates the compact flash slot where the
         Boot Options File (BOF) file was found when the system last rebooted.
         For example, if the BOF file was found on compact flash slot 1, the
         value of this variable will be 'cf1:'"
    ::= { tmnxCpmCardEntry 26 }

tmnxCpmCardConfigSource          OBJECT-TYPE
    SYNTAX      INTEGER {
        unknown   (0),
        primary   (1),
        secondary (2),
        tertiary  (3)
    }
    MAX-ACCESS  read-only
    STATUS      current
    DESCRIPTION
        "The value of tmnxCpmCardConfigSource indicates the location in the
         Boot Options File(BOF) where the configuration file was found when the
         system last rebooted."
    ::= { tmnxCpmCardEntry 27 }

tmnxCpmCardBootOptionLastSaved   OBJECT-TYPE
    SYNTAX      DateAndTime
    MAX-ACCESS  read-only
    STATUS      current
    DESCRIPTION
        "The date and time the boot options file (BOF) was last saved. If
         tmnxCpmCardBootOptionLastSaved is more recent than the value of
         tmnxHwSwLastBoot, the boot options file has been edited since the
         software was booted and different software images or configuration
         will likely be used when this card is next rebooted."
    ::= { tmnxCpmCardEntry 28 }

tmnxCpmCardMasterSlaveRefState   OBJECT-TYPE
    SYNTAX      INTEGER {
        primaryRef     (1),
        secondaryRef   (2),
        notInitialized (3)
    }
    MAX-ACCESS  read-only
    STATUS      current
    DESCRIPTION
        "The current Master/Slave clocking reference designation.

         primaryRef       Indicates this card is designated as the primary
                          clocking reference in a redundant system for cards
                          within the same physical chassis.
         secondaryRef     Indicates this card is designated as the secondary
                          clocking reference in a redundant system for cards
                          within the same physical chassis.
         notInitialized   Indicates the clock is not initialized."
    ::= { tmnxCpmCardEntry 30 }

tmnxCpmCardConfigUserLastModified OBJECT-TYPE
    SYNTAX      SnmpAdminString (SIZE (0..65))
    MAX-ACCESS  read-only
    STATUS      current
    DESCRIPTION
        "The value of tmnxCpmCardConfigUserLastModified indicates the last user
         who modified the configuration.

         If the configuration was last modified by an SNMPv1 or SNMPv2 set
         operation, the value of this object will indicate the SNMP community
         string and view name separated by the '/' character.

         If the configuration was last modified by an SNMPv3 set operation, the
         value of this object will be the SNMPv3 user and view name separated
         by the '/' character.

         If the configuration has not been saved since the last boot, the
         object will have the value of an empty string."
    ::= { tmnxCpmCardEntry 31 }

tmnxCpmCardCmplxCAMErrOccur      OBJECT-TYPE
    SYNTAX      Counter32
    MAX-ACCESS  read-only
    STATUS      current
    DESCRIPTION
        "The value of tmnxCpmCardCmplxCAMErrOccur indicates the number of times
         the complex experienced an occurrence of a CAM error since startup, or
         card reboot."
    ::= { tmnxCpmCardEntry 32 }

tmnxCpmCardCmplxCAMErrOccurTime  OBJECT-TYPE
    SYNTAX      TimeStamp
    MAX-ACCESS  read-only
    STATUS      current
    DESCRIPTION
        "The value of tmnxCpmCardCmplxCAMErrOccurTime indicates the last time
         tmnxCpmCardCmplxCAMErrOccur incremented."
    ::= { tmnxCpmCardEntry 33 }

tmnxCpmCardOscillatorType        OBJECT-TYPE
    SYNTAX      INTEGER {
        none (1),
        tcxo (2),
        ocxo (3)
    }
    MAX-ACCESS  read-only
    STATUS      current
    DESCRIPTION
        "The value of tmnxCpmCardOscillatorType indicates the type of
         oscillator present on the card.

         An Oven-Controlled Crystal Oscillator (OCXO) is required for the card
         to support IEEE 1588 clock recovery.  A Temperature-Compensated Crystal
         Oscillator (TCXO) is not sufficient.

         The type of oscillator also affects the holdover performance of the
         system."
    ::= { tmnxCpmCardEntry 34 }

tmnxCpmCardCmplxMemErrOccur      OBJECT-TYPE
    SYNTAX      Counter32
    MAX-ACCESS  read-only
    STATUS      current
    DESCRIPTION
        "The value of tmnxCpmCardCmplxMemErrOccur indicates the number of times
         the complex experienced an occurrence of a memory error since startup,
         or card reboot."
    ::= { tmnxCpmCardEntry 35 }

tmnxCpmCardCmplxMemErrOccurTime  OBJECT-TYPE
    SYNTAX      TimeStamp
    MAX-ACCESS  read-only
    STATUS      current
    DESCRIPTION
        "The value of tmnxCpmCardCmplxMemErrOccurTime indicates the last time
         tmnxCpmCardCmplxMemErrOccur incremented."
    ::= { tmnxCpmCardEntry 36 }

tmnxCpmCardCmplBufMemErrOcc      OBJECT-TYPE
    SYNTAX      Counter32
    MAX-ACCESS  read-only
    STATUS      current
    DESCRIPTION
        "The value of tmnxCpmCardCmplBufMemErrOcc indicates the number of times
         the complex experienced an occurrence of a buffer memory error since
         startup, or card reboot."
    ::= { tmnxCpmCardEntry 37 }

tmnxCpmCardCmplBufMemErrOccTime  OBJECT-TYPE
    SYNTAX      TimeStamp
    MAX-ACCESS  read-only
    STATUS      current
    DESCRIPTION
        "The value of tmnxCpmCardCmplBufMemErrOccTime indicates the last time
         tmnxCpmCardCmplBufMemErrOcc incremented."
    ::= { tmnxCpmCardEntry 38 }

tmnxCpmCardCmplStatMemErrOcc     OBJECT-TYPE
    SYNTAX      Counter32
    MAX-ACCESS  read-only
    STATUS      current
    DESCRIPTION
        "The value of tmnxCpmCardCmplStatMemErrOcc indicates the number of
         times the complex experienced an occurrence of a statistics memory
         error since startup, or card reboot."
    ::= { tmnxCpmCardEntry 39 }

tmnxCpmCardCmplStatMemErrOccTime OBJECT-TYPE
    SYNTAX      TimeStamp
    MAX-ACCESS  read-only
    STATUS      current
    DESCRIPTION
        "The value of tmnxCpmCardCmplStatMemErrOccTime indicates the last time
         tmnxCpmCardCmplStatMemErrOcc incremented."
    ::= { tmnxCpmCardEntry 40 }

tmnxCpmCardCmplIntMemErrOcc      OBJECT-TYPE
    SYNTAX      Counter32
    MAX-ACCESS  read-only
    STATUS      current
    DESCRIPTION
        "The value of tmnxCpmCardCmplIntMemErrOcc indicates the number of times
         the complex experienced an occurrence of an internal memory error
         since startup, or card reboot."
    ::= { tmnxCpmCardEntry 41 }

tmnxCpmCardCmplIntMemErrOccTime  OBJECT-TYPE
    SYNTAX      TimeStamp
    MAX-ACCESS  read-only
    STATUS      current
    DESCRIPTION
        "The value of tmnxCpmCardCmplIntMemErrOccTime indicates the last time
         tmnxCpmCardCmplIntMemErrOcc incremented."
    ::= { tmnxCpmCardEntry 42 }

tmnxCpmCardCmplChipIfDownOcc     OBJECT-TYPE
    SYNTAX      Counter32
    MAX-ACCESS  read-only
    STATUS      current
    DESCRIPTION
        "The value of tmnxCpmCardCmplChipIfDownOcc indicates the number of
         times the complex experienced an occurrence of an internal datapath
         problem."
    ::= { tmnxCpmCardEntry 43 }

tmnxCpmCardCmplChipIfDownOccTime OBJECT-TYPE
    SYNTAX      TimeStamp
    MAX-ACCESS  read-only
    STATUS      current
    DESCRIPTION
        "The value of tmnxCpmCardCmplChipIfDownOccTime indicates the last time
         tmnxCpmCardCmplChipIfDownOcc incremented."
    ::= { tmnxCpmCardEntry 44 }

tmnxCpmCardCmplChipIfCellOcc     OBJECT-TYPE
    SYNTAX      Counter32
    MAX-ACCESS  read-only
    STATUS      current
    DESCRIPTION
        "The value of tmnxCpmCardCmplChipIfCellOcc indicates the number of
         times the complex experienced an occurrence of internal datapath cell
         errors."
    ::= { tmnxCpmCardEntry 45 }

tmnxCpmCardCmplChipIfCellOccTime OBJECT-TYPE
    SYNTAX      TimeStamp
    MAX-ACCESS  read-only
    STATUS      current
    DESCRIPTION
        "The value of tmnxCpmCardCmplChipIfCellOccTime indicates the last time
         tmnxCpmCardCmplChipIfCellOcc incremented."
    ::= { tmnxCpmCardEntry 46 }

tmnxCpmCardRebootHold            OBJECT-TYPE
    SYNTAX      TruthValue
    MAX-ACCESS  read-write
    STATUS      current
    DESCRIPTION
        "The value of tmnxCpmCardRebootHold specifies putting the standby CPM
         card in hold on a soft reboot, preventing the standby CPM+SFM from
         coming back online. To do so, this attribute must be set to 'true(1)'
         together with tmnxCpmCardReboot set to 'doAction(1)' and only for the
         standby CPM; otherwise, the set will fail with error
         'inconsistentValue'. For the active CPM, tmnxCpmCardRebootHold can't
         be set to 'true(1)' and will always return a value of 'false(2)'.

         When tmnxCpmCardRebootHold is set to 'true(1)', the standby CPM
         reboots as expected, but remains in a booting state (in hold).

         The setting of tmnxCpmCardRebootHold to 'true(1)' prevents the active
         CPM from declaring the standby CPM dead because it failed to boot. MIB
         attribute tmnxHwFailureReason will be updated for the standby CPM
         indicating that there is no SFM.

         The system is not redundant while tmnxCpmCardRebootHold is 'true(1)'.
         If the active CPM fails, or is manually rebooted, the standby CPM will
         also reboot.

         tmnxCpmCardRebootHold is set to 'false(2)' when tmnxCpmCardReboot for
         the standby CPM is set to 'doAction(1)' without also setting
         tmnxCpmCardRebootHold, or if the active CPM reboots."
    DEFVAL      { false }
    ::= { tmnxCpmCardEntry 47 }

tmnxCpmCardUuid                  OBJECT-TYPE
    SYNTAX      TmnxUuid
    MAX-ACCESS  read-only
    STATUS      current
    DESCRIPTION
        "The value of tmnxCpmCardUuid indicates the Universally Unique
         Identifier (UUID) of the CPM card."
    ::= { tmnxCpmCardEntry 49 }

tmnxCpmCardCmplxIngrFcsOccur     OBJECT-TYPE
    SYNTAX      Counter32
    MAX-ACCESS  read-only
    STATUS      current
    DESCRIPTION
        "The value of tmnxCpmCardCmplxIngrFcsOccur indicates the number of
         times the first CPM card complex experienced an occurrence of an FCS
         error in the ingress direction since startup, last clear, or CPM
         reboot."
    ::= { tmnxCpmCardEntry 50 }

tmnxCpmCardCmplxIngrFcsOccurTime OBJECT-TYPE
    SYNTAX      TimeStamp
    MAX-ACCESS  read-only
    STATUS      current
    DESCRIPTION
        "The value of tmnxCpmCardCmplxIngrFcsOccurTime indicates the last time
         tmnxCardCmplx1IngrFcsOccur incremented."
    ::= { tmnxCpmCardEntry 51 }

tmnxCpmCardCmplxEgrFcsOccur      OBJECT-TYPE
    SYNTAX      Counter32
    MAX-ACCESS  read-only
    STATUS      current
    DESCRIPTION
        "The value of tmnxCpmCardCmplxEgrFcsOccur indicates the number of times
         the first CPM card complex experienced an occurrence of an FCS error
         in the egress direction since startup, last clear, or CPM reboot."
    ::= { tmnxCpmCardEntry 52 }

tmnxCpmCardCmplxEgrFcsOccurTime  OBJECT-TYPE
    SYNTAX      TimeStamp
    MAX-ACCESS  read-only
    STATUS      current
    DESCRIPTION
        "The value of tmnxCpmCardCmplxEgrFcsOccurTime indicates the last time
         tmnxCardCmplx1EgrFcsOccur incremented."
    ::= { tmnxCpmCardEntry 53 }

tmnxCpmCardCmplxEgrFcsSrcSlots   OBJECT-TYPE
    SYNTAX      TmnxCardSlotBitMap
    MAX-ACCESS  read-only
    STATUS      current
    DESCRIPTION
        "The value of tmnxCpmCardCmplxEgrFcsSrcSlots indicates the source slots
         reported from the last time tmnxCpmCardCmplxEgrFcsOccur incremented."
    ::= { tmnxCpmCardEntry 54 }

tmnxCpmCardVmHypervisor          OBJECT-TYPE
    SYNTAX      TItemDescription
    MAX-ACCESS  read-only
    STATUS      obsolete
    DESCRIPTION
        "The value of tmnxCpmCardVmHypervisor indicates the name of the
         hypervisor.

         The value of this object is only relevant in a virtual machine
         implementation."
    DEFVAL      { "" }
    ::= { tmnxCpmCardEntry 55 }

tmnxCpmCardVmCpu                 OBJECT-TYPE
    SYNTAX      TItemDescription
    MAX-ACCESS  read-only
    STATUS      obsolete
    DESCRIPTION
        "The value of tmnxCpmCardVmCpu indicates the description of the CPU.

         The value of this object is only relevant in a virtual machine
         implementation."
    DEFVAL      { "" }
    ::= { tmnxCpmCardEntry 56 }

tmnxCpmCardVmNumCores            OBJECT-TYPE
    SYNTAX      Unsigned32
    MAX-ACCESS  read-only
    STATUS      obsolete
    DESCRIPTION
        "The value of tmnxCpmCardVmNumCores indicates the number of processor
         cores available.

         The value of this object is only relevant in a virtual machine
         implementation."
    ::= { tmnxCpmCardEntry 57 }

tmnxCpmCardAntiTheft             OBJECT-TYPE
    SYNTAX      TmnxEnabledDisabled
    MAX-ACCESS  read-only
    STATUS      current
    DESCRIPTION
        "The value of the object tmnxCpmCardAntiTheft indicates whether the
         system has activated the Anti-Theft component of the OS Security suite
         on this CPM."
    ::= { tmnxCpmCardEntry 61 }

tmnxCpmCardPwdPendingActivation  OBJECT-TYPE
    SYNTAX      TruthValue
    MAX-ACCESS  read-only
    STATUS      current
    DESCRIPTION
        "The value of tmnxCpmCardPwdPendingActivation indicates whether or not
         an OS Security password is pending activation on this CPM. OS Security
         password will only be pending activation if the OS Security password
         is changed while Anti_theft is enabled."
    ::= { tmnxCpmCardEntry 62 }

tmnxFabricLastChange             OBJECT-TYPE
    SYNTAX      TimeStamp
    MAX-ACCESS  read-only
    STATUS      current
    DESCRIPTION
        "The value of sysUpTime when the tmnxFabricTable was last changed."
    ::= { tmnxCardObjs 5 }

tmnxFabricTable                  OBJECT-TYPE
    SYNTAX      SEQUENCE OF TmnxFabricEntry
    MAX-ACCESS  not-accessible
    STATUS      current
    DESCRIPTION
        "The tmnxFabricTable has an entry for each fabric card slot in each
         chassis in the TMNX system."
    ::= { tmnxCardObjs 6 }

tmnxFabricEntry                  OBJECT-TYPE
    SYNTAX      TmnxFabricEntry
    MAX-ACCESS  not-accessible
    STATUS      current
    DESCRIPTION
        "Each row entry represents a fabric card slot in a chassis in
         the system.  Entries cannot be created and deleted via
         SNMP SET operations.  When a tmnxChassisEntry is created,
         a tmnxFabricEntry is created for each fabric card slot in that
         chassis.  Before a tmnxChassisEntry can be deleted, each
         tmnxFabricEntry for that chassis must be in the proper state
         for removal."
    INDEX       {
        tmnxChassisIndex,
        tmnxFabricSlotNum
    }
    ::= { tmnxFabricTable 1 }

TmnxFabricEntry                  ::= SEQUENCE
{
    tmnxFabricSlotNum                Unsigned32,
    tmnxFabricAssignedType           TmnxFabricType,
    tmnxFabricEquippedType           TmnxFabricType,
    tmnxFabricHwIndex                TmnxHwIndex,
    tmnxFabricSupportedTypes         TmnxFabricSuppType,
    tmnxFabricReboot                 TmnxActionType
}

tmnxFabricSlotNum                OBJECT-TYPE
    SYNTAX      Unsigned32 (1..16)
    MAX-ACCESS  not-accessible
    STATUS      current
    DESCRIPTION
        "The unique value which identifies this fabric slot within a
         chassis in the system. The CPM cards and IOM cards cannot be
         physically inserted into the switch fabric card slots.  In
         some models, the CPM is not a separate card, but rather a
         module on a Fabric card."
    ::= { tmnxFabricEntry 1 }

tmnxFabricAssignedType           OBJECT-TYPE
    SYNTAX      TmnxFabricType
    MAX-ACCESS  read-write
    STATUS      current
    DESCRIPTION
        "The administratively assigned switch fabric card type that should
         occupy this fabric slot in this chassis."
    DEFVAL      { 1 }
    ::= { tmnxFabricEntry 2 }

tmnxFabricEquippedType           OBJECT-TYPE
    SYNTAX      TmnxFabricType
    MAX-ACCESS  read-only
    STATUS      current
    DESCRIPTION
        "The switch fabric card type that is physically inserted into this slot
         in this chassis."
    ::= { tmnxFabricEntry 3 }

tmnxFabricHwIndex                OBJECT-TYPE
    SYNTAX      TmnxHwIndex
    MAX-ACCESS  read-only
    STATUS      current
    DESCRIPTION
        "The value of tmnxFabricHwIndex indicates the tmnxHwIndex into the
         tmnxHwTable to locate the row entry that represents the hardware
         component information for this fabric card."
    ::= { tmnxFabricEntry 4 }

tmnxFabricSupportedTypes         OBJECT-TYPE
    SYNTAX      TmnxFabricSuppType
    MAX-ACCESS  read-only
    STATUS      current
    DESCRIPTION
        "A bit-mask that indicates what fabric card types can be configured in
         this slot in this chassis."
    ::= { tmnxFabricEntry 5 }

tmnxFabricReboot                 OBJECT-TYPE
    SYNTAX      TmnxActionType
    MAX-ACCESS  read-write
    STATUS      current
    DESCRIPTION
        "Setting this variable to 'doAction' causes the fabric to execute a
         soft-reboot."
    DEFVAL      { notApplicable }
    ::= { tmnxFabricEntry 6 }

tmnxCpmFlashTable                OBJECT-TYPE
    SYNTAX      SEQUENCE OF TmnxCpmFlashEntry
    MAX-ACCESS  not-accessible
    STATUS      current
    DESCRIPTION
        "This table contains information about Flash devices on a CPM card."
    ::= { tmnxCardObjs 7 }

tmnxCpmFlashEntry                OBJECT-TYPE
    SYNTAX      TmnxCpmFlashEntry
    MAX-ACCESS  not-accessible
    STATUS      current
    DESCRIPTION
        "Contains information regarding a CPM card's flash unit."
    INDEX       {
        tmnxChassisIndex,
        tmnxCardSlotNum,
        tmnxCpmFlashId
    }
    ::= { tmnxCpmFlashTable 1 }

TmnxCpmFlashEntry                ::= SEQUENCE
{
    tmnxCpmFlashId                   Unsigned32,
    tmnxCpmFlashOperStatus           TmnxDeviceState,
    tmnxCpmFlashSerialNumber         TItemDescription,
    tmnxCpmFlashFirmwareRevision     TItemDescription,
    tmnxCpmFlashModelNumber          TItemDescription,
    tmnxCpmFlashCapacity             Unsigned32,
    tmnxCpmFlashUsed                 Unsigned32,
    tmnxCpmFlashHwIndex              TmnxHwIndex,
    tmnxCpmFlashPercentageUsed       Unsigned32
}

tmnxCpmFlashId                   OBJECT-TYPE
    SYNTAX      Unsigned32 (1..32)
    MAX-ACCESS  not-accessible
    STATUS      current
    DESCRIPTION
        "The unique identifier index for a flash device on a CPM card."
    ::= { tmnxCpmFlashEntry 1 }

tmnxCpmFlashOperStatus           OBJECT-TYPE
    SYNTAX      TmnxDeviceState
    MAX-ACCESS  read-only
    STATUS      current
    DESCRIPTION
        "Current status of this flash unit on this CPM card."
    ::= { tmnxCpmFlashEntry 2 }

tmnxCpmFlashSerialNumber         OBJECT-TYPE
    SYNTAX      TItemDescription
    MAX-ACCESS  read-only
    STATUS      current
    DESCRIPTION
        "The serial number for this flash unit on this CPM card."
    ::= { tmnxCpmFlashEntry 3 }

tmnxCpmFlashFirmwareRevision     OBJECT-TYPE
    SYNTAX      TItemDescription
    MAX-ACCESS  read-only
    STATUS      current
    DESCRIPTION
        "The firmware revision number for this flash unit on this CPM card."
    ::= { tmnxCpmFlashEntry 4 }

tmnxCpmFlashModelNumber          OBJECT-TYPE
    SYNTAX      TItemDescription
    MAX-ACCESS  read-only
    STATUS      current
    DESCRIPTION
        "The model number for this flash unit on this CPM card."
    ::= { tmnxCpmFlashEntry 5 }

tmnxCpmFlashCapacity             OBJECT-TYPE
    SYNTAX      Unsigned32
    UNITS       "sectors"
    MAX-ACCESS  read-only
    STATUS      current
    DESCRIPTION
        "The value of tmnxCpmFlashCapacity indicates the maximum size of this
         flash unit in 512-byte sectors."
    ::= { tmnxCpmFlashEntry 6 }

tmnxCpmFlashUsed                 OBJECT-TYPE
    SYNTAX      Unsigned32
    UNITS       "sectors"
    MAX-ACCESS  read-only
    STATUS      current
    DESCRIPTION
        "The value of tmnxCpmFlashUsed indicates the amount used, in 512-byte
         sectors, of this flash unit's total capacity."
    ::= { tmnxCpmFlashEntry 7 }

tmnxCpmFlashHwIndex              OBJECT-TYPE
    SYNTAX      TmnxHwIndex
    MAX-ACCESS  read-only
    STATUS      current
    DESCRIPTION
        "The value of tmnxCpmFlashHwIndex indicates the tmnxHwIndex into the
         tmnxHwTable for the row entry that represents the hardware component
         information for this flash unit."
    ::= { tmnxCpmFlashEntry 8 }

tmnxCpmFlashPercentageUsed       OBJECT-TYPE
    SYNTAX      Unsigned32
    UNITS       "percent"
    MAX-ACCESS  read-only
    STATUS      current
    DESCRIPTION
        "The value of tmnxCpmFlashPercentageUsed indicates the amount used for
         this flash unit as a percentage of total capacity."
    ::= { tmnxCpmFlashEntry 9 }

tmnxMDATable                     OBJECT-TYPE
    SYNTAX      SEQUENCE OF TmnxMDAEntry
    MAX-ACCESS  not-accessible
    STATUS      current
    DESCRIPTION
        "The tmnxMDATable has an entry for each MDA slot in each IOM card in
         this chassis in the TMNX system."
    ::= { tmnxCardObjs 8 }

tmnxMDAEntry                     OBJECT-TYPE
    SYNTAX      TmnxMDAEntry
    MAX-ACCESS  not-accessible
    STATUS      current
    DESCRIPTION
        "Each row entry represents a MDA slot in an IOM card in a
         chassis in the system.  Entries cannot be created and
         deleted via SNMP SET operations.  When a tmnxCardEntry
         has tmnxCardAssignedType or tmnxCardEquippedType equal to
         an IOM card type that supports MDA slots, a tmnxMDAEntry is
         created by the agent for each MDA slot on that IOM card.
         Before a tmnxCardEntry can be deleted, each tmnxMDAEntry for
         that card must be in the proper state for removal."
    INDEX       {
        tmnxChassisIndex,
        tmnxCardSlotNum,
        tmnxMDASlotNum
    }
    ::= { tmnxMDATable 1 }

TmnxMDAEntry                     ::= SEQUENCE
{
    tmnxMDASlotNum                   Unsigned32,
    tmnxMDASupportedTypes            TmnxMDASuppType,
    tmnxMDAAllowedTypes              TmnxMdaType,
    tmnxMDAAssignedType              TmnxMdaType,
    tmnxMDAEquippedType              TmnxMdaType,
    tmnxMDAHwIndex                   TmnxHwIndex,
    tmnxMDAMaxPorts                  Integer32,
    tmnxMDAEquippedPorts             Unsigned32,
    tmnxMDATxTimingSelected          INTEGER,
    tmnxMDASyncIfTimingStatus        INTEGER,
    tmnxMDANetworkIngQueues          TNamedItem,
    tmnxMDACapabilities              BITS,
    tmnxMDAMinChannelization         TmnxMDAChanType,
    tmnxMDAMaxChannelization         TmnxMDAChanType,
    tmnxMDAMaxChannels               Unsigned32,
    tmnxMDAChannelsInUse             Unsigned32,
    tmnxMDACcagId                    TmnxCcagId,
    tmnxMDAReboot                    TmnxActionType,
    tmnxMDAHiBwMcastSource           TruthValue,
    tmnxMDAHiBwMcastAlarm            TruthValue,
    tmnxMDAHiBwMcastTapCount         Gauge32,
    tmnxMDAHiBwMcastGroup            Unsigned32,
    tmnxMDAClockMode                 INTEGER,
    tmnxMDADiffTimestampFreq         Unsigned32,
    tmnxMDAMcPathMgmtBwPlcyName      TNamedItem,
    tmnxMDAMcPathMgmtPriPathLimit    Unsigned32,
    tmnxMDAMcPathMgmtSecPathLimit    Unsigned32,
    tmnxMDAMcPathMgmtAncPathLimit    Unsigned32,
    tmnxMDAMcPathMgmtAdminState      TmnxAdminState,
    tmnxMDAIngNamedPoolPolicy        TNamedItemOrEmpty,
    tmnxMDAEgrNamedPoolPolicy        TNamedItemOrEmpty,
    tmnxMDAMcPathMgmtPriInUseBw      Gauge32,
    tmnxMDAMcPathMgmtSecInUseBw      Gauge32,
    tmnxMDAMcPathMgmtAncInUseBw      Gauge32,
    tmnxMDAMcPathMgmtBlkHoleInUseBw  Gauge32,
    tmnxMDASynchronousEthernet       INTEGER,
    tmnxMDAXplErrorTime              TimeStamp,
    tmnxMDAXplFailedCount            Gauge32,
    tmnxMDAAtmMode                   TmnxMdaAtmMode,
    tmnxMDAIsaTunnelGroup            TmnxTunnelGroupIdOrZero,
    tmnxMDAIsaTunnelGroupInUse       TruthValue,
    tmnxMDAHwPowerPriority           Unsigned32,
    tmnxMDAFailOnError               BITS,
    tmnxMDAEgrXplErrThreshold        Unsigned32,
    tmnxMDAEgrXplErrWindow           Unsigned32,
    tmnxMDAIngrXplErrThreshold       Unsigned32,
    tmnxMDAIngrXplErrWindow          Unsigned32,
    tmnxMDAResetOnRecoverableError   TruthValue,
    tmnxMDAAssignedLevel             TmnxMDAFunctionalLevel,
    tmnxMDAEquippedLevel             TmnxMDAFunctionalLevel,
    tmnxMDALicensedLevel             TmnxMDAFunctionalLevel,
    tmnxMDALicensedBandwidth         Unsigned32,
    tmnxMDAIsaMemberPoolAssoc        TNamedItemOrEmpty,
    tmnxMDAIsaTunnelActiveInGrp      TmnxTunnelGroupIdOrZero,
    tmnxMDAMacMode                   INTEGER,
    tmnxMDAIngPreClassifierPolicy    TLNamedItemOrEmpty,
    tmnxMDAIngPreClassfrUngtagDot1p  Dot1PUntagValue
}

tmnxMDASlotNum                   OBJECT-TYPE
    SYNTAX      Unsigned32 (0..16)
    MAX-ACCESS  not-accessible
    STATUS      current
    DESCRIPTION
        "The unique value which identifies this MDA slot within a
         specific IOM card in the system.  Rows with a tmnxMDASlotNum
         value of zero (0) represent the special case of an IOM card
         without MDA slots but that instead has its ports directly
         on the IOM card itself.  In that case, there should be only
         that one row entry in the tmnxMDATable for that IOM card."
    ::= { tmnxMDAEntry 1 }

tmnxMDASupportedTypes            OBJECT-TYPE
    SYNTAX      TmnxMDASuppType
    MAX-ACCESS  read-only
    STATUS      current
    DESCRIPTION
        "A bit-mask that indicates what MDA card types can be configured in
         this slot in this chassis."
    ::= { tmnxMDAEntry 2 }

tmnxMDAAllowedTypes              OBJECT-TYPE
    SYNTAX      TmnxMdaType
    MAX-ACCESS  read-write
    STATUS      obsolete
    DESCRIPTION
        "An integer that specified what MDA card types the administrator has
         designated be allowed to be inserted into this slot. If the slot has
         not been pre-provisioned and a MDA card that does not match one of the
         allowed types is inserted into this slot, a mismatch alarm will be
         raised.

         The object was made obsolete in the 3.0 release."
    ::= { tmnxMDAEntry 3 }

tmnxMDAAssignedType              OBJECT-TYPE
    SYNTAX      TmnxMdaType
    MAX-ACCESS  read-write
    STATUS      current
    DESCRIPTION
        "An integer that specifies the administratively assigned
         (pre-provisioned) MDA card type that should occupy this slot in
         this chassis.  If tmnxMDAAssignedType has a value of
         'unassigned', this slot has not yet been pre-provisioned."
    DEFVAL      { 1 }
    ::= { tmnxMDAEntry 4 }

tmnxMDAEquippedType              OBJECT-TYPE
    SYNTAX      TmnxMdaType
    MAX-ACCESS  read-only
    STATUS      current
    DESCRIPTION
        "An integer that indicates the MDA card type that is physically
         inserted into this slot in this chassis.  If the slot has been
         pre-provisioned, tmnxMDAAssignedType is not equal 'unassigned',
         and the value of tmnxMDAEquippedType is not the same as
         tmnxMDAAssignedType, a mismatch alarm will be raised.
         A value of 0 indicates the equipped MDA is not supported by
         this software release."
    ::= { tmnxMDAEntry 5 }

tmnxMDAHwIndex                   OBJECT-TYPE
    SYNTAX      TmnxHwIndex
    MAX-ACCESS  read-only
    STATUS      current
    DESCRIPTION
        "The value of tmnxMDAHwIndex indicates the tmnxHwIndex into the
         tmnxHwTable for the row entry that represents the hardware component
         information for this MDA card."
    ::= { tmnxMDAEntry 6 }

tmnxMDAMaxPorts                  OBJECT-TYPE
    SYNTAX      Integer32
    MAX-ACCESS  read-only
    STATUS      current
    DESCRIPTION
        "The maximum number of ports or connectors that can be equipped on this
         MDA card."
    ::= { tmnxMDAEntry 7 }

tmnxMDAEquippedPorts             OBJECT-TYPE
    SYNTAX      Unsigned32
    MAX-ACCESS  read-only
    STATUS      current
    DESCRIPTION
        "The value of tmnxMDAEquippedPorts indicates the number of ports or
         connectors equipped on this MDA card."
    ::= { tmnxMDAEntry 8 }

tmnxMDATxTimingSelected          OBJECT-TYPE
    SYNTAX      INTEGER {
        cpmCardA      (1),
        cpmCardB      (2),
        local         (3),
        holdover      (4),
        notApplicable (5),
        cpmCardC      (6),
        cpmCardD      (7)
    }
    MAX-ACCESS  read-only
    STATUS      current
    DESCRIPTION
        "The value of tmnxMDATxTimingSelected indicates the transmit timing
         method which is presently selected and being used by this MDA.
         tmnxMDATxTimingSelected will be set to 'notApplicable (5)' if this MDA
         does not use the transmit timing subsystem."
    ::= { tmnxMDAEntry 10 }

tmnxMDASyncIfTimingStatus        OBJECT-TYPE
    SYNTAX      INTEGER {
        qualified      (1),
        not-qualified  (2),
        not-applicable (3)
    }
    MAX-ACCESS  read-only
    STATUS      current
    DESCRIPTION
        "Indicates the status of the synchronous equipment timing subsystem. If
         the tmnxSyncIfTimingRef1Qualified and tmnxSyncIfTimingRef2Qualified
         are both set to 'not-qualified, then tmnxMDASyncIfTimingStatus is set
         to 'not-qualified'. If any of the timing references is in use, then
         tmnxMDASyncIfTimingStatus is set to 'qualified'.
         tmnxMDASyncIfTimingStatus will be set to 'not-applicable' if this MDA
         does not use the transmit timing subsystem."
    ::= { tmnxMDAEntry 11 }

tmnxMDANetworkIngQueues          OBJECT-TYPE
    SYNTAX      TNamedItem
    MAX-ACCESS  read-write
    STATUS      obsolete
    DESCRIPTION
        "Specifies the network queue policy being used for this object to
         define the queueing structure for this object.

         This object is obsoleted in 19.5R1 release and has been replaced with
         tmnxFPIngNetQueuePolicy object."
    DEFVAL      { "default" }
    ::= { tmnxMDAEntry 12 }

tmnxMDACapabilities              OBJECT-TYPE
    SYNTAX      BITS {
        isEthernet    (0),
        isSonet       (1),
        isTDM         (2),
        supportsPPP   (3),
        supportsFR    (4),
        supportsATM   (5),
        supportscHDLC (6),
        isCMA         (7),
        supportsCEM   (8),
        isSerial      (9),
        isWireless    (10),
        isCellular    (11)
    }
    MAX-ACCESS  read-only
    STATUS      current
    DESCRIPTION
        "tmnxMDACapabilities indicates the capabilities of this MDA. It
         identifies the type of MDA and the protocols that can run on it."
    ::= { tmnxMDAEntry 13 }

tmnxMDAMinChannelization         OBJECT-TYPE
    SYNTAX      TmnxMDAChanType
    MAX-ACCESS  read-only
    STATUS      current
    DESCRIPTION
        "tmnxMDAMinChannelization indicates the minimum size of the channel
         that can exist on this MDA."
    ::= { tmnxMDAEntry 14 }

tmnxMDAMaxChannelization         OBJECT-TYPE
    SYNTAX      TmnxMDAChanType
    MAX-ACCESS  read-only
    STATUS      current
    DESCRIPTION
        "tmnxMDAMaxChannelization indicates the maximum size of the channel
         that can exist on this MDA."
    ::= { tmnxMDAEntry 15 }

tmnxMDAMaxChannels               OBJECT-TYPE
    SYNTAX      Unsigned32
    MAX-ACCESS  read-only
    STATUS      current
    DESCRIPTION
        "tmnxMDAMaxChannels is applicable for SONET and TDM MDAs only. It
         indicates the total number of leaf SONET paths, TDM channels and
         bundles on the MDA that may be configured to pass traffic."
    ::= { tmnxMDAEntry 16 }

tmnxMDAChannelsInUse             OBJECT-TYPE
    SYNTAX      Unsigned32
    MAX-ACCESS  read-only
    STATUS      current
    DESCRIPTION
        "tmnxMDAChannelsInUse is applicable for SONET and TDM MDAs only.  It
         indicates the total number of leaf SONET paths, TDM channels and
         bundles on the MDA which are in use.  A leaf SONET path or TDM
         channel which is currently capable of passing traffic is considered
         to be in use.  Also, a SONET path or TDM channel which is
         channelized and has no subchannels capable of passing traffic
         is considered to be in use.  A SONET path or TDM channel which is
         channelized and has one or more subchannels capable of passing
         traffic is not considered to be in use, although the subchannels
         themselves are considered to be in use.  A bundle is considered to
         be a channel in use as are each of its members since they are TDM
         channels capable of passing traffic."
    ::= { tmnxMDAEntry 17 }

tmnxMDACcagId                    OBJECT-TYPE
    SYNTAX      TmnxCcagId
    MAX-ACCESS  read-write
    STATUS      obsolete
    DESCRIPTION
        "When tmnxMDAAssignedType has a value of 'cca' , the value of
         tmnxMDACcagId specifies the Cross Connect Aggregation Group (CCAG)
         entry this MDA is provisioned on.  If this entry does not represent
         a 'cca' MDA or is not associated with a CCAG, tmnxMDACcagId
         has a value of zero.

         This object was made obsolete in release 21.2."
    DEFVAL      { 0 }
    ::= { tmnxMDAEntry 18 }

tmnxMDAReboot                    OBJECT-TYPE
    SYNTAX      TmnxActionType
    MAX-ACCESS  read-write
    STATUS      current
    DESCRIPTION
        "Setting this variable to 'doAction' causes the MDA to execute a
         soft-reboot."
    DEFVAL      { notApplicable }
    ::= { tmnxMDAEntry 19 }

tmnxMDAHiBwMcastSource           OBJECT-TYPE
    SYNTAX      TruthValue
    MAX-ACCESS  read-write
    STATUS      obsolete
    DESCRIPTION
        "The value of tmnxMDAHiBwMcastSource specifies if this MDA should
         attempt to allocate separate fabric planes to allocate high bandwidth
         multicast traffic taps.

         tmnxMDAHiBwMcastGroup must be set in the same SNMP request PDU with
         tmnxMDAHiBwMcastSource or an 'inconsistentValue' error will be
         returned.

         This object was obsoleted from release 15.0R1."
    DEFVAL      { false }
    ::= { tmnxMDAEntry 20 }

tmnxMDAHiBwMcastAlarm            OBJECT-TYPE
    SYNTAX      TruthValue
    MAX-ACCESS  read-write
    STATUS      obsolete
    DESCRIPTION
        "The value of tmnxMDAHiBwMcastAlarm specifies if a
         tmnxChassisHiBwMcastAlarm alarm is raised if there are more than one
         high bandwidth multicast traffic taps sharing a plane.

         This object was obsoleted from release 15.0R1."
    DEFVAL      { true }
    ::= { tmnxMDAEntry 21 }

tmnxMDAHiBwMcastTapCount         OBJECT-TYPE
    SYNTAX      Gauge32
    MAX-ACCESS  read-only
    STATUS      obsolete
    DESCRIPTION
        "The value of tmnxMDAHiBwMcastTapCount indicates the number of high
         bandwidth multicast traffic taps on this MDA.

         This object was obsoleted from release 15.0R1."
    ::= { tmnxMDAEntry 22 }

tmnxMDAHiBwMcastGroup            OBJECT-TYPE
    SYNTAX      Unsigned32 (0..32)
    MAX-ACCESS  read-write
    STATUS      obsolete
    DESCRIPTION
        "The value of tmnxMDAHiBwMcastGroup specifies the group of high
         bandwidth multicast traffic taps to which this tap belongs.

         A value of '0' specifies that this tap is not a member of any High
         Bandwidth Multicast group.

         On an IOM of type 'iom-10g', the value of tmnxMDAHiBwMcastGroup should
         be the same as the value of tmnxMDAHiBwMcastGroup set on the other MDA
         residing on the IOM if the tmnxMDAHiBwMcastSource is set to 'true'.
         Attempt to set to different values will result in an
         'inconsistentValue' error.

         tmnxMDAHiBwMcastGroup must be set in the same SNMP request PDU with
         tmnxMDAHiBwMcastSource or an 'inconsistentValue' error will be
         returned.

         This object was obsoleted from release 15.0R1."
    DEFVAL      { 0 }
    ::= { tmnxMDAEntry 23 }

tmnxMDAClockMode                 OBJECT-TYPE
    SYNTAX      INTEGER {
        notApplicable (0),
        adaptive      (1),
        differential  (2)
    }
    MAX-ACCESS  read-write
    STATUS      obsolete
    DESCRIPTION
        "The value of tmnxMDAClockMode specifies the clock mode of the MDA.

         notApplicable - The MDA does not support any clock modes or domains.
         adaptive      - The MDA is in 'adaptive' clock mode.  This allows
                         adaptive clock domains to be created.
         differential  - The MDA is in 'differential clock mode.  This allows
                         differential clock domains to be created.

         The value of tmnxMDAClockMode can be changed when there are no ports
         created on the MDA.  If there are ports created, a shutdown of the
         MDA is required in order to change the value."
    DEFVAL      { notApplicable }
    ::= { tmnxMDAEntry 24 }

tmnxMDADiffTimestampFreq         OBJECT-TYPE
    SYNTAX      Unsigned32 (0 | 19440 | 77760 | 103680)
    UNITS       "kilohertz"
    MAX-ACCESS  read-write
    STATUS      current
    DESCRIPTION
        "The value of tmnxMDADiffTimestampFreq specifies the differential
         timestamp frequency of the differential clock on the MDA.

         The value must be a multiple of 8 KHz.

         If the value of tmnxMDACapabilities is 'supportsCEM' then the default
         is 77760. Otherwise, the default value is 0."
    DEFVAL      { 0 }
    ::= { tmnxMDAEntry 25 }

tmnxMDAMcPathMgmtBwPlcyName      OBJECT-TYPE
    SYNTAX      TNamedItem
    MAX-ACCESS  read-write
    STATUS      obsolete
    DESCRIPTION
        "The value of tmnxMDAMcPathMgmtBwPlcyName specifies the multicast
         policy name configured on the MDA.

         This object was obsoleted from release 15.0R1."
    DEFVAL      { "default" }
    ::= { tmnxMDAEntry 27 }

tmnxMDAMcPathMgmtPriPathLimit    OBJECT-TYPE
    SYNTAX      Unsigned32 (0..2000)
    UNITS       "mega-bits-per-second"
    MAX-ACCESS  read-write
    STATUS      obsolete
    DESCRIPTION
        "The value of tmnxMDAMcPathMgmtPriPathLimit specifies the primary path
         limit for the MDA.

         This object was obsoleted from release 15.0R1."
    DEFVAL      { 0 }
    ::= { tmnxMDAEntry 28 }

tmnxMDAMcPathMgmtSecPathLimit    OBJECT-TYPE
    SYNTAX      Unsigned32 (0..2000)
    UNITS       "mega-bits-per-second"
    MAX-ACCESS  read-write
    STATUS      obsolete
    DESCRIPTION
        "The value of tmnxMDAMcPathMgmtSecPathLimit specifies the secondary
         path limit for the MDA.

         This object was obsoleted from release 15.0R1."
    DEFVAL      { 0 }
    ::= { tmnxMDAEntry 29 }

tmnxMDAMcPathMgmtAncPathLimit    OBJECT-TYPE
    SYNTAX      Unsigned32 (0..5000)
    UNITS       "mega-bits-per-second"
    MAX-ACCESS  read-write
    STATUS      obsolete
    DESCRIPTION
        "The value of tmnxMDAMcPathMgmtAncPathLimit specifies the ancillary
         path limit for the MDA.

         This object was obsoleted from release 15.0R1."
    DEFVAL      { 0 }
    ::= { tmnxMDAEntry 30 }

tmnxMDAMcPathMgmtAdminState      OBJECT-TYPE
    SYNTAX      TmnxAdminState
    MAX-ACCESS  read-write
    STATUS      obsolete
    DESCRIPTION
        "The value of tmnxMDAMcPathMgmtAdminState specifies administrative
         state of this multicast path on the MDA.

         This object was obsoleted from release 15.0R1."
    DEFVAL      { outOfService }
    ::= { tmnxMDAEntry 31 }

tmnxMDAIngNamedPoolPolicy        OBJECT-TYPE
    SYNTAX      TNamedItemOrEmpty
    MAX-ACCESS  read-write
    STATUS      obsolete
    DESCRIPTION
        "The value of tmnxMDAIngNamedPoolPolicy specifies a named pool policy
         associated with an MDA ingress context. The policy governs the way
         named pools are created at the MDA level.

         This object is obsoleted in 20.0 Release."
    DEFVAL      { "" }
    ::= { tmnxMDAEntry 32 }

tmnxMDAEgrNamedPoolPolicy        OBJECT-TYPE
    SYNTAX      TNamedItemOrEmpty
    MAX-ACCESS  read-write
    STATUS      obsolete
    DESCRIPTION
        "The value of tmnxMDAEgrNamedPoolPolicy specifies a named pool policy
         associated with an MDA egress context. The policy governs the way
         named pools are created at the MDA level.

         This object is obsoleted in 20.0 Release."
    DEFVAL      { "" }
    ::= { tmnxMDAEntry 33 }

tmnxMDAMcPathMgmtPriInUseBw      OBJECT-TYPE
    SYNTAX      Gauge32
    UNITS       "kilobps"
    MAX-ACCESS  read-only
    STATUS      obsolete
    DESCRIPTION
        "The value of tmnxMDAMcPathMgmtPriInUseBw indicates the in use ingress
         multicast bandwidth for the primary forwarding path.

         This object was obsoleted from release 15.0R1."
    ::= { tmnxMDAEntry 36 }

tmnxMDAMcPathMgmtSecInUseBw      OBJECT-TYPE
    SYNTAX      Gauge32
    UNITS       "kilobps"
    MAX-ACCESS  read-only
    STATUS      obsolete
    DESCRIPTION
        "The value of tmnxMDAMcPathMgmtSecInUseBw indicates the in use ingress
         multicast bandwidth for the secondary forwarding path.

         This object was obsoleted from release 15.0R1."
    ::= { tmnxMDAEntry 37 }

tmnxMDAMcPathMgmtAncInUseBw      OBJECT-TYPE
    SYNTAX      Gauge32
    UNITS       "kilobps"
    MAX-ACCESS  read-only
    STATUS      obsolete
    DESCRIPTION
        "The value of tmnxMDAMcPathMgmtAncInUseBw indicates the in use ingress
         multicast bandwidth for the ancillary forwarding path.

         This object was obsoleted from release 15.0R1."
    ::= { tmnxMDAEntry 38 }

tmnxMDAMcPathMgmtBlkHoleInUseBw  OBJECT-TYPE
    SYNTAX      Gauge32
    UNITS       "kilobps"
    MAX-ACCESS  read-only
    STATUS      obsolete
    DESCRIPTION
        "The value of tmnxMDAMcPathMgmtBlkHoleInUseBw indicates the bandwidth
         of the ingress multicast traffic that is being black holed on the MDA.

         This object was obsoleted from release 15.0R1."
    ::= { tmnxMDAEntry 39 }

tmnxMDASynchronousEthernet       OBJECT-TYPE
    SYNTAX      INTEGER {
        not-applicable (0),
        enabled        (1),
        disabled       (2)
    }
    MAX-ACCESS  read-write
    STATUS      current
    DESCRIPTION
        "The value of tmnxMDASynchronousEthernet specifies whether or not the
         MDA maintains synchronous Ethernet (syncE) communication on all of its
         ports.

         not-applicable - The MDA does not support synchronous Ethernet.
         enabled        - The MDA is in synchronous mode.
         disabled       - The MDA is in asynchronous mode (default).

         On MDAs that do not support synchronous ethernet the only supported
         value is 'not-applicable (0)'.

         If tmnxMDASynchronousEthernet is 'enabled (1)' then any port on the
         MDA can be used as a source port in the tmnxSyncIfTimingTable."
    DEFVAL      { disabled }
    ::= { tmnxMDAEntry 40 }

tmnxMDAXplErrorTime              OBJECT-TYPE
    SYNTAX      TimeStamp
    MAX-ACCESS  read-only
    STATUS      current
    DESCRIPTION
        "The value of tmnxMDAXplErrorTime indicates the last time when the
         tmnxEqMdaXplError notification occurred."
    ::= { tmnxMDAEntry 41 }

tmnxMDAXplFailedCount            OBJECT-TYPE
    SYNTAX      Gauge32
    MAX-ACCESS  read-only
    STATUS      current
    DESCRIPTION
        "The value of tmnxMDAXplFailedCount indicates the number of egress XPL
         failures on the MDA since startup."
    ::= { tmnxMDAEntry 42 }

tmnxMDAAtmMode                   OBJECT-TYPE
    SYNTAX      TmnxMdaAtmMode
    MAX-ACCESS  read-write
    STATUS      obsolete
    DESCRIPTION
        "The value of tmnxMDAAtmMode specifies the maximum number of Virtual
         Circuits for the MDA.

         On MDA's that do not support ATM, 'notApplicable' is the only allowed
         value and this is also the default value.

         On MDA's that support ATM, the default value is 'max8kVc'."
    ::= { tmnxMDAEntry 43 }

tmnxMDAIsaTunnelGroup            OBJECT-TYPE
    SYNTAX      TmnxTunnelGroupIdOrZero
    MAX-ACCESS  read-write
    STATUS      current
    DESCRIPTION
        "The value of tmnxMDAIsaTunnelGroup specifies the tunnel group
         identifier associated with this MDA.

         The tunnel groups are configured by tmnxIPsecIsaGrpTable.

         When the object is set to a non-default value, the value of
         'tmnxMDAIsaMemberPoolAssoc' must be default."
    DEFVAL      { 0 }
    ::= { tmnxMDAEntry 46 }

tmnxMDAIsaTunnelGroupInUse       OBJECT-TYPE
    SYNTAX      TruthValue
    MAX-ACCESS  read-only
    STATUS      current
    DESCRIPTION
        "The value of tmnxMDAIsaTunnelGroupInUse indicates if this MDA is
         active in the Integrated Service Adaptor (ISA) tunnel group indicated
         by tmnxMDAIsaTunnelGroup.

         This object has meaning only when the ISA tunnel group is configured
         to be multi-active (i.e. tmnxIPsecIsaGrpMultiActive in
         tmnxIPsecIsaGrpTable is 'true (1)'). In all other cases, the value of
         this object is equal to 'false (2)'"
    ::= { tmnxMDAEntry 47 }

tmnxMDAHwPowerPriority           OBJECT-TYPE
    SYNTAX      Unsigned32 (1..200)
    MAX-ACCESS  read-write
    STATUS      current
    DESCRIPTION
        "The value of tmnxMDAHwPowerPriority specifies the functional priority
         of the MDA. Lower priority (higher numerically) MDAs will power off
         sooner than higher priority (lower numerically) MDAs during a power
         shortage. Lower priority MDAs will also power up after higher priority
         MDAs."
    DEFVAL      { 150 }
    ::= { tmnxMDAEntry 48 }

tmnxMDAFailOnError               OBJECT-TYPE
    SYNTAX      BITS {
        eventGroupA (0)
    }
    MAX-ACCESS  read-write
    STATUS      current
    DESCRIPTION
        "The value of tmnxMDAFailOnError specifies the set of events that, if
         triggered, will cause the MDA to fail. The suppression or generation
         of the NOTIFICATION-TYPE event is independent of the MDA failing.

         The following set of events are configurable:
              eventGroupA (0) - tmnxEqMdaXplError
                              - tmnxEqMdaIngrXplError

         If an XPL error is declared, the MDA is declared failed."
    DEFVAL      { {} }
    ::= { tmnxMDAEntry 49 }

tmnxMDAEgrXplErrThreshold        OBJECT-TYPE
    SYNTAX      Unsigned32 (1..1000000)
    UNITS       "xpl errors"
    MAX-ACCESS  read-write
    STATUS      current
    DESCRIPTION
        "The value of tmnxMDAEgrXplErrThreshold specifies the threshold for
         egress XPL errors that determine a failure scenario."
    DEFVAL      { 1000 }
    ::= { tmnxMDAEntry 50 }

tmnxMDAEgrXplErrWindow           OBJECT-TYPE
    SYNTAX      Unsigned32 (1..1440)
    UNITS       "minutes"
    MAX-ACCESS  read-write
    STATUS      current
    DESCRIPTION
        "The value of tmnxMDAEgrXplErrWindow specifies the window size in
         minutes for egress XPL errors that determine a failure scenario."
    DEFVAL      { 60 }
    ::= { tmnxMDAEntry 51 }

tmnxMDAIngrXplErrThreshold       OBJECT-TYPE
    SYNTAX      Unsigned32 (1..1000000)
    UNITS       "xpl errors"
    MAX-ACCESS  read-write
    STATUS      current
    DESCRIPTION
        "The value of tmnxMDAIngrXplErrThreshold specifies the threshold for
         ingress XPL errors that determine a failure scenario."
    DEFVAL      { 1000 }
    ::= { tmnxMDAEntry 52 }

tmnxMDAIngrXplErrWindow          OBJECT-TYPE
    SYNTAX      Unsigned32 (1..1440)
    UNITS       "minutes"
    MAX-ACCESS  read-write
    STATUS      current
    DESCRIPTION
        "The value of tmnxMDAIngrXplErrWindow specifies the window size in
         minutes for ingress XPL errors that determine a failure scenario."
    DEFVAL      { 60 }
    ::= { tmnxMDAEntry 53 }

tmnxMDAResetOnRecoverableError   OBJECT-TYPE
    SYNTAX      TruthValue
    MAX-ACCESS  read-write
    STATUS      current
    DESCRIPTION
        "The value of tmnxMDAResetOnRecoverableError specifies whether or not
         the system resets the MDA when there are fatal memory parity errors on
         one of the Q-chips on the card with which this MDA is associated.

         If the value of tmnxMDAResetOnRecoverableError is 'true (1)' and there
         is a fatal memory parity error on a Q-chip, the system will reset the
         MDA but not fail it, even if tmnxMDAFailOnError is 'true (1)'."
    DEFVAL      { false }
    ::= { tmnxMDAEntry 54 }

tmnxMDAAssignedLevel             OBJECT-TYPE
    SYNTAX      TmnxMDAFunctionalLevel
    MAX-ACCESS  read-write
    STATUS      current
    DESCRIPTION
        "An integer that specifies the administratively assigned
         (pre-provisioned) MDA functional level variant that should occupy this
         slot in this chassis."
    DEFVAL      { unrestricted }
    ::= { tmnxMDAEntry 55 }

tmnxMDAEquippedLevel             OBJECT-TYPE
    SYNTAX      TmnxMDAFunctionalLevel
    MAX-ACCESS  read-only
    STATUS      current
    DESCRIPTION
        "An integer that indicates the MDA functional-level variant that is
         physically inserted into this slot in this chassis.  If the value of
         tmnxMDAAssignedLevel is not equal to the value of
         tmnxMDAEquippedLevel, a mismatch alarm will be raised."
    ::= { tmnxMDAEntry 56 }

tmnxMDALicensedLevel             OBJECT-TYPE
    SYNTAX      TmnxMDAFunctionalLevel
    MAX-ACCESS  read-only
    STATUS      current
    DESCRIPTION
        "An integer that indicates the MDA functional-level that is licensed
         for this slot in this chassis."
    ::= { tmnxMDAEntry 57 }

tmnxMDALicensedBandwidth         OBJECT-TYPE
    SYNTAX      Unsigned32
    UNITS       "gigabps"
    MAX-ACCESS  read-only
    STATUS      current
    DESCRIPTION
        "Indicates the amount of licensed bandwidth that is used on this
         MDA. Bandwidth becomes licensed as physical connectors are provisioned
         or physical ports are enabled.
         Licensed bandwidth on MDAs that have multiple functional levels
         supported.  The system enforces that the licensed bandwidth does
         not exceed any bandwidth restriction associated with this card's
         licensed level."
    ::= { tmnxMDAEntry 58 }

tmnxMDAIsaMemberPoolAssoc        OBJECT-TYPE
    SYNTAX      TNamedItemOrEmpty
    MAX-ACCESS  read-write
    STATUS      current
    DESCRIPTION
        "The value of tmnxMDAIsaMemberPoolAssoc specifies the name of the IPsec
         ISA member pool this MDA is associated with.

         An 'inconsistentValue' error is returned if this object is set to a
         value which does not have a corresponding entry in
         TIMETRA-CHASSIS-MIB::tmnxIPsecIsaMemberPoolTable.

         When the object is set to a non-default value, the value of
         tmnxMDAIsaTunnelGroup must be default."
    DEFVAL      { "" }
    ::= { tmnxMDAEntry 59 }

tmnxMDAIsaTunnelActiveInGrp      OBJECT-TYPE
    SYNTAX      TmnxTunnelGroupIdOrZero
    MAX-ACCESS  read-only
    STATUS      current
    DESCRIPTION
        "The value of tmnxMDAIsaTunnelActiveInGrp indicates which
         tunnel-group, if any, the MDA is active in.  This value is
         only relevant when the MDA is associated with a member pool."
    ::= { tmnxMDAEntry 60 }

tmnxMDAMacMode                   OBJECT-TYPE
    SYNTAX      INTEGER {
        notApplicable (0),
        mode100g      (1),
        mode800g      (2),
        mode10g       (3)
    }
    MAX-ACCESS  read-write
    STATUS      current
    DESCRIPTION
        "The value of tmnxMDAMacMode indicates the MAC mode to be used on the
         connectors of the MDA."
    DEFVAL      { notApplicable }
    ::= { tmnxMDAEntry 61 }

tmnxMDAIngPreClassifierPolicy    OBJECT-TYPE
    SYNTAX      TLNamedItemOrEmpty
    MAX-ACCESS  read-write
    STATUS      current
    DESCRIPTION
        "The value of tmnxMDAIngPreClassifierPolicy specifies the name of
         ingress qos pre classifier policy to associate with this mda."
    DEFVAL      { "default" }
    ::= { tmnxMDAEntry 62 }

tmnxMDAIngPreClassfrUngtagDot1p  OBJECT-TYPE
    SYNTAX      Dot1PUntagValue
    MAX-ACCESS  read-write
    STATUS      current
    DESCRIPTION
        "The value of tmnxMDAIngPreClassfrUngtagDot1p specifies the dot1p
         mapping for untagged traffic. After the configuration, untagged
         traffic received from any port of the given COE MDA operates identical
         to dot1q encap traffic."
    DEFVAL      { 0 }
    ::= { tmnxMDAEntry 63 }

tmnxCardTypeTable                OBJECT-TYPE
    SYNTAX      SEQUENCE OF TmnxCardTypeEntry
    MAX-ACCESS  not-accessible
    STATUS      current
    DESCRIPTION
        "The card type table has an entry for each card model supported by the
         system."
    ::= { tmnxCardObjs 9 }

tmnxCardTypeEntry                OBJECT-TYPE
    SYNTAX      TmnxCardTypeEntry
    MAX-ACCESS  not-accessible
    STATUS      current
    DESCRIPTION
        "Each row entry represents an Nokia SROS series Card model. Rows in
         this table are created by the agent at initialization and cannot be
         created or destroyed by SNMP Get or Set requests."
    INDEX       { tmnxCardTypeIndex }
    ::= { tmnxCardTypeTable 1 }

TmnxCardTypeEntry                ::= SEQUENCE
{
    tmnxCardTypeIndex                TmnxCardType,
    tmnxCardTypeName                 TNamedItemOrEmpty,
    tmnxCardTypeDescription          TItemDescription,
    tmnxCardTypeStatus               TruthValue
}

tmnxCardTypeIndex                OBJECT-TYPE
    SYNTAX      TmnxCardType
    MAX-ACCESS  not-accessible
    STATUS      current
    DESCRIPTION
        "The unique index value which identifies this type of Nokia SROS series
         card model."
    ::= { tmnxCardTypeEntry 1 }

tmnxCardTypeName                 OBJECT-TYPE
    SYNTAX      TNamedItemOrEmpty
    MAX-ACCESS  read-only
    STATUS      current
    DESCRIPTION
        "The administrative name that identifies this type of Nokia
         SROS series card model.  This name string may be used in
         CLI commands to specify a particular card model type."
    ::= { tmnxCardTypeEntry 2 }

tmnxCardTypeDescription          OBJECT-TYPE
    SYNTAX      TItemDescription
    MAX-ACCESS  read-only
    STATUS      current
    DESCRIPTION
        "A detailed description of this Nokia SROS series card model."
    ::= { tmnxCardTypeEntry 3 }

tmnxCardTypeStatus               OBJECT-TYPE
    SYNTAX      TruthValue
    MAX-ACCESS  read-only
    STATUS      current
    DESCRIPTION
        "When tmnxCardTypeStatus has a value of 'true' it indicates that
         this card model is supported in this revision of the management
         software.  When it has a value of 'false' there is no support."
    ::= { tmnxCardTypeEntry 4 }

tmnxMdaTypeTable                 OBJECT-TYPE
    SYNTAX      SEQUENCE OF TmnxMdaTypeEntry
    MAX-ACCESS  not-accessible
    STATUS      current
    DESCRIPTION
        "The MDA type table has an entry for each MDA card model supported by
         the system."
    ::= { tmnxCardObjs 10 }

tmnxMdaTypeEntry                 OBJECT-TYPE
    SYNTAX      TmnxMdaTypeEntry
    MAX-ACCESS  not-accessible
    STATUS      current
    DESCRIPTION
        "Each row entry represents an Nokia SROS series MDA card
         model.  Rows in this table are created by the agent at initialization
         and cannot be created or destroyed by SNMP Get or Set requests."
    INDEX       { tmnxMdaTypeIndex }
    ::= { tmnxMdaTypeTable 1 }

TmnxMdaTypeEntry                 ::= SEQUENCE
{
    tmnxMdaTypeIndex                 TmnxMdaType,
    tmnxMdaTypeName                  TNamedItemOrEmpty,
    tmnxMdaTypeDescription           TItemDescription,
    tmnxMdaTypeStatus                TruthValue
}

tmnxMdaTypeIndex                 OBJECT-TYPE
    SYNTAX      TmnxMdaType
    MAX-ACCESS  not-accessible
    STATUS      current
    DESCRIPTION
        "The unique index value which identifies this type of Nokia SROS series
         MDA card model."
    ::= { tmnxMdaTypeEntry 1 }

tmnxMdaTypeName                  OBJECT-TYPE
    SYNTAX      TNamedItemOrEmpty
    MAX-ACCESS  read-only
    STATUS      current
    DESCRIPTION
        "The administrative name that identifies this type of Nokia
         SROS series MDA card model.  This name string may be used
         in CLI commands to specify a particular MDA card model type."
    ::= { tmnxMdaTypeEntry 2 }

tmnxMdaTypeDescription           OBJECT-TYPE
    SYNTAX      TItemDescription
    MAX-ACCESS  read-only
    STATUS      current
    DESCRIPTION
        "A detailed description of this Nokia SROS series MDA card model."
    ::= { tmnxMdaTypeEntry 3 }

tmnxMdaTypeStatus                OBJECT-TYPE
    SYNTAX      TruthValue
    MAX-ACCESS  read-only
    STATUS      current
    DESCRIPTION
        "When tmnxMdaTypeStatus has a value of 'true' it indicates that
         this MDA card model is supported in this revision of the management
         software.  When it has a value of 'false' there is no support."
    ::= { tmnxMdaTypeEntry 4 }

tmnxSyncIfTimingTable            OBJECT-TYPE
    SYNTAX      SEQUENCE OF TmnxSyncIfTimingEntry
    MAX-ACCESS  not-accessible
    STATUS      current
    DESCRIPTION
        "The synchronous interface timing table has an entry for each cpm card
         in the system."
    ::= { tmnxCardObjs 11 }

tmnxSyncIfTimingEntry            OBJECT-TYPE
    SYNTAX      TmnxSyncIfTimingEntry
    MAX-ACCESS  not-accessible
    STATUS      current
    DESCRIPTION
        "A row represents the configuration of Synchronous Equipment Timing
         Source (SETS) of the system. Entries cannot be created and deleted
         via SNMP SET operations.  When a tmnxCpmCardEntry is created, a
         tmnxSyncIfTimingEntry is created.  SNMP set operations with
         tmnxCpmCardSlotNum of the secondary CPM will be denied.

         If the value of the reference source port is a valid Port ID then the
         reference is a port.  If the value of the source hardware is a valid
         non-zero HWIndex then the source is the hardware specified by the
         HWIndex."
    AUGMENTS    { tmnxCpmCardEntry }
    ::= { tmnxSyncIfTimingTable 1 }

TmnxSyncIfTimingEntry            ::= SEQUENCE
{
    tmnxSyncIfTimingRevert           TruthValue,
    tmnxSyncIfTimingRefOrder1        TmnxSETSRefSource,
    tmnxSyncIfTimingRefOrder2        TmnxSETSRefSource,
    tmnxSyncIfTimingRef1SrcPort      TmnxPortID,
    tmnxSyncIfTimingRef1AdminStatus  TmnxPortAdminStatus,
    tmnxSyncIfTimingRef1InUse        TruthValue,
    tmnxSyncIfTimingRef1Qualified    TmnxSETSRefQualified,
    tmnxSyncIfTimingRef1Alarm        TmnxSETSRefAlarm,
    tmnxSyncIfTimingRef2SrcPort      TmnxPortID,
    tmnxSyncIfTimingRef2AdminStatus  TmnxPortAdminStatus,
    tmnxSyncIfTimingRef2InUse        TruthValue,
    tmnxSyncIfTimingRef2Qualified    TmnxSETSRefQualified,
    tmnxSyncIfTimingRef2Alarm        TmnxSETSRefAlarm,
    tmnxSyncIfTimingFreqOffset       Integer32,
    tmnxSyncIfTimingStatus           TmnxSETSStatus,
    tmnxSyncIfTimingRefOrder3        TmnxSETSRefSource,
    tmnxSyncIfTimingBITSIfType       TmnxBITSIfType,
    tmnxSyncIfTimingBITSAdminStatus  TmnxPortAdminStatus,
    tmnxSyncIfTimingBITSInUse        TruthValue,
    tmnxSyncIfTimingBITSQualified    TmnxSETSRefQualified,
    tmnxSyncIfTimingBITSAlarm        TmnxSETSRefAlarm,
    tmnxSyncIfTimingRef1SrcHw        TmnxHwIndexOrZero,
    tmnxSyncIfTimingRef1BITSIfType   TmnxBITSIfType,
    tmnxSyncIfTimingRef2SrcHw        TmnxHwIndexOrZero,
    tmnxSyncIfTimingRef2BITSIfType   TmnxBITSIfType,
    tmnxSyncIfTimingBITSOutAdmStatus TmnxPortAdminStatus,
    tmnxSyncIfTimingBITSOutLineLen   INTEGER,
    tmnxSyncIfTimingRef1CfgQltyLevel TmnxSSMQualityLevel,
    tmnxSyncIfTimingRef1RxQltyLevel  TmnxSSMQualityLevel,
    tmnxSyncIfTimingRef2CfgQltyLevel TmnxSSMQualityLevel,
    tmnxSyncIfTimingRef2RxQltyLevel  TmnxSSMQualityLevel,
    tmnxSyncIfTimingBITSCfgQltyLevel TmnxSSMQualityLevel,
    tmnxSyncIfTimingBITSRxQltyLevel  TmnxSSMQualityLevel,
    tmnxSyncIfTimingBITS2InUse       TruthValue,
    tmnxSyncIfTimingBITS2Qualified   TmnxSETSRefQualified,
    tmnxSyncIfTimingBITS2Alarm       TmnxSETSRefAlarm,
    tmnxSyncIfTimingBITS2RxQltyLevel TmnxSSMQualityLevel,
    tmnxSyncIfTimingRef1State        TmnxRefInState,
    tmnxSyncIfTimingRef2State        TmnxRefInState,
    tmnxSyncIfTimingBITSState        TmnxRefInState,
    tmnxSyncIfTimingBITS2State       TmnxRefInState,
    tmnxSyncIfTimingRef1NationalUse  Unsigned32,
    tmnxSyncIfTimingRef2NationalUse  Unsigned32,
    tmnxSyncIfTimingBITSNationalUse  Unsigned32,
    tmnxSyncIfTimingQLSelection      TmnxEnabledDisabled,
    tmnxSyncIfTimingOtherCPMInUse    TruthValue,
    tmnxSyncIfTimingOtherCPMQual     TmnxSETSRefQualified,
    tmnxSyncIfTimingOtherCPMAlarm    TmnxSETSRefAlarm,
    tmnxSyncIfTimingOtherCPMState    TmnxRefInState,
    tmnxSyncIfTimingBITSOutRefSel    TmnxSETSRefSource,
    tmnxSyncIfTimingBITSTxQltyLevel  TmnxSSMQualityLevel,
    tmnxSyncIfTimingBITS2AdminStatus TmnxPortAdminStatus,
    tmnxSyncIfTimingSystemQltyLevel  TmnxSSMQualityLevel,
    tmnxSyncIfTimingRefOrder4        TmnxSETSRefSource,
    tmnxSyncIfTimingPTPAdminStatus   TmnxPortAdminStatus,
    tmnxSyncIfTimingPTPInUse         TruthValue,
    tmnxSyncIfTimingPTPQualified     TmnxSETSRefQualified,
    tmnxSyncIfTimingPTPAlarm         TmnxSETSRefAlarm,
    tmnxSyncIfTimingPTPCfgQltyLevel  TmnxSSMQualityLevel,
    tmnxSyncIfTimingPTPRxQltyLevel   TmnxSSMQualityLevel,
    tmnxSyncIfTimingPTPState         TmnxRefInState,
    tmnxSyncIfTimingBITSOutSource    TmnxBITSOutSource,
    tmnxSyncIfTimingBITSOutQlMin     TmnxSSMQualityLevel,
    tmnxSyncIfTimingBITSOutSquelch   TruthValue,
    tmnxSyncIfTimingQlMin            TmnxSSMQualityLevel,
    tmnxSyncIfTimingWaitToRestorTime Unsigned32,
    tmnxSyncIfTimingSyncEAdminStatus TmnxPortAdminStatus,
    tmnxSyncIfTimingSyncEInUse       TruthValue,
    tmnxSyncIfTimingSyncEQualified   TmnxSETSRefQualified,
    tmnxSyncIfTimingSyncEAlarm       TmnxSETSRefAlarm,
    tmnxSyncIfTimingSyncECfgQltyLevl TmnxSSMQualityLevel,
    tmnxSyncIfTimingSyncERxQltyLevel TmnxSSMQualityLevel,
    tmnxSyncIfTimingSyncEState       TmnxRefInState,
    tmnxSyncIfTimingSyncE2AdmnStatus TmnxPortAdminStatus,
    tmnxSyncIfTimingSyncE2InUse      TruthValue,
    tmnxSyncIfTimingSyncE2Qualified  TmnxSETSRefQualified,
    tmnxSyncIfTimingSyncE2Alarm      TmnxSETSRefAlarm,
    tmnxSyncIfTimingSyncE2RxQltyLevl TmnxSSMQualityLevel,
    tmnxSyncIfTimingSyncE2State      TmnxRefInState,
    tmnxSyncIfTimingRefOrder5        TmnxSETSRefSource,
    tmnxSyncIfTimingGnssAdminStatus  TmnxPortAdminStatus,
    tmnxSyncIfTimingGnssInUse        TruthValue,
    tmnxSyncIfTimingGnssQualified    TmnxSETSRefQualified,
    tmnxSyncIfTimingGnssAlarm        TmnxSETSRefAlarm,
    tmnxSyncIfTimingGnssCfgQltyLevel TmnxSSMQualityLevel,
    tmnxSyncIfTimingGnssRxQltyLevel  TmnxSSMQualityLevel,
    tmnxSyncIfTimingGnssState        TmnxRefInState,
    tmnxSyncIfTimingGnss2AdminStatus TmnxPortAdminStatus,
    tmnxSyncIfTimingGnss2InUse       TruthValue,
    tmnxSyncIfTimingGnss2Qualified   TmnxSETSRefQualified,
    tmnxSyncIfTimingGnss2Alarm       TmnxSETSRefAlarm,
    tmnxSyncIfTimingGnss2RxQltyLevel TmnxSSMQualityLevel,
    tmnxSyncIfTimingGnss2State       TmnxRefInState,
    tmnxSyncIfTimingRefOrder6        TmnxSETSRefSource,
    tmnxSyncIfTimingFreqOffsetPpb    Integer32
}

tmnxSyncIfTimingRevert           OBJECT-TYPE
    SYNTAX      TruthValue
    MAX-ACCESS  read-only
    STATUS      current
    DESCRIPTION
        "The value of tmnxSyncIfTimingRevert indicates whether the reference
         source will revert to a higher priority source that has been
         re-validated or newly validated.

         The synchronous interface timing subsystem is by default non-revertive
         ('false')."
    ::= { tmnxSyncIfTimingEntry 1 }

tmnxSyncIfTimingRefOrder1        OBJECT-TYPE
    SYNTAX      TmnxSETSRefSource
    MAX-ACCESS  read-only
    STATUS      current
    DESCRIPTION
        "The value of tmnxSyncIfTimingRefOrder1 indicates the most preferred
         timing reference source.

         Four different timing input references may be specified in the
         reference order ('bits', 'reference1', 'reference2', and 'ptp').

         The synchronous equipment timing subsystem chooses a reference based
         on priority."
    ::= { tmnxSyncIfTimingEntry 2 }

tmnxSyncIfTimingRefOrder2        OBJECT-TYPE
    SYNTAX      TmnxSETSRefSource
    MAX-ACCESS  read-only
    STATUS      current
    DESCRIPTION
        "The value of tmnxSyncIfTimingRefOrder2 indicates the second most
         preferred timing reference for the synchronous equipment timing
         subsystem."
    ::= { tmnxSyncIfTimingEntry 3 }

tmnxSyncIfTimingRef1SrcPort      OBJECT-TYPE
    SYNTAX      TmnxPortID
    MAX-ACCESS  read-only
    STATUS      current
    DESCRIPTION
        "The value of tmnxSyncIfTimingRef1SrcPort indicates the source port of
         the first timing reference.

         A value of '1e000000'H indicates that there is no source port for this
         reference."
    ::= { tmnxSyncIfTimingEntry 4 }

tmnxSyncIfTimingRef1AdminStatus  OBJECT-TYPE
    SYNTAX      TmnxPortAdminStatus
    MAX-ACCESS  read-only
    STATUS      current
    DESCRIPTION
        "The value of tmnxSyncIfTimingRef1AdminStatus indicates the
         administrative status of the first timing reference."
    ::= { tmnxSyncIfTimingEntry 5 }

tmnxSyncIfTimingRef1InUse        OBJECT-TYPE
    SYNTAX      TruthValue
    MAX-ACCESS  read-only
    STATUS      current
    DESCRIPTION
        "The value of tmnxSyncIfTimingRef1InUse indicates whether the first
         timing reference is presently being used by the synchronous timing
         subsystem.  If it is in use, tmnxSyncIfTimingFreqOffset indicates
         the frequency offset for this reference."
    ::= { tmnxSyncIfTimingEntry 6 }

tmnxSyncIfTimingRef1Qualified    OBJECT-TYPE
    SYNTAX      TmnxSETSRefQualified
    MAX-ACCESS  read-only
    STATUS      current
    DESCRIPTION
        "The value of tmnxSyncIfTimingRef1Qualified indicates whether the first
         timing reference is qualified for use by the synchronous timing
         subsystem.  If tmnxSyncIfTimingRef1Qualified is set to 'not-qualified',
         then the object tmnxSyncIfTimingRef1Alarm gives the reason for
         disqualification."
    ::= { tmnxSyncIfTimingEntry 7 }

tmnxSyncIfTimingRef1Alarm        OBJECT-TYPE
    SYNTAX      TmnxSETSRefAlarm
    MAX-ACCESS  read-only
    STATUS      current
    DESCRIPTION
        "The value of tmnxSyncIfTimingRef1Alarm indicates the alarms on the
         first reference.  If any of the bits is set to '1', then the first
         reference is disqualified by the timing subsystem and the value of
         tmnxSyncIfTimingRef1Qualified is set to 'not-qualified'.
         los    - loss of signal
         oof    - out of frequency range
         oopir  - out of pull in range"
    ::= { tmnxSyncIfTimingEntry 8 }

tmnxSyncIfTimingRef2SrcPort      OBJECT-TYPE
    SYNTAX      TmnxPortID
    MAX-ACCESS  read-only
    STATUS      current
    DESCRIPTION
        "The value of tmnxSyncIfTimingRef2SrcPort indicates the source port of
         the second timing reference.

         A value of '1e000000'H indicates that there is no source port for this
         reference."
    ::= { tmnxSyncIfTimingEntry 9 }

tmnxSyncIfTimingRef2AdminStatus  OBJECT-TYPE
    SYNTAX      TmnxPortAdminStatus
    MAX-ACCESS  read-only
    STATUS      current
    DESCRIPTION
        "The value of tmnxSyncIfTimingRef2AdminStatus indicates the
         administrative status of the second timing reference."
    ::= { tmnxSyncIfTimingEntry 10 }

tmnxSyncIfTimingRef2InUse        OBJECT-TYPE
    SYNTAX      TruthValue
    MAX-ACCESS  read-only
    STATUS      current
    DESCRIPTION
        "The value of tmnxSyncIfTimingRef2InUse indicates whether the second
         timing reference is presently being used by the synchronous timing
         subsystem."
    ::= { tmnxSyncIfTimingEntry 11 }

tmnxSyncIfTimingRef2Qualified    OBJECT-TYPE
    SYNTAX      TmnxSETSRefQualified
    MAX-ACCESS  read-only
    STATUS      current
    DESCRIPTION
        "The value of tmnxSyncIfTimingRef2Qualified indicates whether the
         second timing reference is qualified for use by the synchronous
         timing subsystem.  If tmnxSyncIfTimingRef2Qualified is 'not-qualified'
         then the object tmnxSyncIfTimingRef2Alarm gives the reason for
         disqualification."
    ::= { tmnxSyncIfTimingEntry 12 }

tmnxSyncIfTimingRef2Alarm        OBJECT-TYPE
    SYNTAX      TmnxSETSRefAlarm
    MAX-ACCESS  read-only
    STATUS      current
    DESCRIPTION
        "The value of tmnxSyncIfTimingRef2Alarm indicates the alarms on the
         second reference.  If any of the bits is set to '1', then the second
         reference is disqualified by the timing subsystem and the value of
         tmnxSyncIfTimingRef2Qualified is set to 'not-qualified'.
         los    - loss of signal
         oof    - out of frequency range
         oopir  - out of pull in range"
    ::= { tmnxSyncIfTimingEntry 13 }

tmnxSyncIfTimingFreqOffset       OBJECT-TYPE
    SYNTAX      Integer32
    UNITS       "parts-per-million"
    MAX-ACCESS  read-only
    STATUS      current
    DESCRIPTION
        "The value of tmnxSyncIfTimingFreqOffset indicates the frequency offset
         of the current selected timing reference in parts per million (ppm).

         The object tmnxSyncIfTimingFreqOffsetPpb, which provides a higher
         precision, may also be available in this table."
    ::= { tmnxSyncIfTimingEntry 14 }

tmnxSyncIfTimingStatus           OBJECT-TYPE
    SYNTAX      TmnxSETSStatus
    MAX-ACCESS  read-only
    STATUS      current
    DESCRIPTION
        "The value of tmnxSyncIfTimingStatus indicates the present status of
         the Synchronous Timing Equipment Source (SETS)."
    ::= { tmnxSyncIfTimingEntry 15 }

tmnxSyncIfTimingRefOrder3        OBJECT-TYPE
    SYNTAX      TmnxSETSRefSource
    MAX-ACCESS  read-only
    STATUS      current
    DESCRIPTION
        "The value of tmnxSyncIfTimingRefOrder3 is the third most preferred
         timing reference for the synchronous equipment timing subsystem."
    ::= { tmnxSyncIfTimingEntry 16 }

tmnxSyncIfTimingBITSIfType       OBJECT-TYPE
    SYNTAX      TmnxBITSIfType
    MAX-ACCESS  read-only
    STATUS      current
    DESCRIPTION
        "The value of tmnxSyncIfTimingBITSIfType indicates the interface type
         of the BITS (Building Integrated Timing Supply) timing reference. It
         also indicates the framing type of the interface."
    ::= { tmnxSyncIfTimingEntry 17 }

tmnxSyncIfTimingBITSAdminStatus  OBJECT-TYPE
    SYNTAX      TmnxPortAdminStatus
    MAX-ACCESS  read-only
    STATUS      current
    DESCRIPTION
        "The value of tmnxSyncIfTimingBITSAdminStatus indicates administrative
         status of the BITS (Building Integrated Timing Supply) input timing
         reference.

         The value of this object for the extension chassis in an XRS-40 system
         is always 'inService(2)'."
    ::= { tmnxSyncIfTimingEntry 18 }

tmnxSyncIfTimingBITSInUse        OBJECT-TYPE
    SYNTAX      TruthValue
    MAX-ACCESS  read-only
    STATUS      current
    DESCRIPTION
        "The value of tmnxSyncIfTimingBITSInUse indicates whether the BITS
         timing reference is presently being used by the synchronous timing
         subsystem.  If it is in use, tmnxSyncIfTimingFreqOffset indicates
         the frequency offset for this reference."
    ::= { tmnxSyncIfTimingEntry 19 }

tmnxSyncIfTimingBITSQualified    OBJECT-TYPE
    SYNTAX      TmnxSETSRefQualified
    MAX-ACCESS  read-only
    STATUS      current
    DESCRIPTION
        "The value of tmnxSyncIfTimingBITSQualified indicates whether the BITS
         timing reference is qualified for use by the synchronous timing
         subsystem.  If tmnxSyncIfTimingBITSQualified is 'not-qualified', then
         the object tmnxSyncIfTimingBITSAlarm gives the reason for
         disqualification."
    ::= { tmnxSyncIfTimingEntry 20 }

tmnxSyncIfTimingBITSAlarm        OBJECT-TYPE
    SYNTAX      TmnxSETSRefAlarm
    MAX-ACCESS  read-only
    STATUS      current
    DESCRIPTION
        "The value of tmnxSyncIfTimingBITSAlarm indicates the alarms on the
         BITS reference.  If any of the bits is set to '1', then the BITS
         reference is disqualified by the timing subsystem and the value of
         tmnxSyncIfTimingBITSQualified is set to 'not-qualified'."
    ::= { tmnxSyncIfTimingEntry 21 }

tmnxSyncIfTimingRef1SrcHw        OBJECT-TYPE
    SYNTAX      TmnxHwIndexOrZero
    MAX-ACCESS  read-only
    STATUS      obsolete
    DESCRIPTION
        "The value of tmnxSyncIfTimingRef1SrcHw indicates the source HW index
         of the first timing reference if source is not a port.

         This object was obsoleted in release 20.5."
    ::= { tmnxSyncIfTimingEntry 22 }

tmnxSyncIfTimingRef1BITSIfType   OBJECT-TYPE
    SYNTAX      TmnxBITSIfType
    MAX-ACCESS  read-only
    STATUS      obsolete
    DESCRIPTION
        "The value of tmnxSyncIfTimingRef1BITSIfType indicates the interface
         type of the first timing reference if the source is BITS.  It also
         indicates the framing type of the interface.

         This object was obsoleted in release 20.5."
    ::= { tmnxSyncIfTimingEntry 23 }

tmnxSyncIfTimingRef2SrcHw        OBJECT-TYPE
    SYNTAX      TmnxHwIndexOrZero
    MAX-ACCESS  read-only
    STATUS      obsolete
    DESCRIPTION
        "The value of tmnxSyncIfTimingRef2SrcHw indicates the source HW index
         of the second timing reference if source is not a port.

         This object was obsoleted in release 20.5."
    ::= { tmnxSyncIfTimingEntry 24 }

tmnxSyncIfTimingRef2BITSIfType   OBJECT-TYPE
    SYNTAX      TmnxBITSIfType
    MAX-ACCESS  read-only
    STATUS      obsolete
    DESCRIPTION
        "The value of tmnxSyncIfTimingRef2BITSIfType indicates the interface
         type of the second timing reference if the source is BITS. It also
         indicates the framing type of the interface.

         This object was obsoleted in release 20.5."
    ::= { tmnxSyncIfTimingEntry 25 }

tmnxSyncIfTimingBITSOutAdmStatus OBJECT-TYPE
    SYNTAX      TmnxPortAdminStatus
    MAX-ACCESS  read-only
    STATUS      current
    DESCRIPTION
        "The value of tmnxSyncIfTimingBITSOutAdmStatus indicates administrative
         status of the BITS (Building Integrated Timing Supply) output timing
         reference."
    ::= { tmnxSyncIfTimingEntry 26 }

tmnxSyncIfTimingBITSOutLineLen   OBJECT-TYPE
    SYNTAX      INTEGER {
        lengthNotApplicable (0),
        length0To110        (1),
        length110To220      (2),
        length220To330      (3),
        length330To440      (4),
        length440To550      (5),
        length550To660      (6)
    }
    MAX-ACCESS  read-only
    STATUS      current
    DESCRIPTION
        "tmnxSyncIfTimingBITSOutLineLen indicates the length of the line
         (in feet) for the BITS (Building Integrated Timing Supply) output.
         The following values are valid:
             lengthNotApplicable (0) - When BITS output is not supported
             length0To110        (1) - For line length from 0 to 110 feet
             length110To220      (2) - For line length from 110 to 220 feet
             length220To330      (3) - For line length from 230 to 330 feet
             length330To440      (4) - For line length from 330 to 440 feet
             length440To550      (5) - For line length from 440 to 550 feet
             length550To660      (6) - For line length from 550 to 660 feet
         The default is 'lengthNotApplicable' on CPM cards which do not
         support line length.  Otherwise, the default is 'length0To110'."
    ::= { tmnxSyncIfTimingEntry 27 }

tmnxSyncIfTimingRef1CfgQltyLevel OBJECT-TYPE
    SYNTAX      TmnxSSMQualityLevel
    MAX-ACCESS  read-only
    STATUS      current
    DESCRIPTION
        "The value of tmnxSyncIfTimingRef1CfgQltyLevel indicates the configured
         Quality Level of Reference 1. A value of 'unknown (0)' indicates
         Reference 1 is not forced to a specific quality level."
    ::= { tmnxSyncIfTimingEntry 28 }

tmnxSyncIfTimingRef1RxQltyLevel  OBJECT-TYPE
    SYNTAX      TmnxSSMQualityLevel
    MAX-ACCESS  read-only
    STATUS      current
    DESCRIPTION
        "The value of tmnxSyncIfTimingRef1RxQltyLevel indicates the received
         SSM Quality Level of Reference 1."
    ::= { tmnxSyncIfTimingEntry 29 }

tmnxSyncIfTimingRef2CfgQltyLevel OBJECT-TYPE
    SYNTAX      TmnxSSMQualityLevel
    MAX-ACCESS  read-only
    STATUS      current
    DESCRIPTION
        "The value of tmnxSyncIfTimingRef2CfgQltyLevel indicates the configured
         Quality Level of Reference 2. A value of 'unknown (0)' indicates
         Reference 2 is not forced to a specific quality level."
    ::= { tmnxSyncIfTimingEntry 30 }

tmnxSyncIfTimingRef2RxQltyLevel  OBJECT-TYPE
    SYNTAX      TmnxSSMQualityLevel
    MAX-ACCESS  read-only
    STATUS      current
    DESCRIPTION
        "The value of tmnxSyncIfTimingRef2RxQltyLevel indicates the received
         SSM Quality Level of Reference 2."
    ::= { tmnxSyncIfTimingEntry 31 }

tmnxSyncIfTimingBITSCfgQltyLevel OBJECT-TYPE
    SYNTAX      TmnxSSMQualityLevel
    MAX-ACCESS  read-only
    STATUS      current
    DESCRIPTION
        "The value of tmnxSyncIfTimingBITSCfgQltyLevel indicates the configured
         Quality Level of the BITS interface. A value of 'unknown (0)'
         indicates the BITS interface is not forced to a specific quality
         level."
    ::= { tmnxSyncIfTimingEntry 32 }

tmnxSyncIfTimingBITSRxQltyLevel  OBJECT-TYPE
    SYNTAX      TmnxSSMQualityLevel
    MAX-ACCESS  read-only
    STATUS      current
    DESCRIPTION
        "The value of tmnxSyncIfTimingBITSRxQltyLevel indicates the received
         SSM Quality Level of the BITS interface."
    ::= { tmnxSyncIfTimingEntry 33 }

tmnxSyncIfTimingBITS2InUse       OBJECT-TYPE
    SYNTAX      TruthValue
    MAX-ACCESS  read-only
    STATUS      current
    DESCRIPTION
        "The value of tmnxSyncIfTimingBITS2InUse indicates whether the BITS2
         timing reference is presently being used by the synchronous timing
         subsystem.  If it is in use, tmnxSyncIfTimingFreqOffset indicates
         the frequency offset for this reference."
    ::= { tmnxSyncIfTimingEntry 34 }

tmnxSyncIfTimingBITS2Qualified   OBJECT-TYPE
    SYNTAX      TmnxSETSRefQualified
    MAX-ACCESS  read-only
    STATUS      current
    DESCRIPTION
        "The value of tmnxSyncIfTimingBITS2Qualified indicates whether the BITS2
         timing reference is qualified for use by the synchronous timing
         subsystem.  If tmnxSyncIfTimingBITS2Qualified is 'not-qualified', then
         the object tmnxSyncIfTimingBITS2Alarm gives the reason for
         disqualification."
    ::= { tmnxSyncIfTimingEntry 35 }

tmnxSyncIfTimingBITS2Alarm       OBJECT-TYPE
    SYNTAX      TmnxSETSRefAlarm
    MAX-ACCESS  read-only
    STATUS      current
    DESCRIPTION
        "The value of tmnxSyncIfTimingBITS2Alarm indicates the alarms on the
         BITS2 reference.  If any of the bits is set to '1', then the BITS2
         reference is disqualified by the timing subsystem and the value of
         tmnxSyncIfTimingBITSQualified is set to 'not-qualified'."
    ::= { tmnxSyncIfTimingEntry 36 }

tmnxSyncIfTimingBITS2RxQltyLevel OBJECT-TYPE
    SYNTAX      TmnxSSMQualityLevel
    MAX-ACCESS  read-only
    STATUS      current
    DESCRIPTION
        "The value of tmnxSyncIfTimingBITS2RxQltyLevel indicates the received
         SSM Rx Quality Level of the BITS2 interface."
    ::= { tmnxSyncIfTimingEntry 37 }

tmnxSyncIfTimingRef1State        OBJECT-TYPE
    SYNTAX      TmnxRefInState
    MAX-ACCESS  read-only
    STATUS      current
    DESCRIPTION
        "The value of tmnxSyncIfTimingRef1State indicates the operational state
         of the Reference 1 Timing."
    ::= { tmnxSyncIfTimingEntry 38 }

tmnxSyncIfTimingRef2State        OBJECT-TYPE
    SYNTAX      TmnxRefInState
    MAX-ACCESS  read-only
    STATUS      current
    DESCRIPTION
        "The value of tmnxSyncIfTimingRef2State indicates the operational state
         of the Reference 2 Timing."
    ::= { tmnxSyncIfTimingEntry 39 }

tmnxSyncIfTimingBITSState        OBJECT-TYPE
    SYNTAX      TmnxRefInState
    MAX-ACCESS  read-only
    STATUS      current
    DESCRIPTION
        "The value of tmnxSyncIfTimingBITSState indicates the operational state
         of the BITS Timing Interface."
    ::= { tmnxSyncIfTimingEntry 40 }

tmnxSyncIfTimingBITS2State       OBJECT-TYPE
    SYNTAX      TmnxRefInState
    MAX-ACCESS  read-only
    STATUS      current
    DESCRIPTION
        "The value of tmnxSyncIfTimingBITS2State indicates the operational
         state of the BITS2 Timing Interface."
    ::= { tmnxSyncIfTimingEntry 41 }

tmnxSyncIfTimingRef1NationalUse  OBJECT-TYPE
    SYNTAX      Unsigned32 (4..8)
    MAX-ACCESS  read-only
    STATUS      obsolete
    DESCRIPTION
        "The value of tmnxSyncIfTimingRef1NationalUse indicates the national
         use bit to carry SSM Messages. This applies only to E1 BITS
         interfaces.

         This object was obsoleted in release 20.5."
    DEFVAL      { 8 }
    ::= { tmnxSyncIfTimingEntry 42 }

tmnxSyncIfTimingRef2NationalUse  OBJECT-TYPE
    SYNTAX      Unsigned32 (4..8)
    MAX-ACCESS  read-only
    STATUS      obsolete
    DESCRIPTION
        "The value of tmnxSyncIfTimingRef2NationalUse indicates the national
         use bit to carry SSM Messages. This applies only to E1 BITS
         interfaces.

         This object was obsoleted in release 20.5."
    DEFVAL      { 8 }
    ::= { tmnxSyncIfTimingEntry 43 }

tmnxSyncIfTimingBITSNationalUse  OBJECT-TYPE
    SYNTAX      Unsigned32 (4..8)
    MAX-ACCESS  read-only
    STATUS      current
    DESCRIPTION
        "The value of tmnxSyncIfTimingBITSNationalUse indicates the national
         use bit to carry SSM Messages. This applies only to E1 BITS
         interfaces."
    DEFVAL      { 8 }
    ::= { tmnxSyncIfTimingEntry 44 }

tmnxSyncIfTimingQLSelection      OBJECT-TYPE
    SYNTAX      TmnxEnabledDisabled
    MAX-ACCESS  read-only
    STATUS      current
    DESCRIPTION
        "The value of tmnxSyncIfTimingQLSelection indicates whether or not the
         timing reference selection process uses the quality level of each
         timing reference when making the decision on which reference should
         provide system timing."
    REFERENCE
        "ITU-T Recommendation G.781, June 1999, Section 5.12"
    ::= { tmnxSyncIfTimingEntry 45 }

tmnxSyncIfTimingOtherCPMInUse    OBJECT-TYPE
    SYNTAX      TruthValue
    MAX-ACCESS  read-only
    STATUS      current
    DESCRIPTION
        "The value of tmnxSyncIfTimingOtherCPMInUse indicates whether the
         timing reference from the other CPM is presently being used by the
         synchronous timing subsystem on the this CPM."
    DEFVAL      { false }
    ::= { tmnxSyncIfTimingEntry 46 }

tmnxSyncIfTimingOtherCPMQual     OBJECT-TYPE
    SYNTAX      TmnxSETSRefQualified
    MAX-ACCESS  read-only
    STATUS      current
    DESCRIPTION
        "The value of tmnxSyncIfTimingOtherCPMQual indicates whether the
         timing reference from the other CPM is qualified for use by the
         synchronous timing subsystem on the local CPM.  If
         tmnxSyncIfTimingOtherCPMQual is 'not-qualified', then the object
         tmnxSyncIfTimingOtherCPMAlarm gives the reason for disqualification."
    DEFVAL      { not-qualified }
    ::= { tmnxSyncIfTimingEntry 47 }

tmnxSyncIfTimingOtherCPMAlarm    OBJECT-TYPE
    SYNTAX      TmnxSETSRefAlarm
    MAX-ACCESS  read-only
    STATUS      current
    DESCRIPTION
        "The value of tmnxSyncIfTimingOtherCPMAlarm indicates the alarms on the
         timing reference from the other CPM.  If any of the bits is set to
         '1', then the reference is disqualified by the timing subsystem and the
         value of tmnxSyncIfTimingOtherCPMQual is set to 'not-qualified'."
    DEFVAL      { {} }
    ::= { tmnxSyncIfTimingEntry 48 }

tmnxSyncIfTimingOtherCPMState    OBJECT-TYPE
    SYNTAX      TmnxRefInState
    MAX-ACCESS  read-only
    STATUS      current
    DESCRIPTION
        "The value of tmnxSyncIfTimingOtherCPMState indicates the operational
         state of the timing reference from the other CPM on the local CPM."
    DEFVAL      { disabled }
    ::= { tmnxSyncIfTimingEntry 49 }

tmnxSyncIfTimingBITSOutRefSel    OBJECT-TYPE
    SYNTAX      TmnxSETSRefSource
    MAX-ACCESS  read-only
    STATUS      current
    DESCRIPTION
        "The value of tmnxSyncIfTimingBITSOutRefSel indicates the reference
         source for BITS output."
    DEFVAL      { noReference }
    ::= { tmnxSyncIfTimingEntry 50 }

tmnxSyncIfTimingBITSTxQltyLevel  OBJECT-TYPE
    SYNTAX      TmnxSSMQualityLevel
    MAX-ACCESS  read-only
    STATUS      current
    DESCRIPTION
        "The value of tmnxSyncIfTimingBITSTxQltyLevel indicates the transmitted
         SSM Tx Quality Level of the BITS interface."
    ::= { tmnxSyncIfTimingEntry 51 }

tmnxSyncIfTimingBITS2AdminStatus OBJECT-TYPE
    SYNTAX      TmnxPortAdminStatus
    MAX-ACCESS  read-only
    STATUS      current
    DESCRIPTION
        "The value of tmnxSyncIfTimingBITS2AdminStatus indicates administrative
         status of the BITS2 (Building Integrated Timing Supply) input timing
         reference."
    ::= { tmnxSyncIfTimingEntry 52 }

tmnxSyncIfTimingSystemQltyLevel  OBJECT-TYPE
    SYNTAX      TmnxSSMQualityLevel
    MAX-ACCESS  read-only
    STATUS      current
    DESCRIPTION
        "The value of tmnxSyncIfTimingSystemQltyLevel indicates the quality
         level of the system timing reference.  This is normally the quality
         level of the selected timing reference.  If no timing reference has
         been selected, it indicates the freerun/holdover quality of the
         system."
    ::= { tmnxSyncIfTimingEntry 53 }

tmnxSyncIfTimingRefOrder4        OBJECT-TYPE
    SYNTAX      TmnxSETSRefSource
    MAX-ACCESS  read-only
    STATUS      current
    DESCRIPTION
        "The value of tmnxSyncIfTimingRefOrder4 is the fourth most preferred
         timing reference for the synchronous equipment timing subsystem."
    ::= { tmnxSyncIfTimingEntry 54 }

tmnxSyncIfTimingPTPAdminStatus   OBJECT-TYPE
    SYNTAX      TmnxPortAdminStatus
    MAX-ACCESS  read-only
    STATUS      current
    DESCRIPTION
        "The value of tmnxSyncIfTimingPTPAdminStatus indicates the
         administrative status of the Precision Timing Protocol (PTP) timing
         reference."
    ::= { tmnxSyncIfTimingEntry 55 }

tmnxSyncIfTimingPTPInUse         OBJECT-TYPE
    SYNTAX      TruthValue
    MAX-ACCESS  read-only
    STATUS      current
    DESCRIPTION
        "The value of tmnxSyncIfTimingPTPInUse indicates whether the Precision
         Timing Protocol (PTP) timing reference is presently being used by the
         synchronous timing subsystem.  If it is in use,
         tmnxSyncIfTimingFreqOffset indicates the frequency offset for this
         reference."
    ::= { tmnxSyncIfTimingEntry 56 }

tmnxSyncIfTimingPTPQualified     OBJECT-TYPE
    SYNTAX      TmnxSETSRefQualified
    MAX-ACCESS  read-only
    STATUS      current
    DESCRIPTION
        "The value of tmnxSyncIfTimingPTPQualified indicates whether the
         Precision Timing Protocol (PTP) timing reference is qualified for use
         by the synchronous timing subsystem.  If tmnxSyncIfTimingPTPQualified
         is set to 'not-qualified', then the object tmnxSyncIfTimingPTPAlarm
         gives the reason for the disqualification."
    ::= { tmnxSyncIfTimingEntry 57 }

tmnxSyncIfTimingPTPAlarm         OBJECT-TYPE
    SYNTAX      TmnxSETSRefAlarm
    MAX-ACCESS  read-only
    STATUS      current
    DESCRIPTION
        "The value of tmnxSyncIfTimingPTPAlarm indicates the alarms on the
         Precision Timing Protocol (PTP) reference.  If any of the bits is set
         to '1', then the PTP reference is disqualified by the timing subsystem
         and the value of tmnxSyncIfTimingPTPQualified is set to
         'not-qualified'.
         los     - loss of signal
         oof     - out of frequency range
         oopir   - out of pull in range"
    ::= { tmnxSyncIfTimingEntry 58 }

tmnxSyncIfTimingPTPCfgQltyLevel  OBJECT-TYPE
    SYNTAX      TmnxSSMQualityLevel
    MAX-ACCESS  read-only
    STATUS      current
    DESCRIPTION
        "The value of tmnxSyncIfTimingPTPCfgQltyLevel indicates the configured
         Quality Level of Precision Timing Protocol (PTP).  A value of
         'unknown (0)' indicates PTP is not forced to a specific quality level."
    ::= { tmnxSyncIfTimingEntry 59 }

tmnxSyncIfTimingPTPRxQltyLevel   OBJECT-TYPE
    SYNTAX      TmnxSSMQualityLevel
    MAX-ACCESS  read-only
    STATUS      current
    DESCRIPTION
        "The value of tmnxSyncIfTimingPTPRxQltyLevel indicates the received SSM
         RX Quality Level of the Precision Timing Protocol (PTP)."
    ::= { tmnxSyncIfTimingEntry 60 }

tmnxSyncIfTimingPTPState         OBJECT-TYPE
    SYNTAX      TmnxRefInState
    MAX-ACCESS  read-only
    STATUS      current
    DESCRIPTION
        "The value of tmnxSyncIfTimingPTPState indicates the operational state
         of the Precision Timing Protocol (PTP) Timing."
    ::= { tmnxSyncIfTimingEntry 61 }

tmnxSyncIfTimingBITSOutSource    OBJECT-TYPE
    SYNTAX      TmnxBITSOutSource
    MAX-ACCESS  read-only
    STATUS      current
    DESCRIPTION
        "The value of tmnxSyncIfTimingBITSOutSource indicates the source of the
         BITS (Building Integrated Timing Supply) output."
    ::= { tmnxSyncIfTimingEntry 62 }

tmnxSyncIfTimingBITSOutQlMin     OBJECT-TYPE
    SYNTAX      TmnxSSMQualityLevel
    MAX-ACCESS  read-only
    STATUS      current
    DESCRIPTION
        "The value of tmnxSyncIfTimingBITSOutQlMin indicates the minimum
         quality level that a signal must have for it to be selected for BITS
         output.

         A value of 'unknown (0)' indicates that there is no minimum quality
         level selected for the BITS output."
    ::= { tmnxSyncIfTimingEntry 63 }

tmnxSyncIfTimingBITSOutSquelch   OBJECT-TYPE
    SYNTAX      TruthValue
    MAX-ACCESS  read-only
    STATUS      current
    DESCRIPTION
        "The value of tmnxSyncIfTimingBITSOutSquelch indicates whether or not
         to squelch the output signal. This object is only valid when there is
         no valid reference selected.

         If the value is 'true (1)' and there is no valid reference, then no
         signal is sent out the port.

         If the value is 'false (2)' and there is no valid reference, then the
         AIS signal is presented along with the QL-DNU/QL-DUS SSM if the signal
         format supports SSM."
    ::= { tmnxSyncIfTimingEntry 64 }

tmnxSyncIfTimingQlMin            OBJECT-TYPE
    SYNTAX      TmnxSSMQualityLevel
    MAX-ACCESS  read-only
    STATUS      current
    DESCRIPTION
        "The value of tmnxSyncIfTimingQlMin indicates the minimum acceptable
         quality level that a signal must have for it to be considered for
         selection by the system timing module.

         A value of 'unknown (0)' indicates that there is no minimum quality
         level."
    ::= { tmnxSyncIfTimingEntry 66 }

tmnxSyncIfTimingWaitToRestorTime OBJECT-TYPE
    SYNTAX      Unsigned32 (0..12)
    UNITS       "minutes"
    MAX-ACCESS  read-only
    STATUS      current
    DESCRIPTION
        "The value of tmnxSyncIfTimingWaitToRestorTime indicates the time, in
         minutes, that a previously failed input reference must be valid before
         it will be used for either the BITS output or the central clock input
         reference.

         A value of '0' indicates that the wait-to-restore timer is disabled."
    ::= { tmnxSyncIfTimingEntry 67 }

tmnxSyncIfTimingSyncEAdminStatus OBJECT-TYPE
    SYNTAX      TmnxPortAdminStatus
    MAX-ACCESS  read-only
    STATUS      current
    DESCRIPTION
        "The value of tmnxSyncIfTimingSyncEAdminStatus indicates the
         administrative status of the Synchronous Ethernet (SyncE) timing
         reference."
    ::= { tmnxSyncIfTimingEntry 68 }

tmnxSyncIfTimingSyncEInUse       OBJECT-TYPE
    SYNTAX      TruthValue
    MAX-ACCESS  read-only
    STATUS      current
    DESCRIPTION
        "The value of tmnxSyncIfTimingSyncEInUse indicates whether the Synchronous
         Ethernet (SyncE) timing reference is presently being used by the synchronous
         timing subsystem.  If it is in use, tmnxSyncIfTimingFreqOffset indicates
         the frequency offset for this reference."
    ::= { tmnxSyncIfTimingEntry 69 }

tmnxSyncIfTimingSyncEQualified   OBJECT-TYPE
    SYNTAX      TmnxSETSRefQualified
    MAX-ACCESS  read-only
    STATUS      current
    DESCRIPTION
        "The value of tmnxSyncIfTimingSyncEQualified indicates whether the Synchronous
         Ethernet (SyncE) timing reference is qualified for use by the synchronous timing
         subsystem.  If tmnxSyncIfTimingSyncEQualified is set to 'not-qualified',
         then the object tmnxSyncIfTimingSyncEAlarm gives the reason for
         disqualification."
    ::= { tmnxSyncIfTimingEntry 70 }

tmnxSyncIfTimingSyncEAlarm       OBJECT-TYPE
    SYNTAX      TmnxSETSRefAlarm
    MAX-ACCESS  read-only
    STATUS      current
    DESCRIPTION
        "The value of tmnxSyncIfTimingSyncEAlarm indicates the alarms on the
         Synchronous Ethernet (SyncE) reference.  If any of the bits is set to '1',
         then the SyncE reference is disqualified by the timing subsystem and the value of
         tmnxSyncIfTimingSyncEQualified is set to 'not-qualified'.
         los    - loss of signal
         oof    - out of frequency range
         oopir  - out of pull in range"
    ::= { tmnxSyncIfTimingEntry 71 }

tmnxSyncIfTimingSyncECfgQltyLevl OBJECT-TYPE
    SYNTAX      TmnxSSMQualityLevel
    MAX-ACCESS  read-only
    STATUS      current
    DESCRIPTION
        "The value of tmnxSyncIfTimingSyncECfgQltyLevl indicates the configured
         Quality Level of the Synchronous Ethernet (SyncE) timing reference. A
         value of 'unknown (0)' indicates SyncE is not forced to a specific
         quality level."
    ::= { tmnxSyncIfTimingEntry 72 }

tmnxSyncIfTimingSyncERxQltyLevel OBJECT-TYPE
    SYNTAX      TmnxSSMQualityLevel
    MAX-ACCESS  read-only
    STATUS      current
    DESCRIPTION
        "The value of tmnxSyncIfTimingSyncERxQltyLevel indicates the received
         SSM Quality Level of the Synchronous Ethernet (SyncE) timing
         reference."
    ::= { tmnxSyncIfTimingEntry 73 }

tmnxSyncIfTimingSyncEState       OBJECT-TYPE
    SYNTAX      TmnxRefInState
    MAX-ACCESS  read-only
    STATUS      current
    DESCRIPTION
        "The value of tmnxSyncIfTimingSyncEState indicates the operational
         state of the Synchronous Ethernet (SyncE) timing reference."
    ::= { tmnxSyncIfTimingEntry 74 }

tmnxSyncIfTimingSyncE2AdmnStatus OBJECT-TYPE
    SYNTAX      TmnxPortAdminStatus
    MAX-ACCESS  read-only
    STATUS      current
    DESCRIPTION
        "The value of tmnxSyncIfTimingSyncE2AdmnStatus indicates the
         administrative status of the Synchronous Ethernet 2 (SyncE) timing
         reference."
    ::= { tmnxSyncIfTimingEntry 75 }

tmnxSyncIfTimingSyncE2InUse      OBJECT-TYPE
    SYNTAX      TruthValue
    MAX-ACCESS  read-only
    STATUS      current
    DESCRIPTION
        "The value of tmnxSyncIfTimingSyncE2InUse indicates whether the Synchronous
         Ethernet 2 (SyncE) timing reference is presently being used by the synchronous
         timing subsystem.  If it is in use, tmnxSyncIfTimingFreqOffset indicates
         the frequency offset for this reference."
    ::= { tmnxSyncIfTimingEntry 76 }

tmnxSyncIfTimingSyncE2Qualified  OBJECT-TYPE
    SYNTAX      TmnxSETSRefQualified
    MAX-ACCESS  read-only
    STATUS      current
    DESCRIPTION
        "The value of tmnxSyncIfTimingSyncE2Qualified indicates whether the Synchronous
         Ethernet 2 (SyncE) timing reference is qualified for use by the synchronous timing
         subsystem.  If tmnxSyncIfTimingSyncE2Qualified is set to 'not-qualified',
         then the object tmnxSyncIfTimingSyncE2Alarm gives the reason for
         disqualification."
    ::= { tmnxSyncIfTimingEntry 77 }

tmnxSyncIfTimingSyncE2Alarm      OBJECT-TYPE
    SYNTAX      TmnxSETSRefAlarm
    MAX-ACCESS  read-only
    STATUS      current
    DESCRIPTION
        "The value of tmnxSyncIfTimingSyncE2Alarm indicates the alarms on the
         Synchronous Ethernet 2 (SyncE) reference.  If any of the bits is set to '1',
         then the SyncE 2 reference is disqualified by the timing subsystem and the value
         of tmnxSyncIfTimingSyncE2Qualified is set to 'not-qualified'.
         los    - loss of signal
         oof    - out of frequency range
         oopir  - out of pull in range"
    ::= { tmnxSyncIfTimingEntry 78 }

tmnxSyncIfTimingSyncE2RxQltyLevl OBJECT-TYPE
    SYNTAX      TmnxSSMQualityLevel
    MAX-ACCESS  read-only
    STATUS      current
    DESCRIPTION
        "The value of tmnxSyncIfTimingSyncE2RxQltyLevl indicates the received
         SSM Quality Level of the Synchronous Ethernet 2 (SyncE) timing
         reference."
    ::= { tmnxSyncIfTimingEntry 79 }

tmnxSyncIfTimingSyncE2State      OBJECT-TYPE
    SYNTAX      TmnxRefInState
    MAX-ACCESS  read-only
    STATUS      current
    DESCRIPTION
        "The value of tmnxSyncIfTimingSyncE2State indicates the operational
         state of the Synchronous Ethernet 2 (SyncE) timing reference."
    ::= { tmnxSyncIfTimingEntry 80 }

tmnxSyncIfTimingRefOrder5        OBJECT-TYPE
    SYNTAX      TmnxSETSRefSource
    MAX-ACCESS  read-only
    STATUS      current
    DESCRIPTION
        "The value of tmnxSyncIfTimingRefOrder5 is the fifth most preferred
         timing reference for the synchronous equipment timing subsystem."
    ::= { tmnxSyncIfTimingEntry 81 }

tmnxSyncIfTimingGnssAdminStatus  OBJECT-TYPE
    SYNTAX      TmnxPortAdminStatus
    MAX-ACCESS  read-only
    STATUS      current
    DESCRIPTION
        "The value of tmnxSyncIfTimingGnssAdminStatus indicates the
         administrative status of the Global Navigation Satellite System (GNSS)
         timing reference."
    ::= { tmnxSyncIfTimingEntry 82 }

tmnxSyncIfTimingGnssInUse        OBJECT-TYPE
    SYNTAX      TruthValue
    MAX-ACCESS  read-only
    STATUS      current
    DESCRIPTION
        "The value of tmnxSyncIfTimingGnssInUse indicates whether the GNSS
         timing reference is presently being used by the synchronous timing
         subsystem. If it is in use, tmnxSyncIfTimingFreqOffset indicates the
         frequency offset for this reference."
    ::= { tmnxSyncIfTimingEntry 83 }

tmnxSyncIfTimingGnssQualified    OBJECT-TYPE
    SYNTAX      TmnxSETSRefQualified
    MAX-ACCESS  read-only
    STATUS      current
    DESCRIPTION
        "The value of tmnxSyncIfTimingGnssQualified indicates whether the GNSS
         timing reference is qualified for use by the synchronous timing
         subsystem. If tmnxSyncIfTimingGnssQualified is set to 'not-qualified',
         then the object tmnxSyncIfTimingGnssAlarm gives the reason for
         disqualification."
    ::= { tmnxSyncIfTimingEntry 84 }

tmnxSyncIfTimingGnssAlarm        OBJECT-TYPE
    SYNTAX      TmnxSETSRefAlarm
    MAX-ACCESS  read-only
    STATUS      current
    DESCRIPTION
        "The value of tmnxSyncIfTimingGnssAlarm indicates the alarms on the GNSS timing
         reference.  If any of the bits is set to '1', then the GNSS reference is
         disqualified by the timing subsystem and the value of
         tmnxSyncIfTimingGnssQualified is set to 'not-qualified'.
         los    - loss of signal
         oof    - out of frequency range
         oopir  - out of pull in range"
    ::= { tmnxSyncIfTimingEntry 85 }

tmnxSyncIfTimingGnssCfgQltyLevel OBJECT-TYPE
    SYNTAX      TmnxSSMQualityLevel
    MAX-ACCESS  read-only
    STATUS      current
    DESCRIPTION
        "The value of tmnxSyncIfTimingGnssCfgQltyLevel indicates the configured
         Quality Level of the GNSS timing reference. A value of 'unknown (0)'
         indicates Gnss is not forced to a specific quality level."
    ::= { tmnxSyncIfTimingEntry 86 }

tmnxSyncIfTimingGnssRxQltyLevel  OBJECT-TYPE
    SYNTAX      TmnxSSMQualityLevel
    MAX-ACCESS  read-only
    STATUS      current
    DESCRIPTION
        "The value of tmnxSyncIfTimingGnssRxQltyLevel indicates the received
         SSM Quality Level of the GNSS timing reference."
    ::= { tmnxSyncIfTimingEntry 87 }

tmnxSyncIfTimingGnssState        OBJECT-TYPE
    SYNTAX      TmnxRefInState
    MAX-ACCESS  read-only
    STATUS      current
    DESCRIPTION
        "The value of tmnxSyncIfTimingGnssState indicates the operational state
         of the GNSS timing reference."
    ::= { tmnxSyncIfTimingEntry 88 }

tmnxSyncIfTimingGnss2AdminStatus OBJECT-TYPE
    SYNTAX      TmnxPortAdminStatus
    MAX-ACCESS  read-only
    STATUS      current
    DESCRIPTION
        "The value of tmnxSyncIfTimingGnss2AdminStatus indicates the
         administrative status of the GNSS 2 timing reference."
    ::= { tmnxSyncIfTimingEntry 89 }

tmnxSyncIfTimingGnss2InUse       OBJECT-TYPE
    SYNTAX      TruthValue
    MAX-ACCESS  read-only
    STATUS      current
    DESCRIPTION
        "The value of tmnxSyncIfTimingGnss2InUse indicates whether the GNSS 2
         timing reference is presently being used by the synchronous timing
         subsystem. If it is in use, tmnxSyncIfTimingFreqOffset indicates the
         frequency offset for this reference."
    ::= { tmnxSyncIfTimingEntry 90 }

tmnxSyncIfTimingGnss2Qualified   OBJECT-TYPE
    SYNTAX      TmnxSETSRefQualified
    MAX-ACCESS  read-only
    STATUS      current
    DESCRIPTION
        "The value of tmnxSyncIfTimingGnss2Qualified indicates whether the GNSS
         2 timing reference is qualified for use by the synchronous timing
         subsystem. If tmnxSyncIfTimingGnss2Qualified is set to
         'not-qualified', then the object tmnxSyncIfTimingGnss2Alarm gives the
         reason for disqualification."
    ::= { tmnxSyncIfTimingEntry 91 }

tmnxSyncIfTimingGnss2Alarm       OBJECT-TYPE
    SYNTAX      TmnxSETSRefAlarm
    MAX-ACCESS  read-only
    STATUS      current
    DESCRIPTION
        "The value of tmnxSyncIfTimingGnss2Alarm indicates the alarms on the GNSS 2
         timing reference.  If any of the bits is set to '1', then the GNSS 2 reference
         is disqualified by the timing subsystem and the value of
         tmnxSyncIfTimingGnss2Qualified is set to 'not-qualified'.
         los    - loss of signal
         oof    - out of frequency range
         oopir  - out of pull in range"
    ::= { tmnxSyncIfTimingEntry 92 }

tmnxSyncIfTimingGnss2RxQltyLevel OBJECT-TYPE
    SYNTAX      TmnxSSMQualityLevel
    MAX-ACCESS  read-only
    STATUS      current
    DESCRIPTION
        "The value of tmnxSyncIfTimingGnss2RxQltyLevel indicates the received
         SSM Quality Level of the GNSS 2 timing reference."
    ::= { tmnxSyncIfTimingEntry 93 }

tmnxSyncIfTimingGnss2State       OBJECT-TYPE
    SYNTAX      TmnxRefInState
    MAX-ACCESS  read-only
    STATUS      current
    DESCRIPTION
        "The value of tmnxSyncIfTimingGnss2State indicates the operational
         state of the GNSS 2 timing reference."
    ::= { tmnxSyncIfTimingEntry 94 }

tmnxSyncIfTimingRefOrder6        OBJECT-TYPE
    SYNTAX      TmnxSETSRefSource
    MAX-ACCESS  read-only
    STATUS      current
    DESCRIPTION
        "The value of tmnxSyncIfTimingRefOrder6 is the sixth most preferred
         timing reference for the synchronous equipment timing subsystem."
    ::= { tmnxSyncIfTimingEntry 95 }

tmnxSyncIfTimingFreqOffsetPpb    OBJECT-TYPE
    SYNTAX      Integer32
    UNITS       "parts-per-billion"
    MAX-ACCESS  read-only
    STATUS      current
    DESCRIPTION
        "The value of tmnxSyncIfTimingFreqOffsetPpb indicates the frequency
         offset of the current selected timing reference in parts per billion
         (ppb)."
    ::= { tmnxSyncIfTimingEntry 96 }

tmnxCcagTable                    OBJECT-TYPE
    SYNTAX      SEQUENCE OF TmnxCcagEntry
    MAX-ACCESS  not-accessible
    STATUS      obsolete
    DESCRIPTION
        "The tmnxCcagTable has an entry for each Cross Connect Aggregation
         Group,CCAG, configured on this system.

         This table was made obsolete in release 21.2."
    ::= { tmnxCardObjs 12 }

tmnxCcagEntry                    OBJECT-TYPE
    SYNTAX      TmnxCcagEntry
    MAX-ACCESS  not-accessible
    STATUS      obsolete
    DESCRIPTION
        "Each row entry represents a particular CCAG. Entries are
         created/deleted by the user. There is no StorageType object, entries
         have a presumed StorageType of nonVolatile.

         This entry was made obsolete in release 21.2."
    INDEX       { tmnxCcagId }
    ::= { tmnxCcagTable 1 }

TmnxCcagEntry                    ::= SEQUENCE
{
    tmnxCcagId                       TmnxCcagId,
    tmnxCcagRowStatus                RowStatus,
    tmnxCcagLastChanged              TimeStamp,
    tmnxCcagDescription              DisplayString,
    tmnxCcagAdminStatus              TmnxAdminState,
    tmnxCcagOperStatus               TmnxOperState,
    tmnxCcagCcaRate                  TmnxCcagRate,
    tmnxCcagAccessAdaptQos           INTEGER
}

tmnxCcagId                       OBJECT-TYPE
    SYNTAX      TmnxCcagId
    MAX-ACCESS  not-accessible
    STATUS      obsolete
    DESCRIPTION
        "The value of tmnxCcagId is used to index into the tmnxCcagTable. It
         uniquely identifies a CCAG entry as configured on this system.

         This object was made obsolete in release 21.2."
    ::= { tmnxCcagEntry 1 }

tmnxCcagRowStatus                OBJECT-TYPE
    SYNTAX      RowStatus
    MAX-ACCESS  read-create
    STATUS      obsolete
    DESCRIPTION
        "The value of tmnxCcagRowStatus specifies the row status. It allows
         entries to be created and deleted in the tmnxCcagTable.
         tmnxCcagRowStatus does not support createAndWait. The status can only
         be active or notInService.

         This object was made obsolete in release 21.2."
    ::= { tmnxCcagEntry 2 }

tmnxCcagLastChanged              OBJECT-TYPE
    SYNTAX      TimeStamp
    MAX-ACCESS  read-only
    STATUS      obsolete
    DESCRIPTION
        "The value of tmnxCcagLastChanged indicates the time this row was last
         changed.

         This object was made obsolete in release 21.2."
    ::= { tmnxCcagEntry 3 }

tmnxCcagDescription              OBJECT-TYPE
    SYNTAX      DisplayString
    MAX-ACCESS  read-create
    STATUS      obsolete
    DESCRIPTION
        "The value of tmnxCcagDescription specifies a user provided description
         string of this CCAG entry.

         This object was made obsolete in release 21.2."
    DEFVAL      { "" }
    ::= { tmnxCcagEntry 4 }

tmnxCcagAdminStatus              OBJECT-TYPE
    SYNTAX      TmnxAdminState
    MAX-ACCESS  read-create
    STATUS      obsolete
    DESCRIPTION
        "The value of tmnxCcagAdminStatus specifies the desired state of this
         CCAG.

         This object was made obsolete in release 21.2."
    DEFVAL      { inService }
    ::= { tmnxCcagEntry 5 }

tmnxCcagOperStatus               OBJECT-TYPE
    SYNTAX      TmnxOperState
    MAX-ACCESS  read-only
    STATUS      obsolete
    DESCRIPTION
        "The value of tmnxCcagOperStatus indicates the operational state of
         this CCAG.

         This object was made obsolete in release 21.2."
    ::= { tmnxCcagEntry 6 }

tmnxCcagCcaRate                  OBJECT-TYPE
    SYNTAX      TmnxCcagRate
    UNITS       "kilobps"
    MAX-ACCESS  read-create
    STATUS      obsolete
    DESCRIPTION
        "The value of tmnxCcagCcaRate specifies the maximum forwarding rate for
         each CCA member within the CCAG.

         This object was made obsolete in release 21.2."
    DEFVAL      { -1 }
    ::= { tmnxCcagEntry 7 }

tmnxCcagAccessAdaptQos           OBJECT-TYPE
    SYNTAX      INTEGER {
        link       (1),
        distribute (2),
        portFair   (3)
    }
    MAX-ACCESS  read-create
    STATUS      obsolete
    DESCRIPTION
        "The value of tmnxCcagAccessAdaptQos specifies how the CCAG SAP queue
         and virtual scheduler buffering and rate parameters are adapted over
         multiple active CCAs.
         link           (1) - The CCAG will create the SAP queues and virtual
                              schedulers on each CCA with the actual parameters
                              specified in the tmnxCcagPathCcTable.
         distribute     (2) - Each CCA will receive a portion of the parameters
                              specified in the tmnxCcagPathCcTable.
         portFair       (3) - The LAG will create the SAP queues and virtual
                              schedulers with actual configuration parameters
                              on each port members in the LAG. The bandwidth is
                              distributed among the ports based on each port's
                              bandwidth relative to the total active bandwidth.

          This object was made obsolete in release 21.2."
    DEFVAL      { distribute }
    ::= { tmnxCcagEntry 8 }

tmnxCcagPathTable                OBJECT-TYPE
    SYNTAX      SEQUENCE OF TmnxCcagPathEntry
    MAX-ACCESS  not-accessible
    STATUS      obsolete
    DESCRIPTION
        "The tmnxCcagPathTable has an entry for each Cross Connect Aggregation
         Group, CCAG, path configured on this system.

         This table was made obsolete in release 21.2."
    ::= { tmnxCardObjs 13 }

tmnxCcagPathEntry                OBJECT-TYPE
    SYNTAX      TmnxCcagPathEntry
    MAX-ACCESS  not-accessible
    STATUS      obsolete
    DESCRIPTION
        "Each row entry represents a particular CCAG Path. Entries are
         created/deleted by the user. There is no StorageType object, entries
         have a presumed StorageType of nonVolatile.

         This entry was made obsolete in release 21.2."
    INDEX       {
        tmnxCcagId,
        tmnxCcagPathId
    }
    ::= { tmnxCcagPathTable 1 }

TmnxCcagPathEntry                ::= SEQUENCE
{
    tmnxCcagPathId                   INTEGER,
    tmnxCcagPathLastChanged          TimeStamp,
    tmnxCcagPathRate                 TmnxCcagRate,
    tmnxCcagPathRateOption           TmnxCcagRateOption,
    tmnxCcagPathWeight               Unsigned32
}

tmnxCcagPathId                   OBJECT-TYPE
    SYNTAX      INTEGER {
        alpha (1),
        beta  (2)
    }
    MAX-ACCESS  not-accessible
    STATUS      obsolete
    DESCRIPTION
        "The value of tmnxCcagPathId is used as the secondary index into the
         tmnxCcagPathTable. Along with tmnxCcagId, it uniquely identifies a
         specific path, alpha or beta, on a CCAG.

         This object was made obsolete in release 21.2."
    ::= { tmnxCcagPathEntry 1 }

tmnxCcagPathLastChanged          OBJECT-TYPE
    SYNTAX      TimeStamp
    MAX-ACCESS  read-only
    STATUS      obsolete
    DESCRIPTION
        "The value of tmnxCcagPathLastChanged indicates the time this row was
         last changed.

         This object was made obsolete in release 21.2."
    ::= { tmnxCcagPathEntry 2 }

tmnxCcagPathRate                 OBJECT-TYPE
    SYNTAX      TmnxCcagRate
    UNITS       "kilobps"
    MAX-ACCESS  read-create
    STATUS      obsolete
    DESCRIPTION
        "The value of tmnxCcagPathRate specifies the bandwidth rate limitation
         for this path on each member cross connect adaptor, CCA, in the CCAG.

         This object was made obsolete in release 21.2."
    DEFVAL      { -1 }
    ::= { tmnxCcagPathEntry 3 }

tmnxCcagPathRateOption           OBJECT-TYPE
    SYNTAX      TmnxCcagRateOption
    MAX-ACCESS  read-create
    STATUS      obsolete
    DESCRIPTION
        "The value of tmnxCcagPathRateOption specifies whether the rate in
         tmnxCcagPathRate is defined as an aggregate path rate for all CCAs in
         the CCAG or as a per CCA path rate.

         This object was made obsolete in release 21.2."
    DEFVAL      { aggregate }
    ::= { tmnxCcagPathEntry 4 }

tmnxCcagPathWeight               OBJECT-TYPE
    SYNTAX      Unsigned32 (1..100)
    MAX-ACCESS  read-create
    STATUS      obsolete
    DESCRIPTION
        "The value of tmnxCcagPathWeight specifies the scheduling percentage
         for this path. It is applied to all CCAs in the CCAG membership list
         for this path.

         This object was made obsolete in release 21.2."
    DEFVAL      { 50 }
    ::= { tmnxCcagPathEntry 5 }

tmnxCcagPathCcTable              OBJECT-TYPE
    SYNTAX      SEQUENCE OF TmnxCcagPathCcEntry
    MAX-ACCESS  not-accessible
    STATUS      obsolete
    DESCRIPTION
        "The tmnxCcagPathCcTable has an entry for each type of Cross Connection
         on a Cross Connect Aggregation Group Path configured on this system.

         This table was made obsolete in release 21.2."
    ::= { tmnxCardObjs 14 }

tmnxCcagPathCcEntry              OBJECT-TYPE
    SYNTAX      TmnxCcagPathCcEntry
    MAX-ACCESS  not-accessible
    STATUS      obsolete
    DESCRIPTION
        "Each row entry represents a particular CCAG Path Cross Connect.
         Entries are created/deleted by the user. There is no StorageType
         object, entries have a presumed StorageType of nonVolatile.

         This entry was made obsolete in release 21.2."
    INDEX       {
        tmnxCcagId,
        tmnxCcagPathId,
        tmnxCcagPathCcType
    }
    ::= { tmnxCcagPathCcTable 1 }

TmnxCcagPathCcEntry              ::= SEQUENCE
{
    tmnxCcagPathCcType               INTEGER,
    tmnxCcagPathCcLastChanged        TimeStamp,
    tmnxCcagPathCcEgrPoolResvCbs     Integer32,
    tmnxCcagPathCcEgrPoolSlpPlcy     TNamedItem,
    tmnxCcagPathCcIngPoolResvCbs     Integer32,
    tmnxCcagPathCcIngPoolSlpPlcy     TNamedItem,
    tmnxCcagPathCcAcctPolicyId       Unsigned32,
    tmnxCcagPathCcCollectStats       TruthValue,
    tmnxCcagPathCcQueuePlcy          TNamedItem,
    tmnxCcagPathCcMac                MacAddress,
    tmnxCcagPathCcMtu                Unsigned32,
    tmnxCcagPathCcUserAssignedMac    TruthValue,
    tmnxCcagPathCcHwMac              MacAddress
}

tmnxCcagPathCcType               OBJECT-TYPE
    SYNTAX      INTEGER {
        sapsap (1),
        sapnet (2),
        netsap (3)
    }
    MAX-ACCESS  not-accessible
    STATUS      obsolete
    DESCRIPTION
        "The value of tmnxCcagPathCcType is used as a third index into
         the tmnxCcagPathCcTable. Along with tmnxCcagId and tmnxCcagPathId,
         it uniquely identifies a cross connection type on a specific path
         in a particular CCAG. The types are:
         sapsap (1): the cross connection is between two saps, where both
                     services are access.
         sapnet (2): the cross connection is between a sap and a network
                     service.
         netsap (3): the cross connection is between a network and a sap
                     service.

         This object was made obsolete in release 21.2."
    ::= { tmnxCcagPathCcEntry 1 }

tmnxCcagPathCcLastChanged        OBJECT-TYPE
    SYNTAX      TimeStamp
    MAX-ACCESS  read-only
    STATUS      obsolete
    DESCRIPTION
        "The value of tmnxCcagPathCcLastChanged indicates the time this row was
         last changed.

         This object was made obsolete in release 21.2."
    ::= { tmnxCcagPathCcEntry 2 }

tmnxCcagPathCcEgrPoolResvCbs     OBJECT-TYPE
    SYNTAX      Integer32 (-1..100)
    MAX-ACCESS  read-create
    STATUS      obsolete
    DESCRIPTION
        "The value of tmnxCcagPathCcEgrPoolResvCbs specifies the percentage of
         pool size reserved for the committed burst size, CBS. The value '-1'
         implies that the reserved CBS should be computed as the sum of the CBS
         requested by the entities using this pool if the application point is
         'network'. For 'access' application points the value '-1' means a
         default of 30%.

         This object was made obsolete in release 21.2."
    DEFVAL      { -1 }
    ::= { tmnxCcagPathCcEntry 3 }

tmnxCcagPathCcEgrPoolSlpPlcy     OBJECT-TYPE
    SYNTAX      TNamedItem
    MAX-ACCESS  read-create
    STATUS      obsolete
    DESCRIPTION
        "The value of tmnxCcagPathCcEgrPoolSlpPlcy specifies the slope policy
         being used for the egress pool. The Slope policies define the nature
         of the RED Slopes for the high and the low priority traffic.

         This object was made obsolete in release 21.2."
    DEFVAL      { "default" }
    ::= { tmnxCcagPathCcEntry 4 }

tmnxCcagPathCcIngPoolResvCbs     OBJECT-TYPE
    SYNTAX      Integer32 (-1..100)
    MAX-ACCESS  read-create
    STATUS      obsolete
    DESCRIPTION
        "The value of tmnxCcagPathCcIngPoolResvCbs specifies the percentage of
         pool size reserved for the committed burst size, CBS. The value '-1'
         implies that the reserved CBS should be computed as the sum of the CBS
         requested by the entities using this pool if the application point is
         'network'. For 'access' application points the value '-1' means a
         default of 30%. tmnxCcagPathCcIngPoolResvCbs does not apply to
         tmnxCcagPathCcType 'netsap'.

         This object was made obsolete in release 21.2."
    DEFVAL      { -1 }
    ::= { tmnxCcagPathCcEntry 5 }

tmnxCcagPathCcIngPoolSlpPlcy     OBJECT-TYPE
    SYNTAX      TNamedItem
    MAX-ACCESS  read-create
    STATUS      obsolete
    DESCRIPTION
        "The value of tmnxCcagPathCcIngPoolSlpPlcy specifies the slope policy
         being used for the ingress pool. The Slope policies define the nature
         of the RED Slopes for the high and the low priority traffic.
         tmnxCcagPathCcIngPoolSlpPlcy does not apply to tmnxCcagPathCcType
         'netsap'.

         This object was made obsolete in release 21.2."
    DEFVAL      { "default" }
    ::= { tmnxCcagPathCcEntry 6 }

tmnxCcagPathCcAcctPolicyId       OBJECT-TYPE
    SYNTAX      Unsigned32 (0..99)
    MAX-ACCESS  read-create
    STATUS      obsolete
    DESCRIPTION
        "The value of tmnxCcagPathCcAcctPolicyId specifies the accounting
         policy which must be defined prior to associating it with the port.
         A non-zero value indicates the tmnxLogApPolicyId index identifying the
         policy entry in the tmnxLogApTable from the TIMETRA-LOG-MIB which is
         associated with this port.  A zero value indicates that there is no
         accounting policy associated with this port. It is only meaningful
         when the tmnxCcagPathCcType is 'netsap'.

         This object was made obsolete in release 21.2."
    DEFVAL      { 0 }
    ::= { tmnxCcagPathCcEntry 7 }

tmnxCcagPathCcCollectStats       OBJECT-TYPE
    SYNTAX      TruthValue
    MAX-ACCESS  read-create
    STATUS      obsolete
    DESCRIPTION
        "The value of tmnxCcagPathCcCollectStats specifies whether the
         collection of accounting and statistical data for the network port is
         enabled/disabled, 'true'/'false'. When applying accounting policies
         the data by default will be collected in the appropriate records and
         written to the designated billing file. When the value is set to
         false, the statistics are still accumulated by the IOM cards, however,
         the CPU will not obtain the results and write them to the billing
         file. If the value of tmnxCcagPathCcType is not 'netsap', the value of
         this object is meaningless and an attempt to set it will result in an
         inconsistentValue error.

         This object was made obsolete in release 21.2."
    DEFVAL      { false }
    ::= { tmnxCcagPathCcEntry 8 }

tmnxCcagPathCcQueuePlcy          OBJECT-TYPE
    SYNTAX      TNamedItem
    MAX-ACCESS  read-create
    STATUS      obsolete
    DESCRIPTION
        "The value of tmnxCcagPathCcQueuePlcy specifies the network egress
         queue policy. If the value of tmnxCcagPathCcType is not 'netsap', the
         value of this object is meaningless and an attempt to set it will
         result in an inconsistentValue error.

         This object was made obsolete in release 21.2."
    DEFVAL      { "default" }
    ::= { tmnxCcagPathCcEntry 9 }

tmnxCcagPathCcMac                OBJECT-TYPE
    SYNTAX      MacAddress
    MAX-ACCESS  read-create
    STATUS      obsolete
    DESCRIPTION
        "The value of tmnxCcagPathCcMac specifies the MAC address of the
         virtual LAG that maps to tmnxCcagPathId and tmnxCcagPathCcType. The
         default value of this object is derived from the chassis MAC address
         pool.

         This object was made obsolete in release 21.2."
    DEFVAL      { '000000000000'H }
    ::= { tmnxCcagPathCcEntry 10 }

tmnxCcagPathCcMtu                OBJECT-TYPE
    SYNTAX      Unsigned32
    MAX-ACCESS  read-create
    STATUS      obsolete
    DESCRIPTION
        "The value of tmnxCcagPathCcMtu specifies the MTU of the path indexed
         by tmnxCcagId, tmnxCcagPathId, and tmnxCcagPathCcType. When the value
         is '0', the real MTU is calculated internally.

         This object was made obsolete in release 21.2."
    DEFVAL      { 0 }
    ::= { tmnxCcagPathCcEntry 11 }

tmnxCcagPathCcUserAssignedMac    OBJECT-TYPE
    SYNTAX      TruthValue
    MAX-ACCESS  read-only
    STATUS      obsolete
    DESCRIPTION
        "The value of tmnxCcagPathCcUserAssignedMac indicates whether the value
         of tmnxCcagPathCcMac has been explicitly assigned or inherited from
         tmnxCcagPathCcHwMac, 'true' and 'false', respectively.

         This object was made obsolete in release 21.2."
    DEFVAL      { false }
    ::= { tmnxCcagPathCcEntry 12 }

tmnxCcagPathCcHwMac              OBJECT-TYPE
    SYNTAX      MacAddress
    MAX-ACCESS  read-only
    STATUS      obsolete
    DESCRIPTION
        "The value of tmnxCcagPathCcHwMac is the system assigned MAC address of
         the virtual LAG that maps to tmnxCcagPathId and tmnxCcagPathCcType.
         When tmnxCcagPathCcUserAssignedMac is 'false', tmnxCcagPathCcMac
         inherits its value from this object.

         This object was made obsolete in release 21.2."
    ::= { tmnxCcagPathCcEntry 13 }

tmnxMcmTable                     OBJECT-TYPE
    SYNTAX      SEQUENCE OF TmnxMcmEntry
    MAX-ACCESS  not-accessible
    STATUS      obsolete
    DESCRIPTION
        "The tmnxMcmTable has an entry for each Mda Carrier module (MCM) on the
         7710 system.

         This table was obsoleted in release 20.2."
    ::= { tmnxCardObjs 15 }

tmnxMcmEntry                     OBJECT-TYPE
    SYNTAX      TmnxMcmEntry
    MAX-ACCESS  not-accessible
    STATUS      current
    DESCRIPTION
        "Each row entry represents a MCM in a chassis in the 7710 system.
         Entries in the table cannot be created and deleted via SNMP SET
         operations.  When a tmnxChassisEntry is created, a
         tmnxMcmEntry is created in the chassis.  Before a
         tmnxChassisEntry can be deleted, each tmnxMcmEntry
         for the chassis must be in the proper state for removal."
    INDEX       {
        tmnxChassisIndex,
        tmnxCardSlotNum,
        tmnxMcmSlotNum
    }
    ::= { tmnxMcmTable 1 }

TmnxMcmEntry                     ::= SEQUENCE
{
    tmnxMcmSlotNum                   Unsigned32,
    tmnxMcmSupportedTypes            TmnxMcmType,
    tmnxMcmAssignedType              TmnxMcmType,
    tmnxMcmEquippedType              TmnxMcmType,
    tmnxMcmHwIndex                   TmnxHwIndex
}

tmnxMcmSlotNum                   OBJECT-TYPE
    SYNTAX      Unsigned32 (0..16)
    MAX-ACCESS  not-accessible
    STATUS      obsolete
    DESCRIPTION
        "The unique value which identifies this MDA slot within a specific
         IOM card in the system.  Since the MCM occupies two MDA slots in
         the chassis this value can only be an odd number.

         This object was obsoleted in release 20.2."
    ::= { tmnxMcmEntry 1 }

tmnxMcmSupportedTypes            OBJECT-TYPE
    SYNTAX      TmnxMcmType
    MAX-ACCESS  read-only
    STATUS      obsolete
    DESCRIPTION
        "A bit-mask that indicates what MCM types can be physically supported
         in this chassis.

         This object was obsoleted in release 20.2."
    ::= { tmnxMcmEntry 2 }

tmnxMcmAssignedType              OBJECT-TYPE
    SYNTAX      TmnxMcmType
    MAX-ACCESS  read-write
    STATUS      obsolete
    DESCRIPTION
        "A bit-mask that identifies the administratively assigned
         (pre-provisioned) MCM type that should occupy this chassis.
         If tmnxMcmAssignedType has a value of 'unassigned',
         this slot has not yet been pre-provisioned.  There must not be more
         than one bit set at a time in tmnxMcmAssignedType.

         This object was obsoleted in release 20.2."
    DEFVAL      { 1 }
    ::= { tmnxMcmEntry 3 }

tmnxMcmEquippedType              OBJECT-TYPE
    SYNTAX      TmnxMcmType
    MAX-ACCESS  read-only
    STATUS      obsolete
    DESCRIPTION
        "A bit-mask that identifies the MCM type that is physically
         inserted into this chassis.  If the chassis has been pre-provisioned,
         tmnxMcmAssignedType is not equal 'unassigned', and the
         value of tmnxMcmEquippedType is not the same as
         tmnxMcmAssignedType, a mismatch alarm will be raised.
         If the chassis has not been pre-provisioned, and the value of
         tmnxMcmEquippedType is not one of the supported types as
         specified by tmnxMcmSupportedTypes, a mismatch alarm will
         be raised.  There will not be more than one bit set at a time in
         tmnxMcmEquippedType.

         This object was obsoleted in release 20.2."
    ::= { tmnxMcmEntry 4 }

tmnxMcmHwIndex                   OBJECT-TYPE
    SYNTAX      TmnxHwIndex
    MAX-ACCESS  read-only
    STATUS      obsolete
    DESCRIPTION
        "The value of tmnxMcmHwIndex is the index into the tmnxHwTable for the
         row entry that represents the hardware component information for this
         MCM.

         This object was obsoleted in release 20.2."
    ::= { tmnxMcmEntry 5 }

tmnxMcmTypeTable                 OBJECT-TYPE
    SYNTAX      SEQUENCE OF TmnxMcmTypeEntry
    MAX-ACCESS  not-accessible
    STATUS      obsolete
    DESCRIPTION
        "The card type table has an entry for each Nokia 7710 series Mda
         Carrier Module (MCM) model.

         This table was obsoleted in release 20.2."
    ::= { tmnxCardObjs 16 }

tmnxMcmTypeEntry                 OBJECT-TYPE
    SYNTAX      TmnxMcmTypeEntry
    MAX-ACCESS  not-accessible
    STATUS      current
    DESCRIPTION
        "Each row entry represents an Nokia 7710 series MCM model. Rows in this
         table are created by the agent at initialization and cannot be created
         or destroyed by SNMP Get or Set requests."
    INDEX       { tmnxMcmTypeIndex }
    ::= { tmnxMcmTypeTable 1 }

TmnxMcmTypeEntry                 ::= SEQUENCE
{
    tmnxMcmTypeIndex                 TmnxMcmType,
    tmnxMcmTypeName                  TNamedItemOrEmpty,
    tmnxMcmTypeDescription           TItemDescription,
    tmnxMcmTypeStatus                TruthValue
}

tmnxMcmTypeIndex                 OBJECT-TYPE
    SYNTAX      TmnxMcmType
    MAX-ACCESS  not-accessible
    STATUS      obsolete
    DESCRIPTION
        "The unique index value which identifies this type of Nokia 7710 series
         MCM model.

         This object was obsoleted in release 20.2."
    ::= { tmnxMcmTypeEntry 1 }

tmnxMcmTypeName                  OBJECT-TYPE
    SYNTAX      TNamedItemOrEmpty
    MAX-ACCESS  read-only
    STATUS      obsolete
    DESCRIPTION
        "The administrative name that identifies this type of Nokia
         7710 series MCM model.  This name string may be used in CLI
         commands to specify a particular card model type.

         This object was obsoleted in release 20.2."
    ::= { tmnxMcmTypeEntry 2 }

tmnxMcmTypeDescription           OBJECT-TYPE
    SYNTAX      TItemDescription
    MAX-ACCESS  read-only
    STATUS      obsolete
    DESCRIPTION
        "A detailed description of this Nokia 7710 series MCM model.

         This object was obsoleted in release 20.2."
    ::= { tmnxMcmTypeEntry 3 }

tmnxMcmTypeStatus                OBJECT-TYPE
    SYNTAX      TruthValue
    MAX-ACCESS  read-only
    STATUS      obsolete
    DESCRIPTION
        "When tmnxMcmTypeStatus has a value of 'true' it
         indicates that this MCM is supported in this revision of the
         management software.  When it has a value of 'false' there is no
         support.

         This object was obsoleted in release 20.2."
    ::= { tmnxMcmTypeEntry 4 }

tmnxIPsecIsaGrpTableLastChanged  OBJECT-TYPE
    SYNTAX      TimeStamp
    MAX-ACCESS  read-only
    STATUS      current
    DESCRIPTION
        "The value of tmnxIPsecIsaGrpTableLastChanged indicates the sysUpTime
         at the time of the last modification to tmnxIPsecIsaGrpTable by
         adding, deleting an entry or change to a writable object in the table.

         If no changes were made to the table since the last re-initialization
         of the local network management subsystem, then this object contains a
         zero value."
    ::= { tmnxCardObjs 17 }

tmnxIPsecIsaGrpTable             OBJECT-TYPE
    SYNTAX      SEQUENCE OF TmnxIPsecIsaGrpEntry
    MAX-ACCESS  not-accessible
    STATUS      current
    DESCRIPTION
        "Table to store entries for Groups of IPSec Integrated Service
         Adaptors. The table tmnxIPsecIsaGrpTable used to create and remove
         IPsec ISA groups. An IPsec ISA group is used to represent multiple
         hardware adaptors as a single entity. This allows for warm redundancy
         to be run between two IPsec ISAs."
    ::= { tmnxCardObjs 18 }

tmnxIPsecIsaGrpEntry             OBJECT-TYPE
    SYNTAX      TmnxIPsecIsaGrpEntry
    MAX-ACCESS  not-accessible
    STATUS      current
    DESCRIPTION
        "Information about a single IPsec group entry."
    INDEX       { tmnxIPsecIsaGrpId }
    ::= { tmnxIPsecIsaGrpTable 1 }

TmnxIPsecIsaGrpEntry             ::= SEQUENCE
{
    tmnxIPsecIsaGrpId                TmnxTunnelGroupId,
    tmnxIPsecIsaGrpRowStatus         RowStatus,
    tmnxIPsecIsaGrpLastChanged       TimeStamp,
    tmnxIPsecIsaGrpDescription       TItemDescription,
    tmnxIPsecIsaGrpAdminState        TmnxAdminState,
    tmnxIPsecIsaGrpOperState         TmnxOperState,
    tmnxIPsecIsaGrpIsaChassis        TmnxChassisIndex,
    tmnxIPsecIsaGrpPrimaryIsa        TmnxHwIndexOrZero,
    tmnxIPsecIsaGrpBackupIsa         TmnxHwIndexOrZero,
    tmnxIPsecIsaGrpActiveIsa         TmnxHwIndexOrZero,
    tmnxIPsecIsaGrpTunnels           Unsigned32,
    tmnxIPsecIsaGrpMaxTunnels        Unsigned32,
    tmnxIPsecIsaGrpTunnelReassembly  Integer32,
    tmnxIPsecIsaGrpOperFlags         TmnxIpSecIsaOperFlags,
    tmnxIPsecIsaGrpMultiActive       TruthValue,
    tmnxIPsecIsaGrpActiveMda         Unsigned32,
    tmnxIPsecIsaGrpIpTunnels         Unsigned32,
    tmnxIPsecIsaGrpIpMaxTunnels      Unsigned32,
    tmnxIPsecIsaGrpIPsecRespondOnly  TruthValue,
    tmnxIPsecIsaGrpIsaScaleMode      INTEGER,
    tmnxIPsecIsaGrpDpCpuUsageCollEn  TruthValue,
    tmnxIPsecIsaGrpTrafficFwdCollEn  TruthValue,
    tmnxIPsecIsaGrpMemberPool        TNamedItemOrEmpty,
    tmnxIPsecIsaGrpESPSeqNumOrder    TruthValue,
    tmnxIPsecIsaGrpESPSeqNumOrderOpr TruthValue,
    tmnxIPsecIsaGrpSpiRangeIndex     Unsigned32
}

tmnxIPsecIsaGrpId                OBJECT-TYPE
    SYNTAX      TmnxTunnelGroupId
    MAX-ACCESS  not-accessible
    STATUS      current
    DESCRIPTION
        "The value of tmnxIPsecIsaGrpId specifies the id of a
         TmnxIPsecIsaGrpEntry and is the primary index for the table."
    ::= { tmnxIPsecIsaGrpEntry 1 }

tmnxIPsecIsaGrpRowStatus         OBJECT-TYPE
    SYNTAX      RowStatus
    MAX-ACCESS  read-create
    STATUS      current
    DESCRIPTION
        "The tmnxIPsecIsaGrpRowStatus object is used to create and delete rows
         in the tmnxIPsecIsaGrpTable."
    ::= { tmnxIPsecIsaGrpEntry 2 }

tmnxIPsecIsaGrpLastChanged       OBJECT-TYPE
    SYNTAX      TimeStamp
    MAX-ACCESS  read-only
    STATUS      current
    DESCRIPTION
        "The value of tmnxIPsecIsaGrpLastChanged indicates the sysUpTime at the
         time of the last modification of this entry.

         If no changes were made to the entry since the last re-initialization
         of the local network management subsystem, then this object contains a
         zero value."
    ::= { tmnxIPsecIsaGrpEntry 3 }

tmnxIPsecIsaGrpDescription       OBJECT-TYPE
    SYNTAX      TItemDescription
    MAX-ACCESS  read-create
    STATUS      current
    DESCRIPTION
        "The value of tmnxIPsecIsaGrpDescription specifies the user-provided
         description for each tmnxIPsecIsaGrpEntry in the table
         tmnxIPsecIsaGrpTable."
    DEFVAL      { "" }
    ::= { tmnxIPsecIsaGrpEntry 4 }

tmnxIPsecIsaGrpAdminState        OBJECT-TYPE
    SYNTAX      TmnxAdminState
    MAX-ACCESS  read-create
    STATUS      current
    DESCRIPTION
        "The value of tmnxIPsecIsaGrpAdminState specifies the administrative
         state of the tmnxIPsecIsaGrpEntry."
    DEFVAL      { outOfService }
    ::= { tmnxIPsecIsaGrpEntry 5 }

tmnxIPsecIsaGrpOperState         OBJECT-TYPE
    SYNTAX      TmnxOperState
    MAX-ACCESS  read-only
    STATUS      current
    DESCRIPTION
        "The value of tmnxIPsecIsaGrpOperState indicates the operational status
         of tmnxIPsecIsaGrpEntry."
    ::= { tmnxIPsecIsaGrpEntry 6 }

tmnxIPsecIsaGrpIsaChassis        OBJECT-TYPE
    SYNTAX      TmnxChassisIndex
    MAX-ACCESS  read-create
    STATUS      current
    DESCRIPTION
        "The value of tmnxIPsecIsaGrpIsaChassis specifies the chassis on which
         the tmnxIPsecIsaGrpPrimaryIsa and tmnxIPsecIsaGrpBackupIsa are
         present."
    DEFVAL      { 1 }
    ::= { tmnxIPsecIsaGrpEntry 7 }

tmnxIPsecIsaGrpPrimaryIsa        OBJECT-TYPE
    SYNTAX      TmnxHwIndexOrZero
    MAX-ACCESS  read-create
    STATUS      current
    DESCRIPTION
        "The value of tmnxIPsecIsaGrpPrimaryIsa specifies the primary IPsec ISA
         to be used for this module group."
    DEFVAL      { 0 }
    ::= { tmnxIPsecIsaGrpEntry 8 }

tmnxIPsecIsaGrpBackupIsa         OBJECT-TYPE
    SYNTAX      TmnxHwIndexOrZero
    MAX-ACCESS  read-create
    STATUS      current
    DESCRIPTION
        "The value of tmnxIPsecIsaGrpBackupIsa specifies the backup IPsec ISA
         to be used for this module group."
    DEFVAL      { 0 }
    ::= { tmnxIPsecIsaGrpEntry 9 }

tmnxIPsecIsaGrpActiveIsa         OBJECT-TYPE
    SYNTAX      TmnxHwIndexOrZero
    MAX-ACCESS  read-only
    STATUS      current
    DESCRIPTION
        "The value of tmnxIPsecIsaGrpActiveIsa indicates the active ISA that is
         being used for this module group.

         This object has meaning only when tmnxIPsecIsaGrpPrimaryIsa or
         tmnxIPsecIsaGrpBackupIsa is configured to a non-default value. In all
         other cases, the value of this object is equal to zero."
    ::= { tmnxIPsecIsaGrpEntry 10 }

tmnxIPsecIsaGrpTunnels           OBJECT-TYPE
    SYNTAX      Unsigned32
    MAX-ACCESS  read-only
    STATUS      current
    DESCRIPTION
        "The value of tmnxIPsecIsaGrpTunnels indicates the number of IPSec
         tunnels being used for this module group."
    ::= { tmnxIPsecIsaGrpEntry 11 }

tmnxIPsecIsaGrpMaxTunnels        OBJECT-TYPE
    SYNTAX      Unsigned32
    MAX-ACCESS  read-only
    STATUS      current
    DESCRIPTION
        "The value of tmnxIPsecIsaGrpMaxTunnels indicates the maximum number of
         IPSec tunnels available for this module group."
    ::= { tmnxIPsecIsaGrpEntry 12 }

tmnxIPsecIsaGrpTunnelReassembly  OBJECT-TYPE
    SYNTAX      Integer32 (0..5000)
    UNITS       "milliseconds"
    MAX-ACCESS  read-create
    STATUS      current
    DESCRIPTION
        "The value of tmnxIPsecIsaGrpTunnelReassembly specifies the maximum
         number of milliseconds to wait to receive all fragments of a
         particular IPSec or GRE packet for reassembly.

         The tmnxGreTunnelReassembly value set to zero indicates that
         reassembly is disabled.

         An 'inconsistentValue' error is returned if the value is not a
         multiple of 100 milliseconds."
    DEFVAL      { 0 }
    ::= { tmnxIPsecIsaGrpEntry 13 }

tmnxIPsecIsaGrpOperFlags         OBJECT-TYPE
    SYNTAX      TmnxIpSecIsaOperFlags
    MAX-ACCESS  read-only
    STATUS      current
    DESCRIPTION
        "The value of tmnxIPsecIsaGrpOperFlags indicates the operational flags
         to determine the status of tmnxIPsecIsaGrpEntry."
    ::= { tmnxIPsecIsaGrpEntry 14 }

tmnxIPsecIsaGrpMultiActive       OBJECT-TYPE
    SYNTAX      TruthValue
    MAX-ACCESS  read-create
    STATUS      current
    DESCRIPTION
        "The value of tmnxIPsecIsaGrpMultiActive specifies whether this tunnel
         group will load-balance IPsec traffic on multiple MDAs."
    DEFVAL      { false }
    ::= { tmnxIPsecIsaGrpEntry 15 }

tmnxIPsecIsaGrpActiveMda         OBJECT-TYPE
    SYNTAX      Unsigned32 (1..16)
    MAX-ACCESS  read-create
    STATUS      current
    DESCRIPTION
        "The value of tmnxIPsecIsaGrpActiveMda specifies the number of active
         MDAs to be used by this tunnel-group to load-balance IPsec traffic."
    DEFVAL      { 1 }
    ::= { tmnxIPsecIsaGrpEntry 16 }

tmnxIPsecIsaGrpIpTunnels         OBJECT-TYPE
    SYNTAX      Unsigned32
    MAX-ACCESS  read-only
    STATUS      current
    DESCRIPTION
        "The value of tmnxIPsecIsaGrpIpTunnels indicates the number of IP
         tunnels being used for this module group."
    ::= { tmnxIPsecIsaGrpEntry 17 }

tmnxIPsecIsaGrpIpMaxTunnels      OBJECT-TYPE
    SYNTAX      Unsigned32
    MAX-ACCESS  read-only
    STATUS      current
    DESCRIPTION
        "The value of tmnxIPsecIsaGrpIpMaxTunnels indicates the maximum number
         of IP tunnels available for this module group."
    ::= { tmnxIPsecIsaGrpEntry 18 }

tmnxIPsecIsaGrpIPsecRespondOnly  OBJECT-TYPE
    SYNTAX      TruthValue
    MAX-ACCESS  read-create
    STATUS      current
    DESCRIPTION
        "The value of tmnxIPsecIsaGrpIPsecRespondOnly specifies whether the
         IPsec tunnel will respond to requests only and does not initiate
         exchanges with the peer."
    DEFVAL      { false }
    ::= { tmnxIPsecIsaGrpEntry 19 }

tmnxIPsecIsaGrpIsaScaleMode      OBJECT-TYPE
    SYNTAX      INTEGER {
        tunnelLimit2k  (1),
        tunnelLimit32k (2),
        tunnelLimit64k (3),
        tunnelLimit8   (4),
        tunnelLimit32  (5),
        tunnelLimit4k  (6)
    }
    MAX-ACCESS  read-create
    STATUS      current
    DESCRIPTION
        "The value of tmnxIPsecIsaGrpIsaScaleMode specifies the set of
         supported scaling modes for each ISA in this group.

         The scaling modes can be one of:
             tunnelLimit2k    (1) - maximum 2048 tunnels (e.g., IPsec, GRE and
                                    IP) per ISA
             tunnelLimit32k   (2) - maximum 32678 tunnels per ISA
             tunnelLimit64k   (3) - maximum 65536 tunnels per ISA
             tunnelLimit8     (4) - maximum 8 tunnels per ISA
             tunnelLimit32    (5) - maximum 32 tunnels per ISA
             tunnelLimit4k    (6) - maximum 4096 tunnels per ISA

         When creating a row, this object must be specified in the same SNMP
         PDU as tmnxIPsecIsaGrpRowStatus. The value of this object cannot be
         changed once the row is created.

         Platform    tmnxIPsecIsaGrpIsaScaleMode Default
         ---------    -----------------------------------
         VSR         'tunnelLimit2k(1)'
         SAR-Hm      'tunnelLimit8(4)'
         SAR-Hm      'tunnelLimit32(5)'
         SAR-Gen-2   'tunnelLimit4k(6)'
         Otherwise   'tunnelLimit32k(2)'"
    ::= { tmnxIPsecIsaGrpEntry 20 }

tmnxIPsecIsaGrpDpCpuUsageCollEn  OBJECT-TYPE
    SYNTAX      TruthValue
    MAX-ACCESS  read-create
    STATUS      current
    DESCRIPTION
        "The value of tmnxIPsecIsaGrpDpCpuUsageCollEn specifies whether or not
         the data-plane CPU usage historical statistics collection is enabled
         for this group."
    DEFVAL      { false }
    ::= { tmnxIPsecIsaGrpEntry 21 }

tmnxIPsecIsaGrpTrafficFwdCollEn  OBJECT-TYPE
    SYNTAX      TruthValue
    MAX-ACCESS  read-create
    STATUS      current
    DESCRIPTION
        "The value of tmnxIPsecIsaGrpTrafficFwdCollEn specifies whether or not
         the gateway traffic forwarding statistics collection is enabled for
         this group.

         This object is deprecated in release 16.0. Any configuration on this
         object will be ignored."
    DEFVAL      { true }
    ::= { tmnxIPsecIsaGrpEntry 22 }

tmnxIPsecIsaGrpMemberPool        OBJECT-TYPE
    SYNTAX      TNamedItemOrEmpty
    MAX-ACCESS  read-create
    STATUS      current
    DESCRIPTION
        "The value of tmnxIPsecIsaGrpMemberPool specifies the IPsec ISA Member
         Pool to which is associated with this tunnel-group.

         The member pool specified must exist in tmnxIPsecIsaMemberPoolTable.
         Removal of the member pool from tmnxIPsecIsaMemberPoolTable will not
         be allowed while this associations exists."
    DEFVAL      { "" }
    ::= { tmnxIPsecIsaGrpEntry 23 }

tmnxIPsecIsaGrpESPSeqNumOrder    OBJECT-TYPE
    SYNTAX      TruthValue
    MAX-ACCESS  read-create
    STATUS      current
    DESCRIPTION
        "The value of tmnxIPsecIsaGrpESPSeqNumOrder specifies whether or not
         strict ESP sequence number generation is enabled for this group.

         This configuration object is not present on VSR platforms."
    DEFVAL      { false }
    ::= { tmnxIPsecIsaGrpEntry 24 }

tmnxIPsecIsaGrpESPSeqNumOrderOpr OBJECT-TYPE
    SYNTAX      TruthValue
    MAX-ACCESS  read-only
    STATUS      current
    DESCRIPTION
        "The value of tmnxIPsecIsaGrpESPSeqNumOrderOpr indicates whether or not
         strict ESP sequence number generation is enabled for this group.

         This object is for indicating the state of this parameter on VSR
         platforms. Strict ESP sequence number generation is not configurable
         via management interfaces on VSR platforms.

         This object is only present on VSR platforms."
    ::= { tmnxIPsecIsaGrpEntry 25 }

tmnxIPsecIsaGrpSpiRangeIndex     OBJECT-TYPE
    SYNTAX      Unsigned32 (0..4)
    MAX-ACCESS  read-create
    STATUS      current
    DESCRIPTION
        "The value of tmnxIPsecIsaGrpSpiRangeIndex specifies the Security
         Parameter Index (SPI) range index for this group.

         When this object has value 0, no SPI range index is used for the
         group."
    DEFVAL      { 0 }
    ::= { tmnxIPsecIsaGrpEntry 26 }

tmnxFPTable                      OBJECT-TYPE
    SYNTAX      SEQUENCE OF TmnxFPEntry
    MAX-ACCESS  not-accessible
    STATUS      current
    DESCRIPTION
        "The tmnxFPTable has an entry for each Forwarding Plane configuration.
         An entry is created in this table whenever an entry for card is
         created in tmnxCardTable. This entry is relevant only for IOM3/IMM."
    ::= { tmnxCardObjs 21 }

tmnxFPEntry                      OBJECT-TYPE
    SYNTAX      TmnxFPEntry
    MAX-ACCESS  not-accessible
    STATUS      current
    DESCRIPTION
        "Each row entry represents a Forwarding Plane (FP) configuration."
    INDEX       {
        tmnxChassisIndex,
        tmnxCardSlotNum,
        tmnxFPNum
    }
    ::= { tmnxFPTable 1 }

TmnxFPEntry                      ::= SEQUENCE
{
    tmnxFPNum                        TmnxFPNumber,
    tmnxFPMcPathMgmtBwPlcyName       TNamedItem,
    tmnxFPMcPathMgmtAdminState       TmnxAdminState,
    tmnxFPLastChanged                TimeStamp,
    tmnxFPHiBwMcastSource            TruthValue,
    tmnxFPHiBwMcastAlarm             TruthValue,
    tmnxFPHiBwMcastTapCount          Gauge32,
    tmnxFPHiBwMcastGroup             Unsigned32,
    tmnxFPWredBufAllocMin            Unsigned32,
    tmnxFPWredBufAllocMax            Unsigned32,
    tmnxFPWredResvCbsMin             Unsigned32,
    tmnxFPWredResvCbsMax             Unsigned32,
    tmnxFPWredSlopePolicy            TNamedItemOrEmpty,
    tmnxFPWredAdminState             TmnxAdminState,
    tmnxFPHiBwMcastDefaultPathsOnly  TruthValue,
    tmnxFPDCpuProtDynEnfrcPlcrPool   Integer32,
    tmnxFPStablePoolSizing           TruthValue,
    tmnxFPIngressBufferAllocation    Unsigned32,
    tmnxFPPlcyAcctStatsPool          Unsigned32,
    tmnxFPPlcyAcctStatsInUse         Unsigned32,
    tmnxFPInitExtractDropPrioMode    INTEGER,
    tmnxFPEgrHsPoolPolicy            TNamedItemOrEmpty,
    tmnxFPEgrHsFixedHighThreshDelta  Integer32,
    tmnxFPMcPathMgmtPriInUseBw       Gauge32,
    tmnxFPMcPathMgmtSecInUseBw       Gauge32,
    tmnxFPMcPathMgmtBlkHoleInUseBw   Gauge32,
    tmnxFPGeneration                 TmnxFpGeneration,
    tmnxFPIngNetQueuePolicy          TNamedItem,
    tmnxFPQosFPResourcePolicy        TLNamedItemOrEmpty,
    tmnxFPPlcyAcctPolicerLimit       Unsigned32,
    tmnxFPPlcyAcctPolicerInUse       Unsigned32
}

tmnxFPNum                        OBJECT-TYPE
    SYNTAX      TmnxFPNumber
    MAX-ACCESS  not-accessible
    STATUS      current
    DESCRIPTION
        "The value of tmnxFPNum identifies the Forwarding Plane."
    ::= { tmnxFPEntry 1 }

tmnxFPMcPathMgmtBwPlcyName       OBJECT-TYPE
    SYNTAX      TNamedItem
    MAX-ACCESS  read-write
    STATUS      current
    DESCRIPTION
        "The value of tmnxFPMcPathMgmtBwPlcyName specifies the multicast policy
         name configured for the FP. tmnxFPMcPathMgmtBwPlcyName can be set only
         if the policy exists in
         TIMETRA-MCAST-PATH-MGMT-MIB::tmnxMcPathBwPlcyTable."
    DEFVAL      { "default" }
    ::= { tmnxFPEntry 2 }

tmnxFPMcPathMgmtAdminState       OBJECT-TYPE
    SYNTAX      TmnxAdminState
    MAX-ACCESS  read-write
    STATUS      current
    DESCRIPTION
        "The value of tmnxFPMcPathMgmtAdminState specifies administrative state
         of the multicast path for the FP."
    DEFVAL      { outOfService }
    ::= { tmnxFPEntry 3 }

tmnxFPLastChanged                OBJECT-TYPE
    SYNTAX      TimeStamp
    MAX-ACCESS  read-only
    STATUS      current
    DESCRIPTION
        "The value of tmnxFPLastChanged indicates the timestamp of last change
         to this row in tmnxFPTable."
    ::= { tmnxFPEntry 4 }

tmnxFPHiBwMcastSource            OBJECT-TYPE
    SYNTAX      TruthValue
    MAX-ACCESS  read-write
    STATUS      current
    DESCRIPTION
        "The value of tmnxFPHiBwMcastSource specifies if this FP should attempt
         to allocate separate fabric planes to allocate high bandwidth
         multicast traffic taps.

         tmnxFPHiBwMcastGroup must be set in the same SNMP request PDU with
         tmnxFPHiBwMcastSource or an 'inconsistentValue' error will be
         returned."
    DEFVAL      { false }
    ::= { tmnxFPEntry 5 }

tmnxFPHiBwMcastAlarm             OBJECT-TYPE
    SYNTAX      TruthValue
    MAX-ACCESS  read-write
    STATUS      current
    DESCRIPTION
        "The value of tmnxFPHiBwMcastAlarm specifies if a
         tmnxChassisHiBwMcastAlarm alarm is raised if there are more than one
         high bandwidth multicast traffic taps sharing a plane."
    DEFVAL      { false }
    ::= { tmnxFPEntry 6 }

tmnxFPHiBwMcastTapCount          OBJECT-TYPE
    SYNTAX      Gauge32
    MAX-ACCESS  read-only
    STATUS      current
    DESCRIPTION
        "The value of tmnxFPHiBwMcastTapCount indicates the number of high
         bandwidth multicast traffic taps on this FP."
    ::= { tmnxFPEntry 7 }

tmnxFPHiBwMcastGroup             OBJECT-TYPE
    SYNTAX      Unsigned32 (0..32)
    MAX-ACCESS  read-write
    STATUS      current
    DESCRIPTION
        "The value of tmnxFPHiBwMcastGroup specifies the group of high
         bandwidth multicast traffic taps to which this tap belongs.

         A value of '0' specifies that this tap is not a member of any High
         Bandwidth Multicast group.

         tmnxFPHiBwMcastGroup must be set in the same SNMP request PDU with
         tmnxFPHiBwMcastSource or an 'inconsistentValue' error will be
         returned."
    DEFVAL      { 0 }
    ::= { tmnxFPEntry 8 }

tmnxFPWredBufAllocMin            OBJECT-TYPE
    SYNTAX      Unsigned32 (0..9999)
    UNITS       "centipercent"
    MAX-ACCESS  read-write
    STATUS      current
    DESCRIPTION
        "The value of tmnxFPWredBufAllocMin specifies the minimum WRED
         (Weighted Random Early Detection) queue aggregate buffer allocation
         which will be set aside for WRED queue buffer pools."
    DEFVAL      { 2500 }
    ::= { tmnxFPEntry 9 }

tmnxFPWredBufAllocMax            OBJECT-TYPE
    SYNTAX      Unsigned32 (1..9999)
    UNITS       "centipercent"
    MAX-ACCESS  read-write
    STATUS      current
    DESCRIPTION
        "The value of tmnxFPWredBufAllocMax specifies the maximum WRED queue
         aggregate buffer allocation which will be set aside for WRED queue
         buffer pools."
    DEFVAL      { 2500 }
    ::= { tmnxFPEntry 10 }

tmnxFPWredResvCbsMin             OBJECT-TYPE
    SYNTAX      Unsigned32 (0..9999)
    UNITS       "centipercent"
    MAX-ACCESS  read-write
    STATUS      current
    DESCRIPTION
        "The value of tmnxFPWredResvCbsMin specifies the minimum buffers within
         the WRED pool that will be set aside for WRED queues operating within
         their configured CBS (Committed Buffer Size) thresholds."
    DEFVAL      { 2500 }
    ::= { tmnxFPEntry 11 }

tmnxFPWredResvCbsMax             OBJECT-TYPE
    SYNTAX      Unsigned32 (1..9999)
    UNITS       "centipercent"
    MAX-ACCESS  read-write
    STATUS      current
    DESCRIPTION
        "The value of tmnxFPWredResvCbsMax specifies the maximum buffers within
         the WRED pool that will be set aside for WRED queues operating within
         their configured CBS (Committed Buffer Size) thresholds."
    DEFVAL      { 2500 }
    ::= { tmnxFPEntry 12 }

tmnxFPWredSlopePolicy            OBJECT-TYPE
    SYNTAX      TNamedItemOrEmpty
    MAX-ACCESS  read-write
    STATUS      current
    DESCRIPTION
        "The value of tmnxFPWredSlopePolicy specifies the name of slope policy
         being used within WRED pool."
    DEFVAL      { "default" }
    ::= { tmnxFPEntry 13 }

tmnxFPWredAdminState             OBJECT-TYPE
    SYNTAX      TmnxAdminState
    MAX-ACCESS  read-write
    STATUS      current
    DESCRIPTION
        "The value of tmnxFPWredAdminState specifies administrative state of
         the egress WRED queue support on the card."
    DEFVAL      { outOfService }
    ::= { tmnxFPEntry 14 }

tmnxFPHiBwMcastDefaultPathsOnly  OBJECT-TYPE
    SYNTAX      TruthValue
    MAX-ACCESS  read-write
    STATUS      current
    DESCRIPTION
        "The value of tmnxFPHiBwMcastDefaultPathsOnly specifies whether only
         the default paths are to be High Bandwidth Multicast (HBM) (typically
         paths 0 and 15) and the remaining paths are non-HBM 'true (1)', or all
         paths are configured HBM on the forwarding path 'false (2)'.

         This object is only meaningful if tmnxFPHiBwMcastSource is set to the
         value 'true (1)'."
    DEFVAL      { false }
    ::= { tmnxFPEntry 15 }

tmnxFPDCpuProtDynEnfrcPlcrPool   OBJECT-TYPE
    SYNTAX      Integer32 (0 | 1000..32000)
    MAX-ACCESS  read-write
    STATUS      current
    DESCRIPTION
        "The value of tmnxFPDCpuProtDynEnfrcPlcrPool specifies number of
         policers that are set aside that can be instantiated as dynamic
         enforcement policers when Distributed CPU Protection is configured
         with dynamic enforcement."
    DEFVAL      { 0 }
    ::= { tmnxFPEntry 16 }

tmnxFPStablePoolSizing           OBJECT-TYPE
    SYNTAX      TruthValue
    MAX-ACCESS  read-write
    STATUS      current
    DESCRIPTION
        "The value of tmnxFPStablePoolSizing specifies whether the forwarding
         plane (FP) should split the buffers in a fixed way. When the value of
         tmnxFPStablePoolSizing is set to 'true', the forwarding plane will
         evenly split the buffers between all possible MDAs. Then, each MDA
         buffers will be split between all possible ports based on port max
         bandwidth adjusted by the port's modify-buffer-allocation-rate
         percentages.

         The value of tmnxFPStablePoolSizing cannot be set to 'true' when
         either tmnxCardNamedPoolAdminMode or tmnxCardNamedPoolOperMode is set
         to 'inService'. Likewise, the value of tmnxCardNamedPoolAdminMode or
         tmnxCardNamedPoolOperMode cannot be set to 'inService' when
         tmnxFPStablePoolSizing is set to 'true'."
    DEFVAL      { false }
    ::= { tmnxFPEntry 17 }

tmnxFPIngressBufferAllocation    OBJECT-TYPE
    SYNTAX      Unsigned32 (2000..8000)
    UNITS       "centipercent"
    MAX-ACCESS  read-write
    STATUS      current
    DESCRIPTION
        "The value of tmnxFPIngressBufferAllocation specifies the buffer
         allocation on a given forwarding plane (FP) which will be set aside
         for ingress pools."
    DEFVAL      { 5000 }
    ::= { tmnxFPEntry 18 }

tmnxFPPlcyAcctStatsPool          OBJECT-TYPE
    SYNTAX      Unsigned32 (0 | 1000..128000)
    MAX-ACCESS  read-write
    STATUS      current
    DESCRIPTION
        "The value of tmnxFPPlcyAcctStatsPool specifies the number of stats
         resources to reserve for policy-accounting on this forwarding plane
         (FP).

         The value of zero indicates no stats resources are allocated to policy
         accounting."
    DEFVAL      { 0 }
    ::= { tmnxFPEntry 19 }

tmnxFPPlcyAcctStatsInUse         OBJECT-TYPE
    SYNTAX      Unsigned32
    MAX-ACCESS  read-only
    STATUS      current
    DESCRIPTION
        "The value of tmnxFPPlcyAcctStatsInUse indicates the total number of
         statistics resources currently in use."
    ::= { tmnxFPEntry 20 }

tmnxFPInitExtractDropPrioMode    OBJECT-TYPE
    SYNTAX      INTEGER {
        uniform    (1),
        l3Classify (2)
    }
    MAX-ACCESS  read-write
    STATUS      current
    DESCRIPTION
        "The value of tmnxFPInitExtractDropPrioMode specifies the scheme used
         to select the initial drop priority of extracted control plane
         traffic. The initial drop priority of extracted packets can either be
         of low or high priority. The drop priority can be subsequently altered
         by mechanisms such as cpu-protection. High priority traffic receives
         preferential treatment in control plane congestion situations at the
         expense of low priority traffic.

         Values:
             uniform    (1) - initialize the drop priority of all extracted
                              control traffic as high priority
             l3Classify (2) - initialize the drop priority of all layer 3
                              extracted control traffic based on the QoS
                              classification of the packets
                            - this is useful in networks where the DSCP and EXP
                              markings can be trusted as the primary method to
                              distinguish, protect and isolate good terminating
                              protocol traffic from unknown or potentially
                              harmful protocol traffic"
    DEFVAL      { uniform }
    ::= { tmnxFPEntry 21 }

tmnxFPEgrHsPoolPolicy            OBJECT-TYPE
    SYNTAX      TNamedItemOrEmpty
    MAX-ACCESS  read-write
    STATUS      current
    DESCRIPTION
        "The value of tmnxFPEgrHsPoolPolicy specifies the egress QoS High Scale
         scheduler policy for this port. This object must correspond to the
         index of a row in TIMETRA-QOS-MIB::tHsPoolPolicyTable, otherwise an
         'inconsistentValue' error will be returned.

         When this forwarding plane is on non-High Scale card type, the value
         for tmnxFPEgrHsPoolPolicy will be ignored. If this forwarding plane is
         on High Scale card type, the default for this object will be the
         string 'default'."
    DEFVAL      { "" }
    ::= { tmnxFPEntry 22 }

tmnxFPEgrHsFixedHighThreshDelta  OBJECT-TYPE
    SYNTAX      Integer32 (-1 | 0..65536)
    MAX-ACCESS  read-write
    STATUS      current
    DESCRIPTION
        "The value of tmnxFPEgrHsFixedHighThreshDelta specifies the egress QoS
         High threshold delta for this port. This object must correspond."
    DEFVAL      { -1 }
    ::= { tmnxFPEntry 23 }

tmnxFPMcPathMgmtPriInUseBw       OBJECT-TYPE
    SYNTAX      Gauge32
    UNITS       "kilobps"
    MAX-ACCESS  read-only
    STATUS      current
    DESCRIPTION
        "The value of tmnxFPMcPathMgmtPriInUseBw indicates the in use ingress
         multicast bandwidth for the primary forwarding path."
    ::= { tmnxFPEntry 24 }

tmnxFPMcPathMgmtSecInUseBw       OBJECT-TYPE
    SYNTAX      Gauge32
    UNITS       "kilobps"
    MAX-ACCESS  read-only
    STATUS      current
    DESCRIPTION
        "The value of tmnxFPMcPathMgmtSecInUseBw indicates the in use ingress
         multicast bandwidth for the secondary forwarding path."
    ::= { tmnxFPEntry 25 }

tmnxFPMcPathMgmtBlkHoleInUseBw   OBJECT-TYPE
    SYNTAX      Gauge32
    UNITS       "kilobps"
    MAX-ACCESS  read-only
    STATUS      current
    DESCRIPTION
        "The value of tmnxFPMcPathMgmtBlkHoleInUseBw indicates the bandwidth of
         the ingress multicast traffic that is being black holed on the FP."
    ::= { tmnxFPEntry 26 }

tmnxFPGeneration                 OBJECT-TYPE
    SYNTAX      TmnxFpGeneration
    MAX-ACCESS  read-only
    STATUS      current
    DESCRIPTION
        "The value of tmnxFPGeneration indicates the generation of the FP
         network processor."
    ::= { tmnxFPEntry 27 }

tmnxFPIngNetQueuePolicy          OBJECT-TYPE
    SYNTAX      TNamedItem
    MAX-ACCESS  read-write
    STATUS      current
    DESCRIPTION
        "The value of tmnxFPIngNetQueuePolicy indicates the network queue
         policy being used to define the queueing structure for this object."
    DEFVAL      { "default" }
    ::= { tmnxFPEntry 28 }

tmnxFPQosFPResourcePolicy        OBJECT-TYPE
    SYNTAX      TLNamedItemOrEmpty
    MAX-ACCESS  read-write
    STATUS      current
    DESCRIPTION
        "The value of tmnxFPQosFPResourcePolicy indicates the FP resource
         policy policy being used to define the queueing structure for this
         object. For FP4 default value is 'default' and it is empty for other
         FPs."
    DEFVAL      { "" }
    ::= { tmnxFPEntry 29 }

tmnxFPPlcyAcctPolicerLimit       OBJECT-TYPE
    SYNTAX      Unsigned32 (0..64000)
    MAX-ACCESS  read-write
    STATUS      current
    DESCRIPTION
        "The value of tmnxFPPlcyAcctPolicerLimit specifies the number of
         policer resources to allocate for policy-accounting on this forwarding
         plane (FP).

         The value of zero indicates no resources are allocated to policy
         accounting."
    DEFVAL      { 0 }
    ::= { tmnxFPEntry 30 }

tmnxFPPlcyAcctPolicerInUse       OBJECT-TYPE
    SYNTAX      Unsigned32
    MAX-ACCESS  read-only
    STATUS      current
    DESCRIPTION
        "The value of tmnxFPPlcyAcctPolicerInUse indicates the total number of
         policer resources currently in use."
    ::= { tmnxFPEntry 31 }

tmnxFPAccIngQGrpTableLastChgd    OBJECT-TYPE
    SYNTAX      TimeStamp
    MAX-ACCESS  read-only
    STATUS      current
    DESCRIPTION
        "The value of tmnxFPAccIngQGrpTableLastChgd indicates the timestamp of
         last change to the tmnxFPAccIngQGrpTable."
    ::= { tmnxCardObjs 22 }

tmnxFPAccIngQGrpTable            OBJECT-TYPE
    SYNTAX      SEQUENCE OF TmnxFPAccIngQGrpEntry
    MAX-ACCESS  not-accessible
    STATUS      current
    DESCRIPTION
        "The value of tmnxFPAccIngQGrpTable defines access Ingress Queue Group
         Table for providing, via SNMP, the capability of defining the
         forwarding-plane specific queue groups from the queue-groups existing
         in the TIMETRA-QOS-MIB::tQosIngQGroupTable."
    ::= { tmnxCardObjs 23 }

tmnxFPAccIngQGrpEntry            OBJECT-TYPE
    SYNTAX      TmnxFPAccIngQGrpEntry
    MAX-ACCESS  not-accessible
    STATUS      current
    DESCRIPTION
        "The value of tmnxFPAccIngQGrpEntry defines an entry in the
         tmnxFPAccIngQGrpTable.

         Entries are created/deleted in this table by SNMP sets to
         tmnxFPAccIngQGrpRowStatus."
    INDEX       {
        tmnxChassisIndex,
        tmnxCardSlotNum,
        tmnxFPNum,
        tmnxFPAccIngQGrpName,
        tmnxFPAccIngQGrpInstanceId
    }
    ::= { tmnxFPAccIngQGrpTable 1 }

TmnxFPAccIngQGrpEntry            ::= SEQUENCE
{
    tmnxFPAccIngQGrpName             TNamedItem,
    tmnxFPAccIngQGrpInstanceId       Unsigned32,
    tmnxFPAccIngQGrpRowStatus        RowStatus,
    tmnxFPAccIngQGrpLastChgd         TimeStamp,
    tmnxFPAccIngQGrpAcctgPolId       Unsigned32,
    tmnxFPAccIngQGrpCollectStats     TruthValue,
    tmnxFPAccIngQGrpDescr            TItemDescription,
    tmnxFPAccIngQGrpPolicerPol       TNamedItemOrEmpty
}

tmnxFPAccIngQGrpName             OBJECT-TYPE
    SYNTAX      TNamedItem
    MAX-ACCESS  not-accessible
    STATUS      current
    DESCRIPTION
        "The value of tmnxFPAccIngQGrpName defines the forwarding-plane Ingress
         Queue Group name.  It, along with tmnxFPAccIngQGrpInstanceId uniquely
         identifies a forwarding-plane ingress queue group in the managed
         system."
    ::= { tmnxFPAccIngQGrpEntry 1 }

tmnxFPAccIngQGrpInstanceId       OBJECT-TYPE
    SYNTAX      Unsigned32 (1..65535)
    MAX-ACCESS  not-accessible
    STATUS      current
    DESCRIPTION
        "The value of tmnxFPAccIngQGrpInstanceId defines the unique instance of
         the forwarding-plane ingress Queue Group. It, along with
         tmnxFPAccIngQGrpName, uniquely identifies a forwarding-plane ingress
         queue group in the managed system."
    ::= { tmnxFPAccIngQGrpEntry 2 }

tmnxFPAccIngQGrpRowStatus        OBJECT-TYPE
    SYNTAX      RowStatus
    MAX-ACCESS  read-create
    STATUS      current
    DESCRIPTION
        "The value of tmnxFPAccIngQGrpRowStatus allows entries to be created
         and deleted in the tmnxFPAccIngQGrpTable.

         The creation of an entry in this table will succeed only if the
         queue-group being created exists in
         TIMETRA-QOS-MIB::tQosIngQGroupTable."
    REFERENCE
        "See definition of RowStatus in RFC 2579, 'Textual Conventions for
         SMIv2.'"
    ::= { tmnxFPAccIngQGrpEntry 3 }

tmnxFPAccIngQGrpLastChgd         OBJECT-TYPE
    SYNTAX      TimeStamp
    MAX-ACCESS  read-only
    STATUS      current
    DESCRIPTION
        "The value of tmnxFPAccIngQGrpLastChgd indicates the value of sysUpTime
         when the queue entry was last modified."
    ::= { tmnxFPAccIngQGrpEntry 4 }

tmnxFPAccIngQGrpAcctgPolId       OBJECT-TYPE
    SYNTAX      Unsigned32 (0..99)
    MAX-ACCESS  read-create
    STATUS      current
    DESCRIPTION
        "The value of tmnxFPAccIngQGrpAcctgPolId specifies the
         accounting-policy to be used with this forwarding-plane ingress
         queue-group.

         A non-zero value indicates the tmnxLogApPolicyId index identifying the
         policy entry in the tmnxLogApTable from the TIMETRA-LOG-MIB which is
         associated with this queue-group.

         The value zero indicates that the agent should use the default
         accounting policy, if one exists."
    DEFVAL      { 0 }
    ::= { tmnxFPAccIngQGrpEntry 5 }

tmnxFPAccIngQGrpCollectStats     OBJECT-TYPE
    SYNTAX      TruthValue
    MAX-ACCESS  read-create
    STATUS      current
    DESCRIPTION
        "The value of tmnxFPAccIngQGrpCollectStats specifies whether statistics
         should be collected on this forwarding-plane ingress queue-group."
    DEFVAL      { false }
    ::= { tmnxFPAccIngQGrpEntry 6 }

tmnxFPAccIngQGrpDescr            OBJECT-TYPE
    SYNTAX      TItemDescription
    MAX-ACCESS  read-create
    STATUS      current
    DESCRIPTION
        "The value of tmnxFPAccIngQGrpDescr specifies the description for this
         forwarding-plane queue-group."
    DEFVAL      { "" }
    ::= { tmnxFPAccIngQGrpEntry 7 }

tmnxFPAccIngQGrpPolicerPol       OBJECT-TYPE
    SYNTAX      TNamedItemOrEmpty
    MAX-ACCESS  read-create
    STATUS      current
    DESCRIPTION
        "The value of tmnxFPAccIngQGrpPolicerPol specifies the name of the
         policer control policy to be used with this forwarding-plane ingress
         queue-group."
    DEFVAL      { "" }
    ::= { tmnxFPAccIngQGrpEntry 8 }

tmnxFPNetIngQGrpTableLastChgd    OBJECT-TYPE
    SYNTAX      TimeStamp
    MAX-ACCESS  read-only
    STATUS      current
    DESCRIPTION
        "The value of tmnxFPNetIngQGrpTableLastChgd indicates the timestamp of
         last change to the tmnxFPNetIngQGrpTable."
    ::= { tmnxCardObjs 24 }

tmnxFPNetIngQGrpTable            OBJECT-TYPE
    SYNTAX      SEQUENCE OF TmnxFPNetIngQGrpEntry
    MAX-ACCESS  not-accessible
    STATUS      current
    DESCRIPTION
        "The value of tmnxFPNetIngQGrpTable defines access Ingress Queue Group
         Table for providing, via SNMP, the capability of defining the
         forwarding-plane specific queue groups from the queue-groups existing
         in the TIMETRA-QOS-MIB::tQosIngQGroupTable."
    ::= { tmnxCardObjs 25 }

tmnxFPNetIngQGrpEntry            OBJECT-TYPE
    SYNTAX      TmnxFPNetIngQGrpEntry
    MAX-ACCESS  not-accessible
    STATUS      current
    DESCRIPTION
        "The value of tmnxFPNetIngQGrpEntry defines an entry in the
         tmnxFPNetIngQGrpTable.

         Entries are created/deleted in this table by SNMP sets to
         tmnxFPNetIngQGrpRowStatus."
    INDEX       {
        tmnxChassisIndex,
        tmnxCardSlotNum,
        tmnxFPNum,
        tmnxFPNetIngQGrpName,
        tmnxFPNetIngQGrpInstanceId
    }
    ::= { tmnxFPNetIngQGrpTable 1 }

TmnxFPNetIngQGrpEntry            ::= SEQUENCE
{
    tmnxFPNetIngQGrpName             TNamedItem,
    tmnxFPNetIngQGrpInstanceId       Unsigned32,
    tmnxFPNetIngQGrpRowStatus        RowStatus,
    tmnxFPNetIngQGrpLastChgd         TimeStamp,
    tmnxFPNetIngQGrpAcctgPolId       Unsigned32,
    tmnxFPNetIngQGrpCollectStats     TruthValue,
    tmnxFPNetIngQGrpDescr            TItemDescription,
    tmnxFPNetIngQGrpPolicerPol       TNamedItemOrEmpty
}

tmnxFPNetIngQGrpName             OBJECT-TYPE
    SYNTAX      TNamedItem
    MAX-ACCESS  not-accessible
    STATUS      current
    DESCRIPTION
        "The value of tmnxFPNetIngQGrpName defines the forwarding-plane Ingress
         Queue Group name.  It, along with tmnxFPNetIngQGrpInstanceId uniquely
         identifies a forwarding-plane ingress queue group in the managed
         system."
    ::= { tmnxFPNetIngQGrpEntry 1 }

tmnxFPNetIngQGrpInstanceId       OBJECT-TYPE
    SYNTAX      Unsigned32 (1..65535)
    MAX-ACCESS  not-accessible
    STATUS      current
    DESCRIPTION
        "The value of tmnxFPNetIngQGrpInstanceId defines the unique instance of
         the forwarding-plane ingress Queue Group. It, along with
         tmnxFPNetIngQGrpName, uniquely identifies a forwarding-plane ingress
         queue group in the managed system."
    ::= { tmnxFPNetIngQGrpEntry 2 }

tmnxFPNetIngQGrpRowStatus        OBJECT-TYPE
    SYNTAX      RowStatus
    MAX-ACCESS  read-create
    STATUS      current
    DESCRIPTION
        "The value of tmnxFPNetIngQGrpRowStatus allows entries to be created
         and deleted in the tmnxFPNetIngQGrpTable.

         The creation of an entry in this table will succeed only if the
         queue-group being created exists in
         TIMETRA-QOS-MIB::tQosIngQGroupTable."
    REFERENCE
        "See definition of RowStatus in RFC 2579, 'Textual Conventions for
         SMIv2.'"
    ::= { tmnxFPNetIngQGrpEntry 3 }

tmnxFPNetIngQGrpLastChgd         OBJECT-TYPE
    SYNTAX      TimeStamp
    MAX-ACCESS  read-only
    STATUS      current
    DESCRIPTION
        "The value of tmnxFPNetIngQGrpLastChgd indicates the value of sysUpTime
         when the queue entry was last modified."
    ::= { tmnxFPNetIngQGrpEntry 4 }

tmnxFPNetIngQGrpAcctgPolId       OBJECT-TYPE
    SYNTAX      Unsigned32 (0..99)
    MAX-ACCESS  read-create
    STATUS      current
    DESCRIPTION
        "The value of tmnxFPNetIngQGrpAcctgPolId specifies the
         accounting-policy to be used with this forwarding-plane ingress
         queue-group.

         A non-zero value indicates the tmnxLogApPolicyId index identifying the
         policy entry in the tmnxLogApTable from the TIMETRA-LOG-MIB which is
         associated with this queue-group.

         The value zero indicates that the agent should use the default
         accounting policy, if one exists."
    DEFVAL      { 0 }
    ::= { tmnxFPNetIngQGrpEntry 5 }

tmnxFPNetIngQGrpCollectStats     OBJECT-TYPE
    SYNTAX      TruthValue
    MAX-ACCESS  read-create
    STATUS      current
    DESCRIPTION
        "The value of tmnxFPNetIngQGrpCollectStats specifies whether statistics
         should be collected on this forwarding-plane ingress queue-group."
    DEFVAL      { false }
    ::= { tmnxFPNetIngQGrpEntry 6 }

tmnxFPNetIngQGrpDescr            OBJECT-TYPE
    SYNTAX      TItemDescription
    MAX-ACCESS  read-create
    STATUS      current
    DESCRIPTION
        "The value of tmnxFPNetIngQGrpDescr specifies the description for this
         forwarding-plane queue-group."
    DEFVAL      { "" }
    ::= { tmnxFPNetIngQGrpEntry 7 }

tmnxFPNetIngQGrpPolicerPol       OBJECT-TYPE
    SYNTAX      TNamedItemOrEmpty
    MAX-ACCESS  read-create
    STATUS      current
    DESCRIPTION
        "The value of tmnxFPNetIngQGrpPolicerPol specifies the name of the
         policer control policy to be used with this forwarding-plane ingress
         queue-group."
    DEFVAL      { "" }
    ::= { tmnxFPNetIngQGrpEntry 8 }

tmnxFabricTypeTable              OBJECT-TYPE
    SYNTAX      SEQUENCE OF TmnxFabricTypeEntry
    MAX-ACCESS  not-accessible
    STATUS      current
    DESCRIPTION
        "The fabric type table has an entry for each Nokia SROS series Fabric
         card type."
    ::= { tmnxCardObjs 26 }

tmnxFabricTypeEntry              OBJECT-TYPE
    SYNTAX      TmnxFabricTypeEntry
    MAX-ACCESS  not-accessible
    STATUS      current
    DESCRIPTION
        "Each row entry represents an Nokia SROS series Fabric card. Rows in
         this table are created by the agent at initialization and cannot be
         created or destroyed by SNMP Get or Set requests."
    INDEX       { tmnxFabricTypeIndex }
    ::= { tmnxFabricTypeTable 1 }

TmnxFabricTypeEntry              ::= SEQUENCE
{
    tmnxFabricTypeIndex              TmnxFabricType,
    tmnxFabricTypeName               TNamedItemOrEmpty,
    tmnxFabricTypeDescription        TItemDescription,
    tmnxFabricTypeStatus             TruthValue
}

tmnxFabricTypeIndex              OBJECT-TYPE
    SYNTAX      TmnxFabricType
    MAX-ACCESS  not-accessible
    STATUS      current
    DESCRIPTION
        "The unique index value which identifies this type of Nokia SROS series
         Fabric card type."
    ::= { tmnxFabricTypeEntry 1 }

tmnxFabricTypeName               OBJECT-TYPE
    SYNTAX      TNamedItemOrEmpty
    MAX-ACCESS  read-only
    STATUS      current
    DESCRIPTION
        "The administrative name that identifies this type of Nokia
         SROS series Fabric card.  This name string may be used in CLI
         commands to specify a particular fabric card type."
    ::= { tmnxFabricTypeEntry 2 }

tmnxFabricTypeDescription        OBJECT-TYPE
    SYNTAX      TItemDescription
    MAX-ACCESS  read-only
    STATUS      current
    DESCRIPTION
        "A detailed description of this Nokia SROS series Fabric card."
    ::= { tmnxFabricTypeEntry 3 }

tmnxFabricTypeStatus             OBJECT-TYPE
    SYNTAX      TruthValue
    MAX-ACCESS  read-only
    STATUS      current
    DESCRIPTION
        "When tmnxFabricTypeStatus has a value of 'true' it
         indicates that this Fabric is supported in this revision of the
         management software.  When it has a value of 'false' there is no
         support."
    ::= { tmnxFabricTypeEntry 4 }

tmnxFPNetIngQGrpPStatTable       OBJECT-TYPE
    SYNTAX      SEQUENCE OF TmnxFPNetIngQGrpPStatEntry
    MAX-ACCESS  not-accessible
    STATUS      current
    DESCRIPTION
        "The tmnxFPNetIngQGrpPStatTable contains forwarding-plane ingress QoS
         queue group policer statistics on network side."
    ::= { tmnxCardObjs 27 }

tmnxFPNetIngQGrpPStatEntry       OBJECT-TYPE
    SYNTAX      TmnxFPNetIngQGrpPStatEntry
    MAX-ACCESS  not-accessible
    STATUS      current
    DESCRIPTION
        "The value of tmnxFPNetIngQGrpPStatEntry defines an entry in the
         tmnxFPNetIngQGrpPStatTable. It represents statistics about a specific
         QoS ingress queue group policer."
    INDEX       {
        tmnxChassisIndex,
        tmnxCardSlotNum,
        tmnxFPNum,
        tmnxFPNetIngQGrpName,
        tmnxFPNetIngQGrpInstanceId,
        tmnxFPNetIngQGrpPStatPolicerId
    }
    ::= { tmnxFPNetIngQGrpPStatTable 1 }

TmnxFPNetIngQGrpPStatEntry       ::= SEQUENCE
{
    tmnxFPNetIngQGrpPStatPolicerId   TIngPolicerId,
    tmnxFPNetIngQGrpPStatMode        TmnxIngPolicerStatMode,
    tmnxFPNetIngQgPStOffHPrioPkts    Counter64,
    tmnxFPNetIngQgPStOffHPrioPktsL   Counter32,
    tmnxFPNetIngQgPStOffHPrioPktsH   Counter32,
    tmnxFPNetIngQgPStDrpHPrioPkts    Counter64,
    tmnxFPNetIngQgPStDrpHPrioPktsL   Counter32,
    tmnxFPNetIngQgPStDrpHPrioPktsH   Counter32,
    tmnxFPNetIngQgPStOffLPrioPkts    Counter64,
    tmnxFPNetIngQgPStOffLPrioPktsL   Counter32,
    tmnxFPNetIngQgPStOffLPrioPktsH   Counter32,
    tmnxFPNetIngQgPStDrpLPrioPkts    Counter64,
    tmnxFPNetIngQgPStDrpLPrioPktsL   Counter32,
    tmnxFPNetIngQgPStDrpLPrioPktsH   Counter32,
    tmnxFPNetIngQgPStOffHPrioOcts    Counter64,
    tmnxFPNetIngQgPStOffHPrioOctsL   Counter32,
    tmnxFPNetIngQgPStOffHPrioOctsH   Counter32,
    tmnxFPNetIngQgPStDrpHPrioOcts    Counter64,
    tmnxFPNetIngQgPStDrpHPrioOctsL   Counter32,
    tmnxFPNetIngQgPStDrpHPrioOctsH   Counter32,
    tmnxFPNetIngQgPStOffLPrioOcts    Counter64,
    tmnxFPNetIngQgPStOffLPrioOctsL   Counter32,
    tmnxFPNetIngQgPStOffLPrioOctsH   Counter32,
    tmnxFPNetIngQgPStDrpLPrioOcts    Counter64,
    tmnxFPNetIngQgPStDrpLPrioOctsL   Counter32,
    tmnxFPNetIngQgPStDrpLPrioOctsH   Counter32,
    tmnxFPNetIngQgPStFwdInProfPkts   Counter64,
    tmnxFPNetIngQgPStFwdInProfPktsL  Counter32,
    tmnxFPNetIngQgPStFwdInProfPktsH  Counter32,
    tmnxFPNetIngQgPStFwdOutProfPkts  Counter64,
    tmnxFPNetIngQgPStFwdOutProfPktsL Counter32,
    tmnxFPNetIngQgPStFwdOutProfPktsH Counter32,
    tmnxFPNetIngQgPStFwdInProfOcts   Counter64,
    tmnxFPNetIngQgPStFwdInProfOctsL  Counter32,
    tmnxFPNetIngQgPStFwdInProfOctsH  Counter32,
    tmnxFPNetIngQgPStFwdOutProfOcts  Counter64,
    tmnxFPNetIngQgPStFwdOutProfOctsL Counter32,
    tmnxFPNetIngQgPStFwdOutProfOctsH Counter32,
    tmnxFPNetIngQgPStUncolPktsOff    Counter64,
    tmnxFPNetIngQgPStUncolPktsOffL   Counter32,
    tmnxFPNetIngQgPStUncolPktsOffH   Counter32,
    tmnxFPNetIngQgPStUncolOctsOff    Counter64,
    tmnxFPNetIngQgPStUncolOctsOffL   Counter32,
    tmnxFPNetIngQgPStUncolOctsOffH   Counter32
}

tmnxFPNetIngQGrpPStatPolicerId   OBJECT-TYPE
    SYNTAX      TIngPolicerId
    MAX-ACCESS  not-accessible
    STATUS      current
    DESCRIPTION
        "The value of tmnxFPNetIngQGrpPStatPolicerId specifies the index of the
         ingress QoS policer of this forwarding-plane queue group on network."
    ::= { tmnxFPNetIngQGrpPStatEntry 1 }

tmnxFPNetIngQGrpPStatMode        OBJECT-TYPE
    SYNTAX      TmnxIngPolicerStatMode
    MAX-ACCESS  read-only
    STATUS      current
    DESCRIPTION
        "The value of tmnxFPNetIngQGrpPStatMode indicates the stat mode used by
         this policer."
    ::= { tmnxFPNetIngQGrpPStatEntry 2 }

tmnxFPNetIngQgPStOffHPrioPkts    OBJECT-TYPE
    SYNTAX      Counter64
    MAX-ACCESS  read-only
    STATUS      current
    DESCRIPTION
        "The value of tmnxFPNetIngQgPStOffHPrioPkts indicates the number of
         high priority packets, as determined by the ingress queue group
         policer, offered by the Pchip to the Qchip."
    ::= { tmnxFPNetIngQGrpPStatEntry 3 }

tmnxFPNetIngQgPStOffHPrioPktsL   OBJECT-TYPE
    SYNTAX      Counter32
    MAX-ACCESS  read-only
    STATUS      current
    DESCRIPTION
        "The value of tmnxFPNetIngQgPStOffHPrioPktsL indicates the lower 32
         bits of tmnxFPNetIngQgPStOffHPrioPkts."
    ::= { tmnxFPNetIngQGrpPStatEntry 4 }

tmnxFPNetIngQgPStOffHPrioPktsH   OBJECT-TYPE
    SYNTAX      Counter32
    MAX-ACCESS  read-only
    STATUS      current
    DESCRIPTION
        "The value of tmnxFPNetIngQgPStOffHPrioPktsH indicates the upper 32
         bits of tmnxFPNetIngQgPStOffHPrioPkts."
    ::= { tmnxFPNetIngQGrpPStatEntry 5 }

tmnxFPNetIngQgPStDrpHPrioPkts    OBJECT-TYPE
    SYNTAX      Counter64
    MAX-ACCESS  read-only
    STATUS      current
    DESCRIPTION
        "The value of tmnxFPNetIngQgPStDrpHPrioPkts indicates the number of
         high priority packets, as determined by the ingress queue group
         policer, dropped by the Pchip due to: MBS exceeded, buffer pool limit
         exceeded, etc."
    ::= { tmnxFPNetIngQGrpPStatEntry 6 }

tmnxFPNetIngQgPStDrpHPrioPktsL   OBJECT-TYPE
    SYNTAX      Counter32
    MAX-ACCESS  read-only
    STATUS      current
    DESCRIPTION
        "The value of tmnxFPNetIngQgPStDrpHPrioPktsL indicates the lower 32
         bits of tmnxFPNetIngQgPStDrpHPrioPkts."
    ::= { tmnxFPNetIngQGrpPStatEntry 7 }

tmnxFPNetIngQgPStDrpHPrioPktsH   OBJECT-TYPE
    SYNTAX      Counter32
    MAX-ACCESS  read-only
    STATUS      current
    DESCRIPTION
        "The value of tmnxFPNetIngQgPStDrpHPrioPktsH indicates the upper 32
         bits of tmnxFPNetIngQgPStDrpHPrioPkts."
    ::= { tmnxFPNetIngQGrpPStatEntry 8 }

tmnxFPNetIngQgPStOffLPrioPkts    OBJECT-TYPE
    SYNTAX      Counter64
    MAX-ACCESS  read-only
    STATUS      current
    DESCRIPTION
        "The value of tmnxFPNetIngQgPStOffLPrioPkts indicates the number of low
         priority packets, as determined by the ingress queue group policer,
         offered by the Pchip to the Qchip."
    ::= { tmnxFPNetIngQGrpPStatEntry 9 }

tmnxFPNetIngQgPStOffLPrioPktsL   OBJECT-TYPE
    SYNTAX      Counter32
    MAX-ACCESS  read-only
    STATUS      current
    DESCRIPTION
        "The value of tmnxFPNetIngQgPStOffLPrioPktsL indicates the lower 32
         bits of tmnxFPNetIngQgPStOffLPrioPkts."
    ::= { tmnxFPNetIngQGrpPStatEntry 10 }

tmnxFPNetIngQgPStOffLPrioPktsH   OBJECT-TYPE
    SYNTAX      Counter32
    MAX-ACCESS  read-only
    STATUS      current
    DESCRIPTION
        "The value of tmnxFPNetIngQgPStOffLPrioPktsH indicates the upper 32
         bits of tmnxFPNetIngQgPStOffLPrioPkts."
    ::= { tmnxFPNetIngQGrpPStatEntry 11 }

tmnxFPNetIngQgPStDrpLPrioPkts    OBJECT-TYPE
    SYNTAX      Counter64
    MAX-ACCESS  read-only
    STATUS      current
    DESCRIPTION
        "The value of tmnxFPNetIngQgPStDrpLPrioPkts indicates the number of low
         priority packets, as determined by the ingress queue group policer,
         dropped by the Pchip due to: MBS exceeded, buffer pool limit exceeded,
         etc."
    ::= { tmnxFPNetIngQGrpPStatEntry 12 }

tmnxFPNetIngQgPStDrpLPrioPktsL   OBJECT-TYPE
    SYNTAX      Counter32
    MAX-ACCESS  read-only
    STATUS      current
    DESCRIPTION
        "The value of tmnxFPNetIngQgPStDrpLPrioPktsL indicates the lower 32
         bits of tmnxFPNetIngQgPStDrpLPrioPkts."
    ::= { tmnxFPNetIngQGrpPStatEntry 13 }

tmnxFPNetIngQgPStDrpLPrioPktsH   OBJECT-TYPE
    SYNTAX      Counter32
    MAX-ACCESS  read-only
    STATUS      current
    DESCRIPTION
        "The value of tmnxFPNetIngQgPStDrpLPrioPktsH indicates the upper 32
         bits of tmnxFPNetIngQgPStDrpLPrioPkts."
    ::= { tmnxFPNetIngQGrpPStatEntry 14 }

tmnxFPNetIngQgPStOffHPrioOcts    OBJECT-TYPE
    SYNTAX      Counter64
    MAX-ACCESS  read-only
    STATUS      current
    DESCRIPTION
        "The value of tmnxFPNetIngQgPStOffHPrioOcts indicates the number of
         high priority octets, as determined by the ingress queue group
         policer, offered by the Pchip to the Qchip."
    ::= { tmnxFPNetIngQGrpPStatEntry 15 }

tmnxFPNetIngQgPStOffHPrioOctsL   OBJECT-TYPE
    SYNTAX      Counter32
    MAX-ACCESS  read-only
    STATUS      current
    DESCRIPTION
        "The value of tmnxFPNetIngQgPStOffHPrioOctsL indicates the lower 32
         bits of tmnxFPNetIngQgPStOffHPrioOcts."
    ::= { tmnxFPNetIngQGrpPStatEntry 16 }

tmnxFPNetIngQgPStOffHPrioOctsH   OBJECT-TYPE
    SYNTAX      Counter32
    MAX-ACCESS  read-only
    STATUS      current
    DESCRIPTION
        "The value of tmnxFPNetIngQgPStOffHPrioOctsH indicates the upper 32
         bits of tmnxFPNetIngQgPStOffHPrioOcts."
    ::= { tmnxFPNetIngQGrpPStatEntry 17 }

tmnxFPNetIngQgPStDrpHPrioOcts    OBJECT-TYPE
    SYNTAX      Counter64
    MAX-ACCESS  read-only
    STATUS      current
    DESCRIPTION
        "The value of tmnxFPNetIngQgPStDrpHPrioOcts indicates the number of
         high priority octets, as determined by the ingress queue group
         policer, dropped by the Pchip due to: MBS exceeded, buffer pool limit
         exceeded, etc."
    ::= { tmnxFPNetIngQGrpPStatEntry 18 }

tmnxFPNetIngQgPStDrpHPrioOctsL   OBJECT-TYPE
    SYNTAX      Counter32
    MAX-ACCESS  read-only
    STATUS      current
    DESCRIPTION
        "The value of tmnxFPNetIngQgPStDrpHPrioOctsL indicates the lower 32
         bits of tmnxFPNetIngQgPStDrpHPrioOcts."
    ::= { tmnxFPNetIngQGrpPStatEntry 19 }

tmnxFPNetIngQgPStDrpHPrioOctsH   OBJECT-TYPE
    SYNTAX      Counter32
    MAX-ACCESS  read-only
    STATUS      current
    DESCRIPTION
        "The value of tmnxFPNetIngQgPStDrpHPrioOctsH indicates the upper 32
         bits of tmnxFPNetIngQgPStDrpHPrioOcts."
    ::= { tmnxFPNetIngQGrpPStatEntry 20 }

tmnxFPNetIngQgPStOffLPrioOcts    OBJECT-TYPE
    SYNTAX      Counter64
    MAX-ACCESS  read-only
    STATUS      current
    DESCRIPTION
        "The value of tmnxFPNetIngQgPStOffLPrioOcts indicates the number of low
         priority octets, as determined by the ingress queue group policer,
         offered by the Pchip to the Pchip."
    ::= { tmnxFPNetIngQGrpPStatEntry 21 }

tmnxFPNetIngQgPStOffLPrioOctsL   OBJECT-TYPE
    SYNTAX      Counter32
    MAX-ACCESS  read-only
    STATUS      current
    DESCRIPTION
        "The value of tmnxFPNetIngQgPStOffLPrioOctsL indicates the lower 32
         bits of tmnxFPNetIngQgPStOffLPrioOcts."
    ::= { tmnxFPNetIngQGrpPStatEntry 22 }

tmnxFPNetIngQgPStOffLPrioOctsH   OBJECT-TYPE
    SYNTAX      Counter32
    MAX-ACCESS  read-only
    STATUS      current
    DESCRIPTION
        "The value of tmnxFPNetIngQgPStOffLPrioOctsH indicates the upper 32
         bits of tmnxFPNetIngQgPStOffLPrioOcts."
    ::= { tmnxFPNetIngQGrpPStatEntry 23 }

tmnxFPNetIngQgPStDrpLPrioOcts    OBJECT-TYPE
    SYNTAX      Counter64
    MAX-ACCESS  read-only
    STATUS      current
    DESCRIPTION
        "The value of tmnxFPNetIngQgPStDrpLPrioOcts indicates the number of low
         priority octets, as determined by the ingress queue group policer,
         dropped by the Pchip due to: MBS exceeded, buffer pool limit exceeded,
         etc."
    ::= { tmnxFPNetIngQGrpPStatEntry 24 }

tmnxFPNetIngQgPStDrpLPrioOctsL   OBJECT-TYPE
    SYNTAX      Counter32
    MAX-ACCESS  read-only
    STATUS      current
    DESCRIPTION
        "The value of tmnxFPNetIngQgPStDrpLPrioOctsL indicates the lower 32
         bits of tmnxFPNetIngQgPStDrpLPrioOcts."
    ::= { tmnxFPNetIngQGrpPStatEntry 25 }

tmnxFPNetIngQgPStDrpLPrioOctsH   OBJECT-TYPE
    SYNTAX      Counter32
    MAX-ACCESS  read-only
    STATUS      current
    DESCRIPTION
        "The value of tmnxFPNetIngQgPStDrpLPrioOctsH indicates the upper 32
         bits of tmnxFPNetIngQgPStDrpLPrioOcts."
    ::= { tmnxFPNetIngQGrpPStatEntry 26 }

tmnxFPNetIngQgPStFwdInProfPkts   OBJECT-TYPE
    SYNTAX      Counter64
    MAX-ACCESS  read-only
    STATUS      current
    DESCRIPTION
        "The value of tmnxFPNetIngQgPStFwdInProfPkts indicates the number of
         in-profile packets (rate below CIR) forwarded by the ingress Pchip."
    ::= { tmnxFPNetIngQGrpPStatEntry 27 }

tmnxFPNetIngQgPStFwdInProfPktsL  OBJECT-TYPE
    SYNTAX      Counter32
    MAX-ACCESS  read-only
    STATUS      current
    DESCRIPTION
        "The value of tmnxFPNetIngQgPStFwdInProfPktsL indicates the lower 32
         bits of tmnxFPNetIngQgPStFwdInProfPkts."
    ::= { tmnxFPNetIngQGrpPStatEntry 28 }

tmnxFPNetIngQgPStFwdInProfPktsH  OBJECT-TYPE
    SYNTAX      Counter32
    MAX-ACCESS  read-only
    STATUS      current
    DESCRIPTION
        "The value of tmnxFPNetIngQgPStFwdInProfPktsH indicates the upper 32
         bits of tmnxFPNetIngQgPStFwdInProfPkts."
    ::= { tmnxFPNetIngQGrpPStatEntry 29 }

tmnxFPNetIngQgPStFwdOutProfPkts  OBJECT-TYPE
    SYNTAX      Counter64
    MAX-ACCESS  read-only
    STATUS      current
    DESCRIPTION
        "The value of tmnxFPNetIngQgPStFwdOutProfPkts indicates the number of
         out-of-profile packets (rate above CIR) forwarded by the ingress
         Pchip."
    ::= { tmnxFPNetIngQGrpPStatEntry 30 }

tmnxFPNetIngQgPStFwdOutProfPktsL OBJECT-TYPE
    SYNTAX      Counter32
    MAX-ACCESS  read-only
    STATUS      current
    DESCRIPTION
        "The value of tmnxFPNetIngQgPStFwdOutProfPktsL indicates the lower 32
         bits of tmnxFPNetIngQgPStFwdOutProfPkts."
    ::= { tmnxFPNetIngQGrpPStatEntry 31 }

tmnxFPNetIngQgPStFwdOutProfPktsH OBJECT-TYPE
    SYNTAX      Counter32
    MAX-ACCESS  read-only
    STATUS      current
    DESCRIPTION
        "The value of tmnxFPNetIngQgPStFwdOutProfPktsH indicates the upper 32
         bits of tmnxFPNetIngQgPStFwdOutProfPkts."
    ::= { tmnxFPNetIngQGrpPStatEntry 32 }

tmnxFPNetIngQgPStFwdInProfOcts   OBJECT-TYPE
    SYNTAX      Counter64
    MAX-ACCESS  read-only
    STATUS      current
    DESCRIPTION
        "The value of tmnxFPNetIngQgPStFwdInProfOcts indicates the number of
         in-profile octets (rate below CIR) forwarded by the ingress Pchip."
    ::= { tmnxFPNetIngQGrpPStatEntry 33 }

tmnxFPNetIngQgPStFwdInProfOctsL  OBJECT-TYPE
    SYNTAX      Counter32
    MAX-ACCESS  read-only
    STATUS      current
    DESCRIPTION
        "The value of tmnxFPNetIngQgPStFwdInProfOctsL indicates the lower 32
         bits of tmnxFPNetIngQgPStFwdInProfOcts."
    ::= { tmnxFPNetIngQGrpPStatEntry 34 }

tmnxFPNetIngQgPStFwdInProfOctsH  OBJECT-TYPE
    SYNTAX      Counter32
    MAX-ACCESS  read-only
    STATUS      current
    DESCRIPTION
        "The value of tmnxFPNetIngQgPStFwdInProfOctsH indicates the upper 32
         bits of tmnxFPNetIngQgPStFwdInProfOcts."
    ::= { tmnxFPNetIngQGrpPStatEntry 35 }

tmnxFPNetIngQgPStFwdOutProfOcts  OBJECT-TYPE
    SYNTAX      Counter64
    MAX-ACCESS  read-only
    STATUS      current
    DESCRIPTION
        "The value of tmnxFPNetIngQgPStFwdOutProfOcts indicates the number of
         out-of-profile octets (rate above CIR) forwarded by the ingress Pchip."
    ::= { tmnxFPNetIngQGrpPStatEntry 36 }

tmnxFPNetIngQgPStFwdOutProfOctsL OBJECT-TYPE
    SYNTAX      Counter32
    MAX-ACCESS  read-only
    STATUS      current
    DESCRIPTION
        "The value of tmnxFPNetIngQgPStFwdOutProfOctsL indicates the lower 32
         bits of tmnxFPNetIngQgPStFwdOutProfOcts."
    ::= { tmnxFPNetIngQGrpPStatEntry 37 }

tmnxFPNetIngQgPStFwdOutProfOctsH OBJECT-TYPE
    SYNTAX      Counter32
    MAX-ACCESS  read-only
    STATUS      current
    DESCRIPTION
        "The value of tmnxFPNetIngQgPStFwdOutProfOctsH indicates the upper 32
         bits of tmnxFPNetIngQgPStFwdOutProfOcts."
    ::= { tmnxFPNetIngQGrpPStatEntry 38 }

tmnxFPNetIngQgPStUncolPktsOff    OBJECT-TYPE
    SYNTAX      Counter64
    MAX-ACCESS  read-only
    STATUS      current
    DESCRIPTION
        "The value of tmnxFPNetIngQgPStUncolPktsOff indicates the number of
         uncolored packets offered to the ingress Pchip."
    ::= { tmnxFPNetIngQGrpPStatEntry 39 }

tmnxFPNetIngQgPStUncolPktsOffL   OBJECT-TYPE
    SYNTAX      Counter32
    MAX-ACCESS  read-only
    STATUS      current
    DESCRIPTION
        "The value of tmnxFPNetIngQgPStUncolPktsOffL indicates the lower 32
         bits of tmnxFPNetIngQgPStUncolPktsOff."
    ::= { tmnxFPNetIngQGrpPStatEntry 40 }

tmnxFPNetIngQgPStUncolPktsOffH   OBJECT-TYPE
    SYNTAX      Counter32
    MAX-ACCESS  read-only
    STATUS      current
    DESCRIPTION
        "The value of tmnxFPNetIngQgPStUncolPktsOffH indicates the upper 32
         bits of tmnxFPNetIngQgPStUncolPktsOff."
    ::= { tmnxFPNetIngQGrpPStatEntry 41 }

tmnxFPNetIngQgPStUncolOctsOff    OBJECT-TYPE
    SYNTAX      Counter64
    MAX-ACCESS  read-only
    STATUS      current
    DESCRIPTION
        "The value of tmnxFPNetIngQgPStUncolOctsOff indicates the number of
         uncolored octets offered to the ingress Pchip."
    ::= { tmnxFPNetIngQGrpPStatEntry 42 }

tmnxFPNetIngQgPStUncolOctsOffL   OBJECT-TYPE
    SYNTAX      Counter32
    MAX-ACCESS  read-only
    STATUS      current
    DESCRIPTION
        "The value of tmnxFPNetIngQgPStUncolOctsOffL indicates the lower 32
         bits of tmnxFPNetIngQgPStUncolOctsOff."
    ::= { tmnxFPNetIngQGrpPStatEntry 43 }

tmnxFPNetIngQgPStUncolOctsOffH   OBJECT-TYPE
    SYNTAX      Counter32
    MAX-ACCESS  read-only
    STATUS      current
    DESCRIPTION
        "The value of tmnxFPNetIngQgPStUncolOctsOffH indicates the higher 32
         bits of the value of tmnxFPNetIngQgPStUncolOctsOff."
    ::= { tmnxFPNetIngQGrpPStatEntry 44 }

tmnxFPAccIngQGrpPStatTable       OBJECT-TYPE
    SYNTAX      SEQUENCE OF TmnxFPAccIngQGrpPStatEntry
    MAX-ACCESS  not-accessible
    STATUS      current
    DESCRIPTION
        "The tmnxFPAccIngQGrpPStatTable contains forwarding-plane ingress QoS
         queue group policer statistics on access side."
    ::= { tmnxCardObjs 28 }

tmnxFPAccIngQGrpPStatEntry       OBJECT-TYPE
    SYNTAX      TmnxFPAccIngQGrpPStatEntry
    MAX-ACCESS  not-accessible
    STATUS      current
    DESCRIPTION
        "The value of tmnxFPAccIngQGrpPStatEntry defines an entry in the
         tmnxFPAccIngQGrpPStatTable. It represents statistics about a specific
         QoS ingress queue group policer."
    INDEX       {
        tmnxChassisIndex,
        tmnxCardSlotNum,
        tmnxFPNum,
        tmnxFPAccIngQGrpName,
        tmnxFPAccIngQGrpInstanceId,
        tmnxFPAccIngQGrpPStatPolicerId
    }
    ::= { tmnxFPAccIngQGrpPStatTable 1 }

TmnxFPAccIngQGrpPStatEntry       ::= SEQUENCE
{
    tmnxFPAccIngQGrpPStatPolicerId   TIngPolicerId,
    tmnxFPAccIngQGrpPStatMode        TmnxIngPolicerStatMode,
    tmnxFPAccIngQgPStOffHPrioPkts    Counter64,
    tmnxFPAccIngQgPStOffHPrioPktsL   Counter32,
    tmnxFPAccIngQgPStOffHPrioPktsH   Counter32,
    tmnxFPAccIngQgPStDrpHPrioPkts    Counter64,
    tmnxFPAccIngQgPStDrpHPrioPktsL   Counter32,
    tmnxFPAccIngQgPStDrpHPrioPktsH   Counter32,
    tmnxFPAccIngQgPStOffLPrioPkts    Counter64,
    tmnxFPAccIngQgPStOffLPrioPktsL   Counter32,
    tmnxFPAccIngQgPStOffLPrioPktsH   Counter32,
    tmnxFPAccIngQgPStDrpLPrioPkts    Counter64,
    tmnxFPAccIngQgPStDrpLPrioPktsL   Counter32,
    tmnxFPAccIngQgPStDrpLPrioPktsH   Counter32,
    tmnxFPAccIngQgPStOffHPrioOcts    Counter64,
    tmnxFPAccIngQgPStOffHPrioOctsL   Counter32,
    tmnxFPAccIngQgPStOffHPrioOctsH   Counter32,
    tmnxFPAccIngQgPStDrpHPrioOcts    Counter64,
    tmnxFPAccIngQgPStDrpHPrioOctsL   Counter32,
    tmnxFPAccIngQgPStDrpHPrioOctsH   Counter32,
    tmnxFPAccIngQgPStOffLPrioOcts    Counter64,
    tmnxFPAccIngQgPStOffLPrioOctsL   Counter32,
    tmnxFPAccIngQgPStOffLPrioOctsH   Counter32,
    tmnxFPAccIngQgPStDrpLPrioOcts    Counter64,
    tmnxFPAccIngQgPStDrpLPrioOctsL   Counter32,
    tmnxFPAccIngQgPStDrpLPrioOctsH   Counter32,
    tmnxFPAccIngQgPStFwdInProfPkts   Counter64,
    tmnxFPAccIngQgPStFwdInProfPktsL  Counter32,
    tmnxFPAccIngQgPStFwdInProfPktsH  Counter32,
    tmnxFPAccIngQgPStFwdOutProfPkts  Counter64,
    tmnxFPAccIngQgPStFwdOutProfPktsL Counter32,
    tmnxFPAccIngQgPStFwdOutProfPktsH Counter32,
    tmnxFPAccIngQgPStFwdInProfOcts   Counter64,
    tmnxFPAccIngQgPStFwdInProfOctsL  Counter32,
    tmnxFPAccIngQgPStFwdInProfOctsH  Counter32,
    tmnxFPAccIngQgPStFwdOutProfOcts  Counter64,
    tmnxFPAccIngQgPStFwdOutProfOctsL Counter32,
    tmnxFPAccIngQgPStFwdOutProfOctsH Counter32,
    tmnxFPAccIngQgPStUncolPktsOff    Counter64,
    tmnxFPAccIngQgPStUncolPktsOffL   Counter32,
    tmnxFPAccIngQgPStUncolPktsOffH   Counter32,
    tmnxFPAccIngQgPStUncolOctsOff    Counter64,
    tmnxFPAccIngQgPStUncolOctsOffL   Counter32,
    tmnxFPAccIngQgPStUncolOctsOffH   Counter32
}

tmnxFPAccIngQGrpPStatPolicerId   OBJECT-TYPE
    SYNTAX      TIngPolicerId
    MAX-ACCESS  not-accessible
    STATUS      current
    DESCRIPTION
        "The value of tmnxFPAccIngQGrpPStatPolicerId specifies the index of the
         ingress QoS policer of this forwarding-plane queue group on access."
    ::= { tmnxFPAccIngQGrpPStatEntry 1 }

tmnxFPAccIngQGrpPStatMode        OBJECT-TYPE
    SYNTAX      TmnxIngPolicerStatMode
    MAX-ACCESS  read-only
    STATUS      current
    DESCRIPTION
        "The value of tmnxFPAccIngQGrpPStatMode indicates the stat mode used by
         this policer."
    ::= { tmnxFPAccIngQGrpPStatEntry 2 }

tmnxFPAccIngQgPStOffHPrioPkts    OBJECT-TYPE
    SYNTAX      Counter64
    MAX-ACCESS  read-only
    STATUS      current
    DESCRIPTION
        "The value of tmnxFPAccIngQgPStOffHPrioPkts indicates the number of
         high priority packets, as determined by the ingress queue group
         policer, offered by the Pchip to the Qchip."
    ::= { tmnxFPAccIngQGrpPStatEntry 3 }

tmnxFPAccIngQgPStOffHPrioPktsL   OBJECT-TYPE
    SYNTAX      Counter32
    MAX-ACCESS  read-only
    STATUS      current
    DESCRIPTION
        "The value of tmnxFPAccIngQgPStOffHPrioPktsL indicates the lower 32
         bits of tmnxFPAccIngQgPStOffHPrioPkts."
    ::= { tmnxFPAccIngQGrpPStatEntry 4 }

tmnxFPAccIngQgPStOffHPrioPktsH   OBJECT-TYPE
    SYNTAX      Counter32
    MAX-ACCESS  read-only
    STATUS      current
    DESCRIPTION
        "The value of tmnxFPAccIngQgPStOffHPrioPktsH indicates the upper 32
         bits of tmnxFPAccIngQgPStOffHPrioPkts."
    ::= { tmnxFPAccIngQGrpPStatEntry 5 }

tmnxFPAccIngQgPStDrpHPrioPkts    OBJECT-TYPE
    SYNTAX      Counter64
    MAX-ACCESS  read-only
    STATUS      current
    DESCRIPTION
        "The value of tmnxFPAccIngQgPStDrpHPrioPkts indicates the number of
         high priority packets, as determined by the ingress queue group
         policer, dropped by the Pchip due to: MBS exceeded, buffer pool limit
         exceeded, etc."
    ::= { tmnxFPAccIngQGrpPStatEntry 6 }

tmnxFPAccIngQgPStDrpHPrioPktsL   OBJECT-TYPE
    SYNTAX      Counter32
    MAX-ACCESS  read-only
    STATUS      current
    DESCRIPTION
        "The value of tmnxFPAccIngQgPStDrpHPrioPktsL indicates the lower 32
         bits of tmnxFPAccIngQgPStDrpHPrioPkts."
    ::= { tmnxFPAccIngQGrpPStatEntry 7 }

tmnxFPAccIngQgPStDrpHPrioPktsH   OBJECT-TYPE
    SYNTAX      Counter32
    MAX-ACCESS  read-only
    STATUS      current
    DESCRIPTION
        "The value of tmnxFPAccIngQgPStDrpHPrioPktsH indicates the upper 32
         bits of tmnxFPAccIngQgPStDrpHPrioPkts."
    ::= { tmnxFPAccIngQGrpPStatEntry 8 }

tmnxFPAccIngQgPStOffLPrioPkts    OBJECT-TYPE
    SYNTAX      Counter64
    MAX-ACCESS  read-only
    STATUS      current
    DESCRIPTION
        "The value of tmnxFPAccIngQgPStOffLPrioPkts indicates the number of low
         priority packets, as determined by the ingress queue group policer,
         offered by the Pchip to the Qchip."
    ::= { tmnxFPAccIngQGrpPStatEntry 9 }

tmnxFPAccIngQgPStOffLPrioPktsL   OBJECT-TYPE
    SYNTAX      Counter32
    MAX-ACCESS  read-only
    STATUS      current
    DESCRIPTION
        "The value of tmnxFPAccIngQgPStOffLPrioPktsL indicates the lower 32
         bits of tmnxFPAccIngQgPStOffLPrioPkts."
    ::= { tmnxFPAccIngQGrpPStatEntry 10 }

tmnxFPAccIngQgPStOffLPrioPktsH   OBJECT-TYPE
    SYNTAX      Counter32
    MAX-ACCESS  read-only
    STATUS      current
    DESCRIPTION
        "The value of tmnxFPAccIngQgPStOffLPrioPktsH indicates the upper 32
         bits of tmnxFPAccIngQgPStOffLPrioPkts."
    ::= { tmnxFPAccIngQGrpPStatEntry 11 }

tmnxFPAccIngQgPStDrpLPrioPkts    OBJECT-TYPE
    SYNTAX      Counter64
    MAX-ACCESS  read-only
    STATUS      current
    DESCRIPTION
        "The value of tmnxFPAccIngQgPStDrpLPrioPkts indicates the number of low
         priority packets, as determined by the ingress queue group policer,
         dropped by the Pchip due to: MBS exceeded, buffer pool limit exceeded,
         etc."
    ::= { tmnxFPAccIngQGrpPStatEntry 12 }

tmnxFPAccIngQgPStDrpLPrioPktsL   OBJECT-TYPE
    SYNTAX      Counter32
    MAX-ACCESS  read-only
    STATUS      current
    DESCRIPTION
        "The value of tmnxFPAccIngQgPStDrpLPrioPktsL indicates the lower 32
         bits of tmnxFPAccIngQgPStDrpLPrioPkts."
    ::= { tmnxFPAccIngQGrpPStatEntry 13 }

tmnxFPAccIngQgPStDrpLPrioPktsH   OBJECT-TYPE
    SYNTAX      Counter32
    MAX-ACCESS  read-only
    STATUS      current
    DESCRIPTION
        "The value of tmnxFPAccIngQgPStDrpLPrioPktsH indicates the upper 32
         bits of tmnxFPAccIngQgPStDrpLPrioPkts."
    ::= { tmnxFPAccIngQGrpPStatEntry 14 }

tmnxFPAccIngQgPStOffHPrioOcts    OBJECT-TYPE
    SYNTAX      Counter64
    MAX-ACCESS  read-only
    STATUS      current
    DESCRIPTION
        "The value of tmnxFPAccIngQgPStOffHPrioOcts indicates the number of
         high priority octets, as determined by the ingress queue group
         policer, offered by the Pchip to the Qchip."
    ::= { tmnxFPAccIngQGrpPStatEntry 15 }

tmnxFPAccIngQgPStOffHPrioOctsL   OBJECT-TYPE
    SYNTAX      Counter32
    MAX-ACCESS  read-only
    STATUS      current
    DESCRIPTION
        "The value of tmnxFPAccIngQgPStOffHPrioOctsL indicates the lower 32
         bits of tmnxFPAccIngQgPStOffHPrioOcts."
    ::= { tmnxFPAccIngQGrpPStatEntry 16 }

tmnxFPAccIngQgPStOffHPrioOctsH   OBJECT-TYPE
    SYNTAX      Counter32
    MAX-ACCESS  read-only
    STATUS      current
    DESCRIPTION
        "The value of tmnxFPAccIngQgPStOffHPrioOctsH indicates the upper 32
         bits of tmnxFPAccIngQgPStOffHPrioOcts."
    ::= { tmnxFPAccIngQGrpPStatEntry 17 }

tmnxFPAccIngQgPStDrpHPrioOcts    OBJECT-TYPE
    SYNTAX      Counter64
    MAX-ACCESS  read-only
    STATUS      current
    DESCRIPTION
        "The value of tmnxFPAccIngQgPStDrpHPrioOcts indicates the number of
         high priority octets, as determined by the ingress queue group
         policer, dropped by the Pchip due to: MBS exceeded, buffer pool limit
         exceeded, etc."
    ::= { tmnxFPAccIngQGrpPStatEntry 18 }

tmnxFPAccIngQgPStDrpHPrioOctsL   OBJECT-TYPE
    SYNTAX      Counter32
    MAX-ACCESS  read-only
    STATUS      current
    DESCRIPTION
        "The value of tmnxFPAccIngQgPStDrpHPrioOctsL indicates the lower 32
         bits of tmnxFPAccIngQgPStDrpHPrioOcts."
    ::= { tmnxFPAccIngQGrpPStatEntry 19 }

tmnxFPAccIngQgPStDrpHPrioOctsH   OBJECT-TYPE
    SYNTAX      Counter32
    MAX-ACCESS  read-only
    STATUS      current
    DESCRIPTION
        "The value of tmnxFPAccIngQgPStDrpHPrioOctsH indicates the upper 32
         bits of tmnxFPAccIngQgPStDrpHPrioOcts."
    ::= { tmnxFPAccIngQGrpPStatEntry 20 }

tmnxFPAccIngQgPStOffLPrioOcts    OBJECT-TYPE
    SYNTAX      Counter64
    MAX-ACCESS  read-only
    STATUS      current
    DESCRIPTION
        "The value of tmnxFPAccIngQgPStOffLPrioOcts indicates the number of low
         priority octets, as determined by the ingress queue group policer,
         offered by the Pchip to the Pchip."
    ::= { tmnxFPAccIngQGrpPStatEntry 21 }

tmnxFPAccIngQgPStOffLPrioOctsL   OBJECT-TYPE
    SYNTAX      Counter32
    MAX-ACCESS  read-only
    STATUS      current
    DESCRIPTION
        "The value of tmnxFPAccIngQgPStOffLPrioOctsL indicates the lower 32
         bits of tmnxFPAccIngQgPStOffLPrioOcts."
    ::= { tmnxFPAccIngQGrpPStatEntry 22 }

tmnxFPAccIngQgPStOffLPrioOctsH   OBJECT-TYPE
    SYNTAX      Counter32
    MAX-ACCESS  read-only
    STATUS      current
    DESCRIPTION
        "The value of tmnxFPAccIngQgPStOffLPrioOctsH indicates the upper 32
         bits of tmnxFPAccIngQgPStOffLPrioOcts."
    ::= { tmnxFPAccIngQGrpPStatEntry 23 }

tmnxFPAccIngQgPStDrpLPrioOcts    OBJECT-TYPE
    SYNTAX      Counter64
    MAX-ACCESS  read-only
    STATUS      current
    DESCRIPTION
        "The value of tmnxFPAccIngQgPStDrpLPrioOcts indicates the number of low
         priority octets, as determined by the ingress queue group policer,
         dropped by the Pchip due to: MBS exceeded, buffer pool limit exceeded,
         etc."
    ::= { tmnxFPAccIngQGrpPStatEntry 24 }

tmnxFPAccIngQgPStDrpLPrioOctsL   OBJECT-TYPE
    SYNTAX      Counter32
    MAX-ACCESS  read-only
    STATUS      current
    DESCRIPTION
        "The value of tmnxFPAccIngQgPStDrpLPrioOctsL indicates the lower 32
         bits of tmnxFPAccIngQgPStDrpLPrioOcts."
    ::= { tmnxFPAccIngQGrpPStatEntry 25 }

tmnxFPAccIngQgPStDrpLPrioOctsH   OBJECT-TYPE
    SYNTAX      Counter32
    MAX-ACCESS  read-only
    STATUS      current
    DESCRIPTION
        "The value of tmnxFPAccIngQgPStDrpLPrioOctsH indicates the upper 32
         bits of tmnxFPAccIngQgPStDrpLPrioOcts."
    ::= { tmnxFPAccIngQGrpPStatEntry 26 }

tmnxFPAccIngQgPStFwdInProfPkts   OBJECT-TYPE
    SYNTAX      Counter64
    MAX-ACCESS  read-only
    STATUS      current
    DESCRIPTION
        "The value of tmnxFPAccIngQgPStFwdInProfPkts indicates the number of
         in-profile packets (rate below CIR) forwarded by the ingress Pchip."
    ::= { tmnxFPAccIngQGrpPStatEntry 27 }

tmnxFPAccIngQgPStFwdInProfPktsL  OBJECT-TYPE
    SYNTAX      Counter32
    MAX-ACCESS  read-only
    STATUS      current
    DESCRIPTION
        "The value of tmnxFPAccIngQgPStFwdInProfPktsL indicates the lower 32
         bits of tmnxFPAccIngQgPStFwdInProfPkts."
    ::= { tmnxFPAccIngQGrpPStatEntry 28 }

tmnxFPAccIngQgPStFwdInProfPktsH  OBJECT-TYPE
    SYNTAX      Counter32
    MAX-ACCESS  read-only
    STATUS      current
    DESCRIPTION
        "The value of tmnxFPAccIngQgPStFwdInProfPktsH indicates the upper 32
         bits of tmnxFPAccIngQgPStFwdInProfPkts."
    ::= { tmnxFPAccIngQGrpPStatEntry 29 }

tmnxFPAccIngQgPStFwdOutProfPkts  OBJECT-TYPE
    SYNTAX      Counter64
    MAX-ACCESS  read-only
    STATUS      current
    DESCRIPTION
        "The value of tmnxFPAccIngQgPStFwdOutProfPkts indicates the number of
         out-of-profile packets (rate above CIR) forwarded by the ingress
         Pchip."
    ::= { tmnxFPAccIngQGrpPStatEntry 30 }

tmnxFPAccIngQgPStFwdOutProfPktsL OBJECT-TYPE
    SYNTAX      Counter32
    MAX-ACCESS  read-only
    STATUS      current
    DESCRIPTION
        "The value of tmnxFPAccIngQgPStFwdOutProfPktsL indicates the lower 32
         bits of tmnxFPAccIngQgPStFwdOutProfPkts."
    ::= { tmnxFPAccIngQGrpPStatEntry 31 }

tmnxFPAccIngQgPStFwdOutProfPktsH OBJECT-TYPE
    SYNTAX      Counter32
    MAX-ACCESS  read-only
    STATUS      current
    DESCRIPTION
        "The value of tmnxFPAccIngQgPStFwdOutProfPktsH indicates the upper 32
         bits of tmnxFPAccIngQgPStFwdOutProfPkts."
    ::= { tmnxFPAccIngQGrpPStatEntry 32 }

tmnxFPAccIngQgPStFwdInProfOcts   OBJECT-TYPE
    SYNTAX      Counter64
    MAX-ACCESS  read-only
    STATUS      current
    DESCRIPTION
        "The value of tmnxFPAccIngQgPStFwdInProfOcts indicates the number of
         in-profile octets (rate below CIR) forwarded by the ingress Pchip."
    ::= { tmnxFPAccIngQGrpPStatEntry 33 }

tmnxFPAccIngQgPStFwdInProfOctsL  OBJECT-TYPE
    SYNTAX      Counter32
    MAX-ACCESS  read-only
    STATUS      current
    DESCRIPTION
        "The value of tmnxFPAccIngQgPStFwdInProfOctsL indicates the lower 32
         bits of tmnxFPAccIngQgPStFwdInProfOcts."
    ::= { tmnxFPAccIngQGrpPStatEntry 34 }

tmnxFPAccIngQgPStFwdInProfOctsH  OBJECT-TYPE
    SYNTAX      Counter32
    MAX-ACCESS  read-only
    STATUS      current
    DESCRIPTION
        "The value of tmnxFPAccIngQgPStFwdInProfOctsH indicates the upper 32
         bits of tmnxFPAccIngQgPStFwdInProfOcts."
    ::= { tmnxFPAccIngQGrpPStatEntry 35 }

tmnxFPAccIngQgPStFwdOutProfOcts  OBJECT-TYPE
    SYNTAX      Counter64
    MAX-ACCESS  read-only
    STATUS      current
    DESCRIPTION
        "The value of tmnxFPAccIngQgPStFwdOutProfOcts indicates the number of
         out-of-profile octets (rate above CIR) forwarded by the ingress Pchip."
    ::= { tmnxFPAccIngQGrpPStatEntry 36 }

tmnxFPAccIngQgPStFwdOutProfOctsL OBJECT-TYPE
    SYNTAX      Counter32
    MAX-ACCESS  read-only
    STATUS      current
    DESCRIPTION
        "The value of tmnxFPAccIngQgPStFwdOutProfOctsL indicates the lower 32
         bits of tmnxFPAccIngQgPStFwdOutProfOcts."
    ::= { tmnxFPAccIngQGrpPStatEntry 37 }

tmnxFPAccIngQgPStFwdOutProfOctsH OBJECT-TYPE
    SYNTAX      Counter32
    MAX-ACCESS  read-only
    STATUS      current
    DESCRIPTION
        "The value of tmnxFPAccIngQgPStFwdOutProfOctsH indicates the upper 32
         bits of tmnxFPAccIngQgPStFwdOutProfOcts."
    ::= { tmnxFPAccIngQGrpPStatEntry 38 }

tmnxFPAccIngQgPStUncolPktsOff    OBJECT-TYPE
    SYNTAX      Counter64
    MAX-ACCESS  read-only
    STATUS      current
    DESCRIPTION
        "The value of tmnxFPAccIngQgPStUncolPktsOff indicates the number of
         uncolored packets offered to the ingress Pchip."
    ::= { tmnxFPAccIngQGrpPStatEntry 39 }

tmnxFPAccIngQgPStUncolPktsOffL   OBJECT-TYPE
    SYNTAX      Counter32
    MAX-ACCESS  read-only
    STATUS      current
    DESCRIPTION
        "The value of tmnxFPAccIngQgPStUncolPktsOffL indicates the lower 32
         bits of tmnxFPAccIngQgPStUncolPktsOff."
    ::= { tmnxFPAccIngQGrpPStatEntry 40 }

tmnxFPAccIngQgPStUncolPktsOffH   OBJECT-TYPE
    SYNTAX      Counter32
    MAX-ACCESS  read-only
    STATUS      current
    DESCRIPTION
        "The value of tmnxFPAccIngQgPStUncolPktsOffH indicates the upper 32
         bits of tmnxFPAccIngQgPStUncolPktsOff."
    ::= { tmnxFPAccIngQGrpPStatEntry 41 }

tmnxFPAccIngQgPStUncolOctsOff    OBJECT-TYPE
    SYNTAX      Counter64
    MAX-ACCESS  read-only
    STATUS      current
    DESCRIPTION
        "The value of tmnxFPAccIngQgPStUncolOctsOff indicates the number of
         uncolored octets offered to the ingress Pchip."
    ::= { tmnxFPAccIngQGrpPStatEntry 42 }

tmnxFPAccIngQgPStUncolOctsOffL   OBJECT-TYPE
    SYNTAX      Counter32
    MAX-ACCESS  read-only
    STATUS      current
    DESCRIPTION
        "The value of tmnxFPAccIngQgPStUncolOctsOffL indicates the lower 32
         bits of tmnxFPAccIngQgPStUncolOctsOff."
    ::= { tmnxFPAccIngQGrpPStatEntry 43 }

tmnxFPAccIngQgPStUncolOctsOffH   OBJECT-TYPE
    SYNTAX      Counter32
    MAX-ACCESS  read-only
    STATUS      current
    DESCRIPTION
        "The value of tmnxFPAccIngQgPStUncolOctsOffH indicates the higher 32
         bits of the value of tmnxFPAccIngQgPStUncolOctsOff."
    ::= { tmnxFPAccIngQGrpPStatEntry 44 }

tFPAccIngQGrpPlcrOvrTblLstChgd   OBJECT-TYPE
    SYNTAX      TimeStamp
    MAX-ACCESS  read-only
    STATUS      current
    DESCRIPTION
        "The value of tFPAccIngQGrpPlcrOvrTblLstChgd indicates the timestamp of
         last change to the tFPAccIngQGrpPlcrOvrTable."
    ::= { tmnxCardObjs 29 }

tFPAccIngQGrpPlcrOvrTable        OBJECT-TYPE
    SYNTAX      SEQUENCE OF TFPAccIngQGrpPlcrOvrEntry
    MAX-ACCESS  not-accessible
    STATUS      current
    DESCRIPTION
        "The value of tFPAccIngQGrpPlcrOvrTable contains forwarding-plane QoS
         ingress queue group policer overrides on access side."
    ::= { tmnxCardObjs 30 }

tFPAccIngQGrpPlcrOvrEntry        OBJECT-TYPE
    SYNTAX      TFPAccIngQGrpPlcrOvrEntry
    MAX-ACCESS  not-accessible
    STATUS      current
    DESCRIPTION
        "The value of tFPAccIngQGrpPlcrOvrEntry defines an entry in the
         tFPAccIngQGrpPlcrOvrTable. It represents policer overrides about a
         specific forwarding-plane QoS ingress queue group policer."
    INDEX       {
        tmnxChassisIndex,
        tmnxCardSlotNum,
        tmnxFPNum,
        tmnxFPAccIngQGrpName,
        tmnxFPAccIngQGrpInstanceId,
        tFPAccIngQGrpPlcrOvrPolicerId
    }
    ::= { tFPAccIngQGrpPlcrOvrTable 1 }

TFPAccIngQGrpPlcrOvrEntry        ::= SEQUENCE
{
    tFPAccIngQGrpPlcrOvrPolicerId    TIngPolicerId,
    tFPAccIngQGrpPlcrOvrRowStatus    RowStatus,
    tFPAccIngQGrpPlcrOvrLastChgd     TimeStamp,
    tFPAccIngQGrpPlcrOvrAdminPIR     THPolPIRRateOverride,
    tFPAccIngQGrpPlcrOvrAdminCIR     THPolCIRRateOverride,
    tFPAccIngQGrpPlcrOvrStatMode     TmnxIngPolicerStatModeOverride,
    tFPAccIngQGrpPlcrOvrMBS          TPolicerBurstSizeBytesOverride,
    tFPAccIngQGrpPlcrOvrCBS          TPolicerBurstSizeBytesOverride,
    tFPAccIngQGrpPlcrOvrPktOffset    TPerPacketOffsetOvr
}

tFPAccIngQGrpPlcrOvrPolicerId    OBJECT-TYPE
    SYNTAX      TIngPolicerId
    MAX-ACCESS  not-accessible
    STATUS      current
    DESCRIPTION
        "The value of tFPAccIngQGrpPlcrOvrPolicerId specifies the index of the
         ingress QoS policer of this forwarding-plane queue group on access."
    ::= { tFPAccIngQGrpPlcrOvrEntry 1 }

tFPAccIngQGrpPlcrOvrRowStatus    OBJECT-TYPE
    SYNTAX      RowStatus
    MAX-ACCESS  read-create
    STATUS      current
    DESCRIPTION
        "The value of tFPAccIngQGrpPlcrOvrRowStatus specifies the Row Status of
         the entry.

         This tFPAccIngQGrpPlcrOvrRowStatus object allows creation/deletion of
         rows in this table."
    ::= { tFPAccIngQGrpPlcrOvrEntry 2 }

tFPAccIngQGrpPlcrOvrLastChgd     OBJECT-TYPE
    SYNTAX      TimeStamp
    MAX-ACCESS  read-only
    STATUS      current
    DESCRIPTION
        "The value of tFPAccIngQGrpPlcrOvrLastChgd indicates the timestamp of
         last change to this row in tFPAccIngQGrpPlcrOvrTable."
    ::= { tFPAccIngQGrpPlcrOvrEntry 3 }

tFPAccIngQGrpPlcrOvrAdminPIR     OBJECT-TYPE
    SYNTAX      THPolPIRRateOverride
    UNITS       "kilobps"
    MAX-ACCESS  read-create
    STATUS      current
    DESCRIPTION
        "The value of tFPAccIngQGrpPlcrOvrAdminPIR specifies the administrative
         PIR specified by the user."
    DEFVAL      { -2 }
    ::= { tFPAccIngQGrpPlcrOvrEntry 4 }

tFPAccIngQGrpPlcrOvrAdminCIR     OBJECT-TYPE
    SYNTAX      THPolCIRRateOverride
    UNITS       "kilobps"
    MAX-ACCESS  read-create
    STATUS      current
    DESCRIPTION
        "The value of tFPAccIngQGrpPlcrOvrAdminCIR specifies the administrative
         CIR specified by the user."
    DEFVAL      { -2 }
    ::= { tFPAccIngQGrpPlcrOvrEntry 5 }

tFPAccIngQGrpPlcrOvrStatMode     OBJECT-TYPE
    SYNTAX      TmnxIngPolicerStatModeOverride
    MAX-ACCESS  read-create
    STATUS      current
    DESCRIPTION
        "The value of tFPAccIngQGrpPlcrOvrStatMode specifies the mode of
         statistics collected by the policer on this forwarding-plane QoS
         ingress queue group."
    DEFVAL      { noOverride }
    ::= { tFPAccIngQGrpPlcrOvrEntry 6 }

tFPAccIngQGrpPlcrOvrMBS          OBJECT-TYPE
    SYNTAX      TPolicerBurstSizeBytesOverride
    UNITS       "bytes"
    MAX-ACCESS  read-create
    STATUS      current
    DESCRIPTION
        "The value of tFPAccIngQGrpPlcrOvrMBS specifies the maximum amount of
         buffer space (in bytes) allowed for the queue by the policer on this
         forwarding-plane QoS ingress queue group."
    DEFVAL      { -2 }
    ::= { tFPAccIngQGrpPlcrOvrEntry 7 }

tFPAccIngQGrpPlcrOvrCBS          OBJECT-TYPE
    SYNTAX      TPolicerBurstSizeBytesOverride
    UNITS       "bytes"
    MAX-ACCESS  read-create
    STATUS      current
    DESCRIPTION
        "The value of tFPAccIngQGrpPlcrOvrCBS specifies the amount of reserved
         buffer space (in bytes) set by the policer on this forwarding-plane
         QoS ingress queue group."
    DEFVAL      { -2 }
    ::= { tFPAccIngQGrpPlcrOvrEntry 8 }

tFPAccIngQGrpPlcrOvrPktOffset    OBJECT-TYPE
    SYNTAX      TPerPacketOffsetOvr
    UNITS       "bytes"
    MAX-ACCESS  read-create
    STATUS      current
    DESCRIPTION
        "The value of tFPAccIngQGrpPlcrOvrPktOffset specifies the packet byte
         offset for addition of policing information by the policer on this
         forwarding-plane QoS ingress queue group."
    DEFVAL      { -128 }
    ::= { tFPAccIngQGrpPlcrOvrEntry 9 }

tFPAccIngQGrpArbitStatTable      OBJECT-TYPE
    SYNTAX      SEQUENCE OF TFPAccIngQGrpArbitStatEntry
    MAX-ACCESS  not-accessible
    STATUS      current
    DESCRIPTION
        "The value of tFPAccIngQGrpArbitStatTable contains forwarding-plane
         ingress QoS queue group policer statistics on access side."
    ::= { tmnxCardObjs 31 }

tFPAccIngQGrpArbitStatEntry      OBJECT-TYPE
    SYNTAX      TFPAccIngQGrpArbitStatEntry
    MAX-ACCESS  not-accessible
    STATUS      current
    DESCRIPTION
        "The value of tFPAccIngQGrpArbitStatEntry defines an entry in the
         tFPAccIngQGrpArbitStatTable. It represents statistics about a specific
         QoS ingress queue group policer."
    INDEX       {
        tmnxChassisIndex,
        tmnxCardSlotNum,
        tmnxFPNum,
        tmnxFPAccIngQGrpName,
        tmnxFPAccIngQGrpInstanceId,
        tFPAccIngQGrpArbitStatName
    }
    ::= { tFPAccIngQGrpArbitStatTable 1 }

TFPAccIngQGrpArbitStatEntry      ::= SEQUENCE
{
    tFPAccIngQGrpArbitStatName       TNamedItem,
    tFPAccIngQGrpArbitStatFwdPkts    Counter64,
    tFPAccIngQGrpArbitStatFwdPktsL   Counter32,
    tFPAccIngQGrpArbitStatFwdPktsH   Counter32,
    tFPAccIngQGrpArbitStatFwdOcts    Counter64,
    tFPAccIngQGrpArbitStatFwdOctsL   Counter32,
    tFPAccIngQGrpArbitStatFwdOctsH   Counter32
}

tFPAccIngQGrpArbitStatName       OBJECT-TYPE
    SYNTAX      TNamedItem
    MAX-ACCESS  not-accessible
    STATUS      current
    DESCRIPTION
        "The value of tFPAccIngQGrpArbitStatName specifies the name of the
         ingress QoS arbiter of this forwarding-plane queue group on access."
    ::= { tFPAccIngQGrpArbitStatEntry 1 }

tFPAccIngQGrpArbitStatFwdPkts    OBJECT-TYPE
    SYNTAX      Counter64
    MAX-ACCESS  read-only
    STATUS      current
    DESCRIPTION
        "The value of tFPAccIngQGrpArbitStatFwdPkts indicates the number of
         forwarded packets by the ingress queue group arbiter Pchip."
    ::= { tFPAccIngQGrpArbitStatEntry 2 }

tFPAccIngQGrpArbitStatFwdPktsL   OBJECT-TYPE
    SYNTAX      Counter32
    MAX-ACCESS  read-only
    STATUS      current
    DESCRIPTION
        "The value of tFPAccIngQGrpArbitStatFwdPktsL indicates the lower 32
         bits of tFPAccIngQGrpArbitStatFwdPkts."
    ::= { tFPAccIngQGrpArbitStatEntry 3 }

tFPAccIngQGrpArbitStatFwdPktsH   OBJECT-TYPE
    SYNTAX      Counter32
    MAX-ACCESS  read-only
    STATUS      current
    DESCRIPTION
        "The value of tFPAccIngQGrpArbitStatFwdPktsH indicates the upper 32
         bits of tFPAccIngQGrpArbitStatFwdPkts."
    ::= { tFPAccIngQGrpArbitStatEntry 4 }

tFPAccIngQGrpArbitStatFwdOcts    OBJECT-TYPE
    SYNTAX      Counter64
    MAX-ACCESS  read-only
    STATUS      current
    DESCRIPTION
        "The value of tFPAccIngQGrpArbitStatFwdOcts indicates the number of
         forwarded octets by the ingress queue group arbiter Pchip."
    ::= { tFPAccIngQGrpArbitStatEntry 5 }

tFPAccIngQGrpArbitStatFwdOctsL   OBJECT-TYPE
    SYNTAX      Counter32
    MAX-ACCESS  read-only
    STATUS      current
    DESCRIPTION
        "The value of tFPAccIngQGrpArbitStatFwdOctsL indicates the lower 32
         bits of tFPAccIngQGrpArbitStatFwdOcts."
    ::= { tFPAccIngQGrpArbitStatEntry 6 }

tFPAccIngQGrpArbitStatFwdOctsH   OBJECT-TYPE
    SYNTAX      Counter32
    MAX-ACCESS  read-only
    STATUS      current
    DESCRIPTION
        "The value of tFPAccIngQGrpArbitStatFwdOctsH indicates the upper 32
         bits of tFPAccIngQGrpArbitStatFwdOcts."
    ::= { tFPAccIngQGrpArbitStatEntry 7 }

tFPNetIngQGrpArbitStatTable      OBJECT-TYPE
    SYNTAX      SEQUENCE OF TFPNetIngQGrpArbitStatEntry
    MAX-ACCESS  not-accessible
    STATUS      current
    DESCRIPTION
        "The value of tFPNetIngQGrpArbitStatTable contains forwarding-plane
         ingress QoS queue group arbiter statistics on network side."
    ::= { tmnxCardObjs 32 }

tFPNetIngQGrpArbitStatEntry      OBJECT-TYPE
    SYNTAX      TFPNetIngQGrpArbitStatEntry
    MAX-ACCESS  not-accessible
    STATUS      current
    DESCRIPTION
        "The value of tFPNetIngQGrpArbitStatEntry defines an entry in the
         tFPNetIngQGrpArbitStatTable. It represents statistics about a specific
         QoS ingress queue group arbiter."
    INDEX       {
        tmnxChassisIndex,
        tmnxCardSlotNum,
        tmnxFPNum,
        tmnxFPNetIngQGrpName,
        tmnxFPNetIngQGrpInstanceId,
        tFPNetIngQGrpArbitStatName
    }
    ::= { tFPNetIngQGrpArbitStatTable 1 }

TFPNetIngQGrpArbitStatEntry      ::= SEQUENCE
{
    tFPNetIngQGrpArbitStatName       TNamedItem,
    tFPNetIngQGrpArbitStatFwdPkts    Counter64,
    tFPNetIngQGrpArbitStatFwdPktsL   Counter32,
    tFPNetIngQGrpArbitStatFwdPktsH   Counter32,
    tFPNetIngQGrpArbitStatFwdOcts    Counter64,
    tFPNetIngQGrpArbitStatFwdOctsL   Counter32,
    tFPNetIngQGrpArbitStatFwdOctsH   Counter32
}

tFPNetIngQGrpArbitStatName       OBJECT-TYPE
    SYNTAX      TNamedItem
    MAX-ACCESS  not-accessible
    STATUS      current
    DESCRIPTION
        "The value of tFPNetIngQGrpArbitStatName specifies the name of the
         ingress QoS arbiter of this forwarding-plane queue group on network."
    ::= { tFPNetIngQGrpArbitStatEntry 1 }

tFPNetIngQGrpArbitStatFwdPkts    OBJECT-TYPE
    SYNTAX      Counter64
    MAX-ACCESS  read-only
    STATUS      current
    DESCRIPTION
        "The value of tFPNetIngQGrpArbitStatFwdPkts indicates the number of
         forwarded packets by the ingress queue group arbiter Pchip."
    ::= { tFPNetIngQGrpArbitStatEntry 2 }

tFPNetIngQGrpArbitStatFwdPktsL   OBJECT-TYPE
    SYNTAX      Counter32
    MAX-ACCESS  read-only
    STATUS      current
    DESCRIPTION
        "The value of tFPNetIngQGrpArbitStatFwdPktsL indicates the lower 32
         bits of tFPNetIngQGrpArbitStatFwdPkts."
    ::= { tFPNetIngQGrpArbitStatEntry 3 }

tFPNetIngQGrpArbitStatFwdPktsH   OBJECT-TYPE
    SYNTAX      Counter32
    MAX-ACCESS  read-only
    STATUS      current
    DESCRIPTION
        "The value of tFPNetIngQGrpArbitStatFwdPktsH indicates the upper 32
         bits of tFPNetIngQGrpArbitStatFwdPkts."
    ::= { tFPNetIngQGrpArbitStatEntry 4 }

tFPNetIngQGrpArbitStatFwdOcts    OBJECT-TYPE
    SYNTAX      Counter64
    MAX-ACCESS  read-only
    STATUS      current
    DESCRIPTION
        "The value of tFPNetIngQGrpArbitStatFwdOcts indicates the number of
         forwarded octets by the ingress queue group arbiter Pchip."
    ::= { tFPNetIngQGrpArbitStatEntry 5 }

tFPNetIngQGrpArbitStatFwdOctsL   OBJECT-TYPE
    SYNTAX      Counter32
    MAX-ACCESS  read-only
    STATUS      current
    DESCRIPTION
        "The value of tFPNetIngQGrpArbitStatFwdOctsL indicates the lower 32
         bits of tFPNetIngQGrpArbitStatFwdOcts."
    ::= { tFPNetIngQGrpArbitStatEntry 6 }

tFPNetIngQGrpArbitStatFwdOctsH   OBJECT-TYPE
    SYNTAX      Counter32
    MAX-ACCESS  read-only
    STATUS      current
    DESCRIPTION
        "The value of tFPNetIngQGrpArbitStatFwdOctsH indicates the upper 32
         bits of tFPNetIngQGrpArbitStatFwdOcts."
    ::= { tFPNetIngQGrpArbitStatEntry 7 }

tmnxVirtualSchedulerAdjTable     OBJECT-TYPE
    SYNTAX      SEQUENCE OF TmnxVirtualSchedulerAdjEntry
    MAX-ACCESS  not-accessible
    STATUS      current
    DESCRIPTION
        "The tmnxVirtualSchedulerAdjTable has an entry to fine tune Quality of
         Service (QoS) parameters."
    ::= { tmnxCardObjs 33 }

tmnxVirtualSchedulerAdjEntry     OBJECT-TYPE
    SYNTAX      TmnxVirtualSchedulerAdjEntry
    MAX-ACCESS  not-accessible
    STATUS      current
    DESCRIPTION
        "The tmnxVirtualSchedulerAdjEntry allows fine tune Quality of Service
         (QoS) parameters on the corresponding card.

         The row exists only if the associated card instance identified by
         tmnxCardSlotNum exists in the tmnxCardTable."
    INDEX       {
        tmnxChassisIndex,
        tmnxCardSlotNum
    }
    ::= { tmnxVirtualSchedulerAdjTable 1 }

TmnxVirtualSchedulerAdjEntry     ::= SEQUENCE
{
    tmnxCardRateCalcFastQueue        Unsigned32,
    tmnxCardRateCalcSlowQueue        Unsigned32,
    tmnxCardSchedRun                 Unsigned32,
    tmnxCardTaskScheduling           Unsigned32,
    tmnxCardSlowQueueThresh          Integer32,
    tmnxCardInternalSchedWghtMode    TmnxInternalSchedWeightMode,
    tmnxCardManualCntrlAdminState    TmnxAdminState
}

tmnxCardRateCalcFastQueue        OBJECT-TYPE
    SYNTAX      Unsigned32 (1..100000)
    UNITS       "thousandths of a percent"
    MAX-ACCESS  read-write
    STATUS      current
    DESCRIPTION
        "The value of tmnxCardRateCalcFastQueue specifies the percentage by
         which fine tuning of Quality of Service (QoS) parameter 'Fast-Queue'
         is modified."
    DEFVAL      { 10000 }
    ::= { tmnxVirtualSchedulerAdjEntry 1 }

tmnxCardRateCalcSlowQueue        OBJECT-TYPE
    SYNTAX      Unsigned32 (1..100000)
    UNITS       "thousandths of a percent"
    MAX-ACCESS  read-write
    STATUS      current
    DESCRIPTION
        "The value of tmnxCardRateCalcSlowQueue specifies the percentage by
         which fine tuning of Quality of Service (QoS) parameter 'Slow-Queue'
         is modified."
    DEFVAL      { 10000 }
    ::= { tmnxVirtualSchedulerAdjEntry 2 }

tmnxCardSchedRun                 OBJECT-TYPE
    SYNTAX      Unsigned32 (1..100000)
    UNITS       "thousandths of a percent"
    MAX-ACCESS  read-write
    STATUS      current
    DESCRIPTION
        "The value of tmnxCardSchedRun specifies the percentage by which the
         minimum amount of time required between the iterations of bandwidth
         distribution by an Quality of Service (QoS) virtual scheduler is
         modified."
    DEFVAL      { 10000 }
    ::= { tmnxVirtualSchedulerAdjEntry 3 }

tmnxCardTaskScheduling           OBJECT-TYPE
    SYNTAX      Unsigned32 (1..100000)
    UNITS       "thousandths of a percent"
    MAX-ACCESS  read-write
    STATUS      current
    DESCRIPTION
        "The value of tmnxCardTaskScheduling specifies the percentage change in
         virtual scheduling task wake up interval."
    DEFVAL      { 10000 }
    ::= { tmnxVirtualSchedulerAdjEntry 4 }

tmnxCardSlowQueueThresh          OBJECT-TYPE
    SYNTAX      Integer32 (0..1000000)
    UNITS       "kilobps"
    MAX-ACCESS  read-write
    STATUS      current
    DESCRIPTION
        "The value of tmnxCardSlowQueueThresh specifies the rate at which
         queues are placed in the 'slow-queue' category."
    DEFVAL      { 1000 }
    ::= { tmnxVirtualSchedulerAdjEntry 5 }

tmnxCardInternalSchedWghtMode    OBJECT-TYPE
    SYNTAX      TmnxInternalSchedWeightMode
    MAX-ACCESS  read-write
    STATUS      current
    DESCRIPTION
        "The value of tmnxCardInternalSchedWghtMode specifies the weight-mode
         adjustment applied on this card."
    DEFVAL      { default }
    ::= { tmnxVirtualSchedulerAdjEntry 6 }

tmnxCardManualCntrlAdminState    OBJECT-TYPE
    SYNTAX      TmnxAdminState
    MAX-ACCESS  read-write
    STATUS      current
    DESCRIPTION
        "The value of tmnxCardManualCntrlAdminState specifies the
         administrative state of HQoS related configurable parameters. If
         tmnxCardManualCntrlAdminState is set to 'outOfService', manual control
         for workload performance for this card is disabled."
    DEFVAL      { outOfService }
    ::= { tmnxVirtualSchedulerAdjEntry 7 }

tmnxFpDcpDynEnfrcPlcrStatTable   OBJECT-TYPE
    SYNTAX      SEQUENCE OF TmnxFpDcpDynEnfrcPlcrStatEntry
    MAX-ACCESS  not-accessible
    STATUS      current
    DESCRIPTION
        "The tmnxFpDcpDynEnfrcPlcrStatTable has the statistics information of
         the dynamic enforcement policer per forwarding plane."
    ::= { tmnxCardObjs 34 }

tmnxFpDcpDynEnfrcPlcrStatEntry   OBJECT-TYPE
    SYNTAX      TmnxFpDcpDynEnfrcPlcrStatEntry
    MAX-ACCESS  not-accessible
    STATUS      current
    DESCRIPTION
        "The value of tmnxFpDcpDynEnfrcPlcrStatEntry represents statistics
         information per forwarding plane for the dynamic enforcement policer."
    INDEX       {
        tmnxChassisIndex,
        tmnxCardSlotNum,
        tmnxFPNum
    }
    ::= { tmnxFpDcpDynEnfrcPlcrStatTable 1 }

TmnxFpDcpDynEnfrcPlcrStatEntry   ::= SEQUENCE
{
    tmnxFpDcpDynPlcrHiWtrMrkHitCnt   Counter32,
    tmnxFpDcpDynPlcrHiWtrMrkTime     TimeStamp,
    tmnxFpDcpDynPlcrAllocFailCount   Counter32,
    tmnxFpDcpDynPlcrInUse            Counter32
}

tmnxFpDcpDynPlcrHiWtrMrkHitCnt   OBJECT-TYPE
    SYNTAX      Counter32
    MAX-ACCESS  read-only
    STATUS      current
    DESCRIPTION
        "The value of tmnxFpDcpDynPlcrHiWtrMrkHitCnt indicates the maximum
         number of dynamic enforcement policers in use at any point of time."
    ::= { tmnxFpDcpDynEnfrcPlcrStatEntry 1 }

tmnxFpDcpDynPlcrHiWtrMrkTime     OBJECT-TYPE
    SYNTAX      TimeStamp
    MAX-ACCESS  read-only
    STATUS      current
    DESCRIPTION
        "The value of tmnxFpDcpDynPlcrHiWtrMrkTime indicates the time at which
         maximum number of dynamic enforcement policers was hit."
    ::= { tmnxFpDcpDynEnfrcPlcrStatEntry 2 }

tmnxFpDcpDynPlcrAllocFailCount   OBJECT-TYPE
    SYNTAX      Counter32
    MAX-ACCESS  read-only
    STATUS      current
    DESCRIPTION
        "The value of tmnxFpDcpDynPlcrAllocFailCount indicated the number of
         times the system failed to allocate dynamic enforcement policers."
    ::= { tmnxFpDcpDynEnfrcPlcrStatEntry 3 }

tmnxFpDcpDynPlcrInUse            OBJECT-TYPE
    SYNTAX      Counter32
    MAX-ACCESS  read-only
    STATUS      current
    DESCRIPTION
        "The value of tmnxFpDcpDynPlcrInUse indicated the number of dynamic
         enforcement policers currently in use by the system."
    ::= { tmnxFpDcpDynEnfrcPlcrStatEntry 4 }

tFPNetIngQGrpPlcrOvrTblLstChgd   OBJECT-TYPE
    SYNTAX      TimeStamp
    MAX-ACCESS  read-only
    STATUS      current
    DESCRIPTION
        "The value of tFPNetIngQGrpPlcrOvrTblLstChgd indicates the timestamp of
         last change to the tFPNetIngQGrpPlcrOvrTable."
    ::= { tmnxCardObjs 35 }

tFPNetIngQGrpPlcrOvrTable        OBJECT-TYPE
    SYNTAX      SEQUENCE OF TFPNetIngQGrpPlcrOvrEntry
    MAX-ACCESS  not-accessible
    STATUS      current
    DESCRIPTION
        "The value of tFPNetIngQGrpPlcrOvrTable contains forwarding-plane QoS
         ingress queue group policer overrides on network side."
    ::= { tmnxCardObjs 36 }

tFPNetIngQGrpPlcrOvrEntry        OBJECT-TYPE
    SYNTAX      TFPNetIngQGrpPlcrOvrEntry
    MAX-ACCESS  not-accessible
    STATUS      current
    DESCRIPTION
        "The value of tFPNetIngQGrpPlcrOvrEntry defines an entry in the
         tFPNetIngQGrpPlcrOvrTable. It represents policer overrides about a
         specific forwarding-plane QoS ingress queue group policer."
    INDEX       {
        tmnxChassisIndex,
        tmnxCardSlotNum,
        tmnxFPNum,
        tmnxFPNetIngQGrpName,
        tmnxFPNetIngQGrpInstanceId,
        tFPNetIngQGrpPlcrOvrPolicerId
    }
    ::= { tFPNetIngQGrpPlcrOvrTable 1 }

TFPNetIngQGrpPlcrOvrEntry        ::= SEQUENCE
{
    tFPNetIngQGrpPlcrOvrPolicerId    TIngPolicerId,
    tFPNetIngQGrpPlcrOvrRowStatus    RowStatus,
    tFPNetIngQGrpPlcrOvrLastChgd     TimeStamp,
    tFPNetIngQGrpPlcrOvrAdminPIR     THPolPIRRateOverride,
    tFPNetIngQGrpPlcrOvrAdminCIR     THPolCIRRateOverride,
    tFPNetIngQGrpPlcrOvrStatMode     TmnxIngPolicerStatModeOverride,
    tFPNetIngQGrpPlcrOvrMBS          TPolicerBurstSizeBytesOverride,
    tFPNetIngQGrpPlcrOvrCBS          TPolicerBurstSizeBytesOverride,
    tFPNetIngQGrpPlcrOvrPktOffset    TPerPacketOffsetOvr
}

tFPNetIngQGrpPlcrOvrPolicerId    OBJECT-TYPE
    SYNTAX      TIngPolicerId
    MAX-ACCESS  not-accessible
    STATUS      current
    DESCRIPTION
        "The value of tFPNetIngQGrpPlcrOvrPolicerId specifies the index of the
         ingress QoS policer of this forwarding-plane queue group on network."
    ::= { tFPNetIngQGrpPlcrOvrEntry 1 }

tFPNetIngQGrpPlcrOvrRowStatus    OBJECT-TYPE
    SYNTAX      RowStatus
    MAX-ACCESS  read-create
    STATUS      current
    DESCRIPTION
        "The value of tFPNetIngQGrpPlcrOvrRowStatus specifies the Row Status of
         the entry.

         This tFPNetIngQGrpPlcrOvrRowStatus object allows creation/deletion of
         rows in this table."
    ::= { tFPNetIngQGrpPlcrOvrEntry 2 }

tFPNetIngQGrpPlcrOvrLastChgd     OBJECT-TYPE
    SYNTAX      TimeStamp
    MAX-ACCESS  read-only
    STATUS      current
    DESCRIPTION
        "The value of tFPNetIngQGrpPlcrOvrLastChgd indicates the timestamp of
         last change to this row in tFPNetIngQGrpPlcrOvrTable."
    ::= { tFPNetIngQGrpPlcrOvrEntry 3 }

tFPNetIngQGrpPlcrOvrAdminPIR     OBJECT-TYPE
    SYNTAX      THPolPIRRateOverride
    UNITS       "kilobps"
    MAX-ACCESS  read-create
    STATUS      current
    DESCRIPTION
        "The value of tFPNetIngQGrpPlcrOvrAdminPIR specifies the administrative
         PIR specified by the user."
    DEFVAL      { -2 }
    ::= { tFPNetIngQGrpPlcrOvrEntry 4 }

tFPNetIngQGrpPlcrOvrAdminCIR     OBJECT-TYPE
    SYNTAX      THPolCIRRateOverride
    UNITS       "kilobps"
    MAX-ACCESS  read-create
    STATUS      current
    DESCRIPTION
        "The value of tFPNetIngQGrpPlcrOvrAdminCIR specifies the administrative
         CIR specified by the user."
    DEFVAL      { -2 }
    ::= { tFPNetIngQGrpPlcrOvrEntry 5 }

tFPNetIngQGrpPlcrOvrStatMode     OBJECT-TYPE
    SYNTAX      TmnxIngPolicerStatModeOverride
    MAX-ACCESS  read-create
    STATUS      current
    DESCRIPTION
        "The value of tFPNetIngQGrpPlcrOvrStatMode specifies the mode of
         statistics collected by the policer on this forwarding-plane QoS
         ingress queue group."
    DEFVAL      { noOverride }
    ::= { tFPNetIngQGrpPlcrOvrEntry 6 }

tFPNetIngQGrpPlcrOvrMBS          OBJECT-TYPE
    SYNTAX      TPolicerBurstSizeBytesOverride
    UNITS       "bytes"
    MAX-ACCESS  read-create
    STATUS      current
    DESCRIPTION
        "The value of tFPNetIngQGrpPlcrOvrMBS specifies the maximum amount of
         buffer space (in bytes) allowed for the queue by the policer on this
         forwarding-plane QoS ingress queue group."
    DEFVAL      { -2 }
    ::= { tFPNetIngQGrpPlcrOvrEntry 7 }

tFPNetIngQGrpPlcrOvrCBS          OBJECT-TYPE
    SYNTAX      TPolicerBurstSizeBytesOverride
    UNITS       "bytes"
    MAX-ACCESS  read-create
    STATUS      current
    DESCRIPTION
        "The value of tFPNetIngQGrpPlcrOvrCBS specifies the amount of reserved
         buffer space (in bytes) set by the policer on this forwarding-plane
         QoS ingress queue group."
    DEFVAL      { -2 }
    ::= { tFPNetIngQGrpPlcrOvrEntry 8 }

tFPNetIngQGrpPlcrOvrPktOffset    OBJECT-TYPE
    SYNTAX      TPerPacketOffsetOvr
    UNITS       "bytes"
    MAX-ACCESS  read-create
    STATUS      current
    DESCRIPTION
        "The value of tFPNetIngQGrpPlcrOvrPktOffset specifies the packet byte
         offset for addition of policing information by the policer on this
         forwarding-plane QoS ingress queue group."
    DEFVAL      { -128 }
    ::= { tFPNetIngQGrpPlcrOvrEntry 9 }

tFPAccIngQGrpPCPOvrTblLastChgd   OBJECT-TYPE
    SYNTAX      TimeStamp
    MAX-ACCESS  read-only
    STATUS      current
    DESCRIPTION
        "tFPAccIngQGrpPCPOvrTblLastChgd indicates the timestamp of last change
         to the tFPAccIngQGrpPCPOvrTable."
    ::= { tmnxCardObjs 37 }

tFPAccIngQGrpPCPOvrTable         OBJECT-TYPE
    SYNTAX      SEQUENCE OF TFPAccIngQGrpPCPOvrEntry
    MAX-ACCESS  not-accessible
    STATUS      current
    DESCRIPTION
        "A table that contains forwarding plane ingress policer control
         override information."
    ::= { tmnxCardObjs 38 }

tFPAccIngQGrpPCPOvrEntry         OBJECT-TYPE
    SYNTAX      TFPAccIngQGrpPCPOvrEntry
    MAX-ACCESS  not-accessible
    STATUS      current
    DESCRIPTION
        "Policer control override information about a specific forwarding plane
         on the access ingress side."
    INDEX       {
        tmnxChassisIndex,
        tmnxCardSlotNum,
        tmnxFPNum,
        tmnxFPAccIngQGrpName,
        tmnxFPAccIngQGrpInstanceId
    }
    ::= { tFPAccIngQGrpPCPOvrTable 1 }

TFPAccIngQGrpPCPOvrEntry         ::= SEQUENCE
{
    tFPAccIngQGrpPCPOvrRowStatus     RowStatus,
    tFPAccIngQGrpPCPOvrLastChgd      TimeStamp,
    tFPAccIngQGrpPCPOvrMaxRate       THPolPIRRateOverride,
    tFPAccIngQGrpPCPOvrMinMBSSep     TPlcrBurstSizeBytesOverride
}

tFPAccIngQGrpPCPOvrRowStatus     OBJECT-TYPE
    SYNTAX      RowStatus
    MAX-ACCESS  read-create
    STATUS      current
    DESCRIPTION
        "This is the Row Status of the entry. This allows creation/deletion of
         rows in this table."
    ::= { tFPAccIngQGrpPCPOvrEntry 1 }

tFPAccIngQGrpPCPOvrLastChgd      OBJECT-TYPE
    SYNTAX      TimeStamp
    MAX-ACCESS  read-only
    STATUS      current
    DESCRIPTION
        "The value of tFPAccIngQGrpPCPOvrLastChgd indicates the timestamp of
         last change to this row in tFPAccIngQGrpPCPOvrTable."
    ::= { tFPAccIngQGrpPCPOvrEntry 2 }

tFPAccIngQGrpPCPOvrMaxRate       OBJECT-TYPE
    SYNTAX      THPolPIRRateOverride
    UNITS       "kilobps"
    MAX-ACCESS  read-create
    STATUS      current
    DESCRIPTION
        "The value of tFPAccIngQGrpPCPOvrMaxRate specifies the maximum frame
         based bandwidth limit of this policer override."
    DEFVAL      { -2 }
    ::= { tFPAccIngQGrpPCPOvrEntry 3 }

tFPAccIngQGrpPCPOvrMinMBSSep     OBJECT-TYPE
    SYNTAX      TPlcrBurstSizeBytesOverride
    UNITS       "bytes"
    MAX-ACCESS  read-create
    STATUS      current
    DESCRIPTION
        "The value of tFPAccIngQGrpPCPOvrMinMBSSep specifies the minimum amount
         of separation buffer space (in bytes) allowed by this policer
         override."
    DEFVAL      { -2 }
    ::= { tFPAccIngQGrpPCPOvrEntry 4 }

tFPAccIngQGrpPCPOvrLvlTblLstChgd OBJECT-TYPE
    SYNTAX      TimeStamp
    MAX-ACCESS  read-only
    STATUS      current
    DESCRIPTION
        "tFPAccIngQGrpPCPOvrLvlTblLstChgd indicates the timestamp of last
         change to the tFPAccIngQGrpPCPOvrLvlTable."
    ::= { tmnxCardObjs 39 }

tFPAccIngQGrpPCPOvrLvlTable      OBJECT-TYPE
    SYNTAX      SEQUENCE OF TFPAccIngQGrpPCPOvrLvlEntry
    MAX-ACCESS  not-accessible
    STATUS      current
    DESCRIPTION
        "A table that contains forwarding plane access ingress policer control
         override information for the priority level."
    ::= { tmnxCardObjs 40 }

tFPAccIngQGrpPCPOvrLvlEntry      OBJECT-TYPE
    SYNTAX      TFPAccIngQGrpPCPOvrLvlEntry
    MAX-ACCESS  not-accessible
    STATUS      current
    DESCRIPTION
        "Policer control priority level override information about a specific
         forwarding plane on the access ingress side.

         Entries are created/deleted automatically by the system when entries
         are created/delete in the tFPAccIngQGrpPCPOvrTable."
    INDEX       {
        tmnxChassisIndex,
        tmnxCardSlotNum,
        tmnxFPNum,
        tmnxFPAccIngQGrpName,
        tmnxFPAccIngQGrpInstanceId,
        tFPAccIngQGrpPCPOvrLvl
    }
    ::= { tFPAccIngQGrpPCPOvrLvlTable 1 }

TFPAccIngQGrpPCPOvrLvlEntry      ::= SEQUENCE
{
    tFPAccIngQGrpPCPOvrLvl           TLevel,
    tFPAccIngQGrpPCPOvrLvlLastChgd   TimeStamp,
    tFPAccIngQGrpPCPOvrLvlMBS        TPlcrBurstSizeBytesOverride
}

tFPAccIngQGrpPCPOvrLvl           OBJECT-TYPE
    SYNTAX      TLevel
    MAX-ACCESS  not-accessible
    STATUS      current
    DESCRIPTION
        "The value of tFPAccIngQGrpPCPOvrLvl identifies the level of the
         policer control policy defined by tQosPolicerCtrlPolName."
    ::= { tFPAccIngQGrpPCPOvrLvlEntry 1 }

tFPAccIngQGrpPCPOvrLvlLastChgd   OBJECT-TYPE
    SYNTAX      TimeStamp
    MAX-ACCESS  read-only
    STATUS      current
    DESCRIPTION
        "The value of tFPAccIngQGrpPCPOvrLvlLastChgd indicates the timestamp of
         last change to this row in tFPAccIngQGrpPCPOvrLvlTable."
    ::= { tFPAccIngQGrpPCPOvrLvlEntry 2 }

tFPAccIngQGrpPCPOvrLvlMBS        OBJECT-TYPE
    SYNTAX      TPlcrBurstSizeBytesOverride
    UNITS       "bytes"
    MAX-ACCESS  read-create
    STATUS      current
    DESCRIPTION
        "The value of tFPAccIngQGrpPCPOvrLvlMBS specifies the maximum amount of
         cumulative buffer space (in bytes) allowed for this level by the
         policer of this level."
    DEFVAL      { -2 }
    ::= { tFPAccIngQGrpPCPOvrLvlEntry 3 }

tFPNetIngQGrpPCPOvrTblLastChgd   OBJECT-TYPE
    SYNTAX      TimeStamp
    MAX-ACCESS  read-only
    STATUS      current
    DESCRIPTION
        "tFPNetIngQGrpPCPOvrTblLastChgd indicates the timestamp of last change
         to the tFPNetIngQGrpPCPOvrTable."
    ::= { tmnxCardObjs 41 }

tFPNetIngQGrpPCPOvrTable         OBJECT-TYPE
    SYNTAX      SEQUENCE OF TFPNetIngQGrpPCPOvrEntry
    MAX-ACCESS  not-accessible
    STATUS      current
    DESCRIPTION
        "A table that contains forwarding plane ingress policer control
         override information."
    ::= { tmnxCardObjs 42 }

tFPNetIngQGrpPCPOvrEntry         OBJECT-TYPE
    SYNTAX      TFPNetIngQGrpPCPOvrEntry
    MAX-ACCESS  not-accessible
    STATUS      current
    DESCRIPTION
        "Policer control override information about a specific forwarding plane
         on the access ingress side."
    INDEX       {
        tmnxChassisIndex,
        tmnxCardSlotNum,
        tmnxFPNum,
        tmnxFPNetIngQGrpName,
        tmnxFPNetIngQGrpInstanceId
    }
    ::= { tFPNetIngQGrpPCPOvrTable 1 }

TFPNetIngQGrpPCPOvrEntry         ::= SEQUENCE
{
    tFPNetIngQGrpPCPOvrRowStatus     RowStatus,
    tFPNetIngQGrpPCPOvrLastChgd      TimeStamp,
    tFPNetIngQGrpPCPOvrMaxRate       THPolPIRRateOverride,
    tFPNetIngQGrpPCPOvrMinMBSSep     TPlcrBurstSizeBytesOverride
}

tFPNetIngQGrpPCPOvrRowStatus     OBJECT-TYPE
    SYNTAX      RowStatus
    MAX-ACCESS  read-create
    STATUS      current
    DESCRIPTION
        "This is the Row Status of the entry. This allows creation/deletion of
         rows in this table."
    ::= { tFPNetIngQGrpPCPOvrEntry 1 }

tFPNetIngQGrpPCPOvrLastChgd      OBJECT-TYPE
    SYNTAX      TimeStamp
    MAX-ACCESS  read-only
    STATUS      current
    DESCRIPTION
        "The value of tFPNetIngQGrpPCPOvrLastChgd indicates the timestamp of
         last change to this row in tFPNetIngQGrpPCPOvrTable."
    ::= { tFPNetIngQGrpPCPOvrEntry 2 }

tFPNetIngQGrpPCPOvrMaxRate       OBJECT-TYPE
    SYNTAX      THPolPIRRateOverride
    UNITS       "kilobps"
    MAX-ACCESS  read-create
    STATUS      current
    DESCRIPTION
        "The value of tFPNetIngQGrpPCPOvrMaxRate specifies the maximum frame
         based bandwidth limit of this policer override."
    DEFVAL      { -2 }
    ::= { tFPNetIngQGrpPCPOvrEntry 3 }

tFPNetIngQGrpPCPOvrMinMBSSep     OBJECT-TYPE
    SYNTAX      TPlcrBurstSizeBytesOverride
    UNITS       "bytes"
    MAX-ACCESS  read-create
    STATUS      current
    DESCRIPTION
        "The value of tFPNetIngQGrpPCPOvrMinMBSSep specifies the minimum amount
         of separation buffer space (in bytes) allowed by this policer
         override."
    DEFVAL      { -2 }
    ::= { tFPNetIngQGrpPCPOvrEntry 4 }

tFPNetIngQGrpPCPOvrLvlTblLstChgd OBJECT-TYPE
    SYNTAX      TimeStamp
    MAX-ACCESS  read-only
    STATUS      current
    DESCRIPTION
        "tFPNetIngQGrpPCPOvrLvlTblLstChgd indicates the timestamp of last
         change to the tFPNetIngQGrpPCPOvrLvlTable."
    ::= { tmnxCardObjs 43 }

tFPNetIngQGrpPCPOvrLvlTable      OBJECT-TYPE
    SYNTAX      SEQUENCE OF TFPNetIngQGrpPCPOvrLvlEntry
    MAX-ACCESS  not-accessible
    STATUS      current
    DESCRIPTION
        "A table that contains forwarding plane network ingress policer control
         override information for the priority level."
    ::= { tmnxCardObjs 44 }

tFPNetIngQGrpPCPOvrLvlEntry      OBJECT-TYPE
    SYNTAX      TFPNetIngQGrpPCPOvrLvlEntry
    MAX-ACCESS  not-accessible
    STATUS      current
    DESCRIPTION
        "Policer control priority level override information about a specific
         forwarding plane on the network ingress side.

         Entries are created/deleted automatically by the system when entries
         are created/delete in the tFPNetIngQGrpPCPOvrTable."
    INDEX       {
        tmnxChassisIndex,
        tmnxCardSlotNum,
        tmnxFPNum,
        tmnxFPNetIngQGrpName,
        tmnxFPNetIngQGrpInstanceId,
        tFPNetIngQGrpPCPOvrLvl
    }
    ::= { tFPNetIngQGrpPCPOvrLvlTable 1 }

TFPNetIngQGrpPCPOvrLvlEntry      ::= SEQUENCE
{
    tFPNetIngQGrpPCPOvrLvl           TLevel,
    tFPNetIngQGrpPCPOvrLvlLastChgd   TimeStamp,
    tFPNetIngQGrpPCPOvrLvlMBS        TPlcrBurstSizeBytesOverride
}

tFPNetIngQGrpPCPOvrLvl           OBJECT-TYPE
    SYNTAX      TLevel
    MAX-ACCESS  not-accessible
    STATUS      current
    DESCRIPTION
        "The value of tFPNetIngQGrpPCPOvrLvl identifies the level of the
         policer control policy defined by tQosPolicerCtrlPolName."
    ::= { tFPNetIngQGrpPCPOvrLvlEntry 1 }

tFPNetIngQGrpPCPOvrLvlLastChgd   OBJECT-TYPE
    SYNTAX      TimeStamp
    MAX-ACCESS  read-only
    STATUS      current
    DESCRIPTION
        "The value of tFPNetIngQGrpPCPOvrLvlLastChgd indicates the timestamp of
         last change to this row in tFPNetIngQGrpPCPOvrLvlTable."
    ::= { tFPNetIngQGrpPCPOvrLvlEntry 2 }

tFPNetIngQGrpPCPOvrLvlMBS        OBJECT-TYPE
    SYNTAX      TPlcrBurstSizeBytesOverride
    UNITS       "bytes"
    MAX-ACCESS  read-create
    STATUS      current
    DESCRIPTION
        "The value of tFPNetIngQGrpPCPOvrLvlMBS specifies the maximum amount of
         cumulative buffer space (in bytes) allowed for this level by the
         policer of this level."
    DEFVAL      { -2 }
    ::= { tFPNetIngQGrpPCPOvrLvlEntry 3 }

tCardResTable                    OBJECT-TYPE
    SYNTAX      SEQUENCE OF TCardResEntry
    MAX-ACCESS  not-accessible
    STATUS      current
    DESCRIPTION
        "The value of tCardResTable represents system resource information that
         are specific to a particular card on a given chassis."
    ::= { tmnxCardObjs 45 }

tCardResEntry                    OBJECT-TYPE
    SYNTAX      TCardResEntry
    MAX-ACCESS  not-accessible
    STATUS      current
    DESCRIPTION
        "The value of tCardResEntry represents card specific system resource
         information."
    INDEX       {
        tmnxChassisIndex,
        tmnxCardSlotNum
    }
    ::= { tCardResTable 1 }

TCardResEntry                    ::= SEQUENCE
{
    tCardResQosUserSchedsTotal       Unsigned32,
    tCardResQosUserSchedsAlloc       Unsigned32,
    tCardResQosIntSchedsTotal        Unsigned32,
    tCardResQosIntSchedsAlloc        Unsigned32,
    tCardResSubSPIQosOvrTotal        Unsigned32,
    tCardResSubSPIQosOvrAlloc        Unsigned32,
    tCardResPortAccEgrQGrpInstTotal  Unsigned32,
    tCardResPortAccEgrQGrpInstAlloc  Unsigned32,
    tCardResPortNetEgrQGrpInstTotal  Unsigned32,
    tCardResPortNetEgrQGrpInstAlloc  Unsigned32,
    tCardResPortEgrQGrpInstTotal     Unsigned32,
    tCardResPortEgrQGrpInstAlloc     Unsigned32,
    tCardResFPIngQGrpInstTotal       Unsigned32,
    tCardResFPIngQGrpInstAlloc       Unsigned32,
    tCardResPortEgrVPortTotal        Unsigned32,
    tCardResPortEgrVPortAlloc        Unsigned32,
    tCardResQosUserSchedOvrsTotal    Unsigned32,
    tCardResQosUserSchedOvrsAlloc    Unsigned32,
    tCardResCategoryEntriesTotal     Unsigned32,
    tCardResCategoryEntriesAlloc     Unsigned32,
    tCardResIntArbiterTotal          Unsigned32,
    tCardResIntArbiterAlloc          Unsigned32,
    tCardResIntArbiterOvrsTotal      Unsigned32,
    tCardResIntArbiterOvrsAlloc      Unsigned32,
    tCardResSLAProfileInstanceTotal  Unsigned32,
    tCardResSLAProfileInstanceAlloc  Unsigned32,
    tCardResEncapGrpMemberTotal      Unsigned32,
    tCardResEncapGrpMemberAlloc      Unsigned32,
    tCardResSapInstanceTotal         Unsigned32,
    tCardResSapInstanceAlloc         Unsigned32,
    tCardResNonEpipeSapInstanceTotal Unsigned32,
    tCardResNonEpipeSapInstanceAlloc Unsigned32,
    tCardResApipeSapInstanceTotal    Unsigned32,
    tCardResApipeSapInstanceAlloc    Unsigned32,
    tCardResCpipeSapInstanceTotal    Unsigned32,
    tCardResCpipeSapInstanceAlloc    Unsigned32,
    tCardResEpipeSapInstanceTotal    Unsigned32,
    tCardResEpipeSapInstanceAlloc    Unsigned32,
    tCardResFpipeSapInstanceTotal    Unsigned32,
    tCardResFpipeSapInstanceAlloc    Unsigned32,
    tCardResIpipeSapInstanceTotal    Unsigned32,
    tCardResIpipeSapInstanceAlloc    Unsigned32,
    tCardResIesSapInstanceTotal      Unsigned32,
    tCardResIesSapInstanceAlloc      Unsigned32,
    tCardResMirrorSapInstanceTotal   Unsigned32,
    tCardResMirrorSapInstanceAlloc   Unsigned32,
    tCardResVplsSapInstanceTotal     Unsigned32,
    tCardResVplsSapInstanceAlloc     Unsigned32,
    tCardResVprnSapInstanceTotal     Unsigned32,
    tCardResVprnSapInstanceAlloc     Unsigned32,
    tCardResTLSMcastEntriesAlloc     Unsigned32,
    tCardResTLSMcastEntriesTotal     Unsigned32
}

tCardResQosUserSchedsTotal       OBJECT-TYPE
    SYNTAX      Unsigned32
    MAX-ACCESS  read-only
    STATUS      current
    DESCRIPTION
        "The value of tCardResQosUserSchedsTotal represents the total amount of
         QoS user virtual schedulers that are supported on this card.

         When the value of tCardResQosUserSchedsTotal is zero, it indicates
         that this resource type is not supported on this card."
    ::= { tCardResEntry 1 }

tCardResQosUserSchedsAlloc       OBJECT-TYPE
    SYNTAX      Unsigned32
    MAX-ACCESS  read-only
    STATUS      current
    DESCRIPTION
        "The value of tCardResQosUserSchedsAlloc represents the total number of
         QoS user virtual schedulers that are currently allocated on this card."
    ::= { tCardResEntry 2 }

tCardResQosIntSchedsTotal        OBJECT-TYPE
    SYNTAX      Unsigned32
    MAX-ACCESS  read-only
    STATUS      obsolete
    DESCRIPTION
        "The value of tCardResQosIntSchedsTotal represents the total number of
         QoS internal virtual schedulers that are supported on this card.

         When the value of tCardResQosIntSchedsTotal is zero, it indicates that
         this resource type is not supported on this card.

         This objects is obsoleted in 13.0 release."
    ::= { tCardResEntry 3 }

tCardResQosIntSchedsAlloc        OBJECT-TYPE
    SYNTAX      Unsigned32
    MAX-ACCESS  read-only
    STATUS      obsolete
    DESCRIPTION
        "The value of tCardResQosIntSchedsAlloc represents the total number of
         QoS internal virtual schedulers that are currently allocated on this
         card.

         This objects is obsoleted in 13.0 release."
    ::= { tCardResEntry 4 }

tCardResSubSPIQosOvrTotal        OBJECT-TYPE
    SYNTAX      Unsigned32
    MAX-ACCESS  read-only
    STATUS      current
    DESCRIPTION
        "The value of tCardResSubSPIQosOvrTotal represents the total number of
         QoS subscriber sla-profile instance overrides that are supported on
         this card.

         When the value of tCardResSubSPIQosOvrTotal is zero, it indicates that
         this resource type is not supported on this card."
    ::= { tCardResEntry 5 }

tCardResSubSPIQosOvrAlloc        OBJECT-TYPE
    SYNTAX      Unsigned32
    MAX-ACCESS  read-only
    STATUS      current
    DESCRIPTION
        "The value of tCardResSubSPIQosOvrAlloc represents the total number of
         QoS subscriber sla-profile instance overrides that are currently
         allocated on this card."
    ::= { tCardResEntry 6 }

tCardResPortAccEgrQGrpInstTotal  OBJECT-TYPE
    SYNTAX      Unsigned32
    MAX-ACCESS  read-only
    STATUS      current
    DESCRIPTION
        "The value of tCardResPortAccEgrQGrpInstTotal represents the total
         number of port access egress queue-group instances across all ports on
         this card that are allowed to be provisioned.

         When the value of tCardResPortAccEgrQGrpInstTotal is zero, it
         indicates that this resource type is not supported on this card."
    ::= { tCardResEntry 9 }

tCardResPortAccEgrQGrpInstAlloc  OBJECT-TYPE
    SYNTAX      Unsigned32
    MAX-ACCESS  read-only
    STATUS      current
    DESCRIPTION
        "The value of tCardResPortAccEgrQGrpInstAlloc represents the total
         number of port access egress queue-group instances across all ports on
         this card that are currently provisioned."
    ::= { tCardResEntry 10 }

tCardResPortNetEgrQGrpInstTotal  OBJECT-TYPE
    SYNTAX      Unsigned32
    MAX-ACCESS  read-only
    STATUS      current
    DESCRIPTION
        "The value of tCardResPortNetEgrQGrpInstTotal represents the total
         number of port network egress queue-group instances across all ports
         on this card that are allowed to be provisioned.

         When the value of tCardResPortNetEgrQGrpInstTotal is zero, it
         indicates that this resource type is not supported on this card."
    ::= { tCardResEntry 11 }

tCardResPortNetEgrQGrpInstAlloc  OBJECT-TYPE
    SYNTAX      Unsigned32
    MAX-ACCESS  read-only
    STATUS      current
    DESCRIPTION
        "The value of tCardResPortNetEgrQGrpInstAlloc represents the total
         number of port network egress queue-group instances across all ports
         on this card that are currently provisioned."
    ::= { tCardResEntry 12 }

tCardResPortEgrQGrpInstTotal     OBJECT-TYPE
    SYNTAX      Unsigned32
    MAX-ACCESS  read-only
    STATUS      current
    DESCRIPTION
        "The value of tCardResPortEgrQGrpInstTotal represents the total number
         of port egress queue-group instances across all ports on this card
         including access and network instances that are allowed to be
         provisioned.

         When the value of tCardResPortEgrQGrpInstTotal is zero, it indicates
         that this resource type is not supported on this card."
    ::= { tCardResEntry 13 }

tCardResPortEgrQGrpInstAlloc     OBJECT-TYPE
    SYNTAX      Unsigned32
    MAX-ACCESS  read-only
    STATUS      current
    DESCRIPTION
        "The value of tCardResPortEgrQGrpInstAlloc represents the total number
         of port egress queue-group instances across all ports on this card
         including access and network instances that are currently provisioned."
    ::= { tCardResEntry 14 }

tCardResFPIngQGrpInstTotal       OBJECT-TYPE
    SYNTAX      Unsigned32
    MAX-ACCESS  read-only
    STATUS      current
    DESCRIPTION
        "The value of tCardResFPIngQGrpInstTotal represents the total number of
         forwarding-plane (FP) ingress queue-group instances across all FP on
         this card including access and network instances that are allowed to
         be provisioned.

         When the value of tCardResFPIngQGrpInstTotal is zero, it indicates
         that this resource type is not supported on this card."
    ::= { tCardResEntry 15 }

tCardResFPIngQGrpInstAlloc       OBJECT-TYPE
    SYNTAX      Unsigned32
    MAX-ACCESS  read-only
    STATUS      current
    DESCRIPTION
        "The value of tCardResFPIngQGrpInstAlloc represents the total number of
         forwarding-plane (FP) ingress queue-group instances across all FP on
         this card including access and network instances that are currently
         provisioned."
    ::= { tCardResEntry 16 }

tCardResPortEgrVPortTotal        OBJECT-TYPE
    SYNTAX      Unsigned32
    MAX-ACCESS  read-only
    STATUS      current
    DESCRIPTION
        "The value of tCardResPortEgrVPortTotal represents the total number of
         egress virtual ports across all ports on this card that are allowed to
         be provisioned.

         When the value of tCardResPortEgrVPortTotal is zero, it indicates that
         this resource type is not supported on this card."
    ::= { tCardResEntry 17 }

tCardResPortEgrVPortAlloc        OBJECT-TYPE
    SYNTAX      Unsigned32
    MAX-ACCESS  read-only
    STATUS      current
    DESCRIPTION
        "The value of tCardResPortEgrVPortAlloc represents the total number of
         egress virtual ports across all ports on this card that are currently
         provisioned."
    ::= { tCardResEntry 18 }

tCardResQosUserSchedOvrsTotal    OBJECT-TYPE
    SYNTAX      Unsigned32
    MAX-ACCESS  read-only
    STATUS      current
    DESCRIPTION
        "The value of tCardResQosUserSchedOvrsTotal represents the total amount
         of QoS user virtual scheduler overrides that are supported on this
         card.

         When the value of tCardResQosUserSchedOvrsTotal is zero, it indicates
         that this resource type is not supported on this card."
    ::= { tCardResEntry 19 }

tCardResQosUserSchedOvrsAlloc    OBJECT-TYPE
    SYNTAX      Unsigned32
    MAX-ACCESS  read-only
    STATUS      current
    DESCRIPTION
        "The value of tCardResQosUserSchedOvrsAlloc represents the total number
         of QoS user virtual scheduler overrides that are currently allocated
         on this card."
    ::= { tCardResEntry 20 }

tCardResCategoryEntriesTotal     OBJECT-TYPE
    SYNTAX      Unsigned32
    MAX-ACCESS  read-only
    STATUS      current
    DESCRIPTION
        "The value of tCardResCategoryEntriesTotal indicates the total number
         of subscriber category entries currently associated with this card."
    ::= { tCardResEntry 21 }

tCardResCategoryEntriesAlloc     OBJECT-TYPE
    SYNTAX      Unsigned32
    MAX-ACCESS  read-only
    STATUS      current
    DESCRIPTION
        "The value of tCardResCategoryEntriesAlloc indicates the total number
         of subscriber category entries that are currently allocated on this
         card."
    ::= { tCardResEntry 22 }

tCardResIntArbiterTotal          OBJECT-TYPE
    SYNTAX      Unsigned32
    MAX-ACCESS  read-only
    STATUS      current
    DESCRIPTION
        "The value of tCardResIntArbiterTotal represents the total number of
         intermediate arbiters that are supported on this card.

         When the value of tCardResIntArbiterTotal is zero, it indicates that
         this resource type is not supported on this card."
    ::= { tCardResEntry 23 }

tCardResIntArbiterAlloc          OBJECT-TYPE
    SYNTAX      Unsigned32
    MAX-ACCESS  read-only
    STATUS      current
    DESCRIPTION
        "The value of tCardResIntArbiterAlloc represents the total number of
         intermediate arbiters that are currently allocated on this card."
    ::= { tCardResEntry 24 }

tCardResIntArbiterOvrsTotal      OBJECT-TYPE
    SYNTAX      Unsigned32
    MAX-ACCESS  read-only
    STATUS      current
    DESCRIPTION
        "The value of tCardResIntArbiterOvrsTotal represents the total number
         of intermediate arbiter overrides that are supported on this card.

         When the value of tCardResIntArbiterOvrsTotal  is zero, it indicates that
         this resource type is not supported on this card."
    ::= { tCardResEntry 25 }

tCardResIntArbiterOvrsAlloc      OBJECT-TYPE
    SYNTAX      Unsigned32
    MAX-ACCESS  read-only
    STATUS      current
    DESCRIPTION
        "The value of tCardResIntArbiterOvrsAlloc  represents the total number of
         intermediate arbiter overrides that are currently allocated on this card."
    ::= { tCardResEntry 26 }

tCardResSLAProfileInstanceTotal  OBJECT-TYPE
    SYNTAX      Unsigned32
    MAX-ACCESS  read-only
    STATUS      current
    DESCRIPTION
        "The value of tCardResSLAProfileInstanceTotal represents the total
         number of subscriber SLA profile instances that are supported on this
         card.

         When the value of tCardResSLAProfileInstanceTotal is zero, it
         indicates that this resource type is not supported on this card."
    ::= { tCardResEntry 27 }

tCardResSLAProfileInstanceAlloc  OBJECT-TYPE
    SYNTAX      Unsigned32
    MAX-ACCESS  read-only
    STATUS      current
    DESCRIPTION
        "The value of tCardResSLAProfileInstanceAlloc represents the total
         number of subscriber SLA profile instances that are currently
         allocated on this card."
    ::= { tCardResEntry 28 }

tCardResEncapGrpMemberTotal      OBJECT-TYPE
    SYNTAX      Unsigned32
    MAX-ACCESS  read-only
    STATUS      current
    DESCRIPTION
        "The value of tCardResEncapGrpMemberTotal represents the total number
         of encap group members that are supported on this card.

         When the value of tCardResEncapGrpMemberTotal is zero, it indicates
         that this resource type is not supported on this card."
    ::= { tCardResEntry 29 }

tCardResEncapGrpMemberAlloc      OBJECT-TYPE
    SYNTAX      Unsigned32
    MAX-ACCESS  read-only
    STATUS      current
    DESCRIPTION
        "The value of tCardResEncapGrpMemberAlloc represents the total number
         of encap group members that are currently allocated on this card."
    ::= { tCardResEntry 30 }

tCardResSapInstanceTotal         OBJECT-TYPE
    SYNTAX      Unsigned32
    MAX-ACCESS  read-only
    STATUS      current
    DESCRIPTION
        "The value of tCardResSapInstanceTotal represents the total number of
         SAP instances that are supported on this card.

         When the value of tCardResSapInstanceTotal is zero, it indicates that
         this resource type is not supported on this card."
    ::= { tCardResEntry 31 }

tCardResSapInstanceAlloc         OBJECT-TYPE
    SYNTAX      Unsigned32
    MAX-ACCESS  read-only
    STATUS      current
    DESCRIPTION
        "The value of tCardResSapInstanceAlloc represents the total number of
         SAP instances that are currently allocated on this card."
    ::= { tCardResEntry 32 }

tCardResNonEpipeSapInstanceTotal OBJECT-TYPE
    SYNTAX      Unsigned32
    MAX-ACCESS  read-only
    STATUS      current
    DESCRIPTION
        "The value of tCardResNonEpipeSapInstanceTotal represents the total
         number of non-Epipe SAP instances that are supported on this card.

         When the value of tCardResNonEpipeSapInstanceTotal is zero, it
         indicates that this resource type is not supported on this card."
    ::= { tCardResEntry 33 }

tCardResNonEpipeSapInstanceAlloc OBJECT-TYPE
    SYNTAX      Unsigned32
    MAX-ACCESS  read-only
    STATUS      current
    DESCRIPTION
        "The value of tCardResNonEpipeSapInstanceAlloc represents the total
         number of non-Epipe SAP instances that are currently allocated on this
         card."
    ::= { tCardResEntry 34 }

tCardResApipeSapInstanceTotal    OBJECT-TYPE
    SYNTAX      Unsigned32
    MAX-ACCESS  read-only
    STATUS      current
    DESCRIPTION
        "The value of tCardResApipeSapInstanceTotal represents the total number
         of  Apipe SAP instances that are supported on this card.

         When the value of tCardResApipeSapInstanceTotal is zero, it indicates
         that  this resource type is not supported on this card."
    ::= { tCardResEntry 35 }

tCardResApipeSapInstanceAlloc    OBJECT-TYPE
    SYNTAX      Unsigned32
    MAX-ACCESS  read-only
    STATUS      current
    DESCRIPTION
        "The value of tCardResApipeSapInstanceAlloc represents the total number
         of Apipe SAP instances that are currently allocated on this card."
    ::= { tCardResEntry 36 }

tCardResCpipeSapInstanceTotal    OBJECT-TYPE
    SYNTAX      Unsigned32
    MAX-ACCESS  read-only
    STATUS      current
    DESCRIPTION
        "The value of tCardResCpipeSapInstanceTotal represents the total number
         of  Cpipe SAP instances that are supported on this card.

         When the value of tCardResCpipeSapInstanceTotal is zero, it indicates
         that  this resource type is not supported on this card."
    ::= { tCardResEntry 37 }

tCardResCpipeSapInstanceAlloc    OBJECT-TYPE
    SYNTAX      Unsigned32
    MAX-ACCESS  read-only
    STATUS      current
    DESCRIPTION
        "The value of tCardResCpipeSapInstanceAlloc represents the total number
         of Cpipe SAP instances that are currently allocated on this card."
    ::= { tCardResEntry 38 }

tCardResEpipeSapInstanceTotal    OBJECT-TYPE
    SYNTAX      Unsigned32
    MAX-ACCESS  read-only
    STATUS      current
    DESCRIPTION
        "The value of tCardResEpipeSapInstanceTotal represents the total number
         of Epipe SAP instances that are supported on this card.

         When the value of tCardResEpipeSapInstanceTotal is zero, it indicates
         that this resource type is not supported on this card."
    ::= { tCardResEntry 39 }

tCardResEpipeSapInstanceAlloc    OBJECT-TYPE
    SYNTAX      Unsigned32
    MAX-ACCESS  read-only
    STATUS      current
    DESCRIPTION
        "The value of tCardResEpipeSapInstanceAlloc represents the total number
         of Epipe SAP instances that are currently allocated on this card."
    ::= { tCardResEntry 40 }

tCardResFpipeSapInstanceTotal    OBJECT-TYPE
    SYNTAX      Unsigned32
    MAX-ACCESS  read-only
    STATUS      current
    DESCRIPTION
        "The value of tCardResFpipeSapInstanceTotal represents the total number
         of  Fpipe SAP instances that are supported on this card.

         When the value of tCardResFpipeSapInstanceTotal is zero, it indicates
         that this resource type is not supported on this card."
    ::= { tCardResEntry 41 }

tCardResFpipeSapInstanceAlloc    OBJECT-TYPE
    SYNTAX      Unsigned32
    MAX-ACCESS  read-only
    STATUS      current
    DESCRIPTION
        "The value of tCardResFpipeSapInstanceAlloc represents the total number
         of Fpipe SAP instances that are currently allocated on this card."
    ::= { tCardResEntry 42 }

tCardResIpipeSapInstanceTotal    OBJECT-TYPE
    SYNTAX      Unsigned32
    MAX-ACCESS  read-only
    STATUS      current
    DESCRIPTION
        "The value of tCardResIpipeSapInstanceTotal represents the total number
         of Ipipe SAP instances that are supported on this card.

         When the value of tCardResIpipeSapInstanceTotal is zero, it indicates
         that this resource type is not supported on this card."
    ::= { tCardResEntry 43 }

tCardResIpipeSapInstanceAlloc    OBJECT-TYPE
    SYNTAX      Unsigned32
    MAX-ACCESS  read-only
    STATUS      current
    DESCRIPTION
        "The value of tCardResIpipeSapInstanceAlloc represents the total number
         of Ipipe SAP instances that are currently allocated on this card."
    ::= { tCardResEntry 44 }

tCardResIesSapInstanceTotal      OBJECT-TYPE
    SYNTAX      Unsigned32
    MAX-ACCESS  read-only
    STATUS      current
    DESCRIPTION
        "The value of tCardResIesSapInstanceTotal represents the total number
         of Ies SAP instances that are supported on this card.

         When the value of tCardResIesSapInstanceTotal is zero, it indicates
         that this resource type is not supported on this card."
    ::= { tCardResEntry 45 }

tCardResIesSapInstanceAlloc      OBJECT-TYPE
    SYNTAX      Unsigned32
    MAX-ACCESS  read-only
    STATUS      current
    DESCRIPTION
        "The value of tCardResIesSapInstanceAlloc represents the total number
         of Ies  SAP instances that are currently allocated on this card."
    ::= { tCardResEntry 46 }

tCardResMirrorSapInstanceTotal   OBJECT-TYPE
    SYNTAX      Unsigned32
    MAX-ACCESS  read-only
    STATUS      current
    DESCRIPTION
        "The value of tCardResMirrorSapInstanceTotal represents the total
         number of Mirror SAP instances that are supported on this card.

         When the value of tCardResMirrorSapInstanceTotal is zero, it indicates
         that this resource type is not supported on this card."
    ::= { tCardResEntry 47 }

tCardResMirrorSapInstanceAlloc   OBJECT-TYPE
    SYNTAX      Unsigned32
    MAX-ACCESS  read-only
    STATUS      current
    DESCRIPTION
        "The value of tCardResMirrorSapInstanceAlloc represents the total
         number of Mirror SAP instances that are currently allocated on this
         card."
    ::= { tCardResEntry 48 }

tCardResVplsSapInstanceTotal     OBJECT-TYPE
    SYNTAX      Unsigned32
    MAX-ACCESS  read-only
    STATUS      current
    DESCRIPTION
        "The value of tCardResVplsSapInstanceTotal represents the total number
         of Vpls SAP instances that are supported on this card.

         When the value of tCardResVplsSapInstanceTotal is zero, it indicates
         that this resource type is not supported on this card."
    ::= { tCardResEntry 49 }

tCardResVplsSapInstanceAlloc     OBJECT-TYPE
    SYNTAX      Unsigned32
    MAX-ACCESS  read-only
    STATUS      current
    DESCRIPTION
        "The value of tCardResVplsSapInstanceAlloc represents the total number
         of Vpls SAP  instances that are currently allocated on this card."
    ::= { tCardResEntry 50 }

tCardResVprnSapInstanceTotal     OBJECT-TYPE
    SYNTAX      Unsigned32
    MAX-ACCESS  read-only
    STATUS      current
    DESCRIPTION
        "The value of tCardResVprnSapInstanceTotal represents the total number
         of Vprn SAP instances that are supported on this card.

         When the value of tCardResVprnSapInstanceTotal is zero, it indicates
         that this resource type is not supported on this card."
    ::= { tCardResEntry 51 }

tCardResVprnSapInstanceAlloc     OBJECT-TYPE
    SYNTAX      Unsigned32
    MAX-ACCESS  read-only
    STATUS      current
    DESCRIPTION
        "The value of tCardResVprnSapInstanceAlloc represents the total number
         of Vprn SAP instances that are currently allocated on this card."
    ::= { tCardResEntry 52 }

tCardResTLSMcastEntriesAlloc     OBJECT-TYPE
    SYNTAX      Unsigned32
    MAX-ACCESS  read-only
    STATUS      current
    DESCRIPTION
        "The value of tCardResTLSMcastEntriesAlloc indicates the  total number
         of Egress TLS Mcast Entry resources that are  currently allocated on
         this Chassis."
    ::= { tCardResEntry 53 }

tCardResTLSMcastEntriesTotal     OBJECT-TYPE
    SYNTAX      Unsigned32
    MAX-ACCESS  read-only
    STATUS      current
    DESCRIPTION
        "The value of tCardResTLSMcastEntriesTotal indicates the total number
         of Egress TLS Mcast Entry resources on this Chassis."
    ::= { tCardResEntry 54 }

tFPResTable                      OBJECT-TYPE
    SYNTAX      SEQUENCE OF TFPResEntry
    MAX-ACCESS  not-accessible
    STATUS      current
    DESCRIPTION
        "The value of tFPResTable represents system resource information that
         are specific to forwarding plane (FP) for a particular card on a given
         chassis."
    ::= { tmnxCardObjs 46 }

tFPResEntry                      OBJECT-TYPE
    SYNTAX      TFPResEntry
    MAX-ACCESS  not-accessible
    STATUS      current
    DESCRIPTION
        "The value of tFPResEntry represents forwarding plane (FP) specific
         system resource information."
    INDEX       {
        tmnxChassisIndex,
        tmnxCardSlotNum,
        tmnxFPNum
    }
    ::= { tFPResTable 1 }

TFPResEntry                      ::= SEQUENCE
{
    tFPResSapIngQosPolTotal          Unsigned32,
    tFPResSapIngQosPolAlloc          Unsigned32,
    tFPResDynEgrClassTotal           Unsigned32,
    tFPResDynEgrClassAlloc           Unsigned32,
    tFPResDynEgrClassIUBSE           Unsigned32,
    tFPResDynEgrClassIUBNE           Unsigned32,
    tFPResIngQueueTotal              Unsigned32,
    tFPResIngQueueAlloc              Unsigned32,
    tFPResEgrQueueTotal              Unsigned32,
    tFPResEgrQueueAlloc              Unsigned32,
    tFPResIngPolicerTotal            Unsigned32,
    tFPResIngPolicerAlloc            Unsigned32,
    tFPResEgrPolicerTotal            Unsigned32,
    tFPResEgrPolicerAlloc            Unsigned32,
    tFPResIngPolicerStatTotal        Unsigned32,
    tFPResIngPolicerStatAlloc        Unsigned32,
    tFPResEgrPolicerStatTotal        Unsigned32,
    tFPResEgrPolicerStatAlloc        Unsigned32,
    tFPResIngRootArbiterTotal        Unsigned32,
    tFPResIngRootArbiterAlloc        Unsigned32,
    tFPResEgrRootArbiterTotal        Unsigned32,
    tFPResEgrRootArbiterAlloc        Unsigned32,
    tFPResIntArbiterTotal            Unsigned32,
    tFPResIntArbiterAlloc            Unsigned32,
    tFPResDynQueueTotal              Unsigned32,
    tFPResDynQueueAlloc              Unsigned32,
    tFPResDynQueueIUBI               Unsigned32,
    tFPResDynQueueIUBE               Unsigned32,
    tFPResDynPolicerTotal            Unsigned32,
    tFPResDynPolicerAlloc            Unsigned32,
    tFPResDynPolicerIUBI             Unsigned32,
    tFPResDynPolicerIUBE             Unsigned32,
    tFPResDynPolicerStatTotal        Unsigned32,
    tFPResDynPolicerStatAlloc        Unsigned32,
    tFPResDynPolicerStatIUBI         Unsigned32,
    tFPResDynPolicerStatIUBE         Unsigned32,
    tFPResIngAclEntryTotal           Unsigned32,
    tFPResIngAclEntryAlloc           Unsigned32,
    tFPResIngQosEntryTotal           Unsigned32,
    tFPResIngQosEntryAlloc           Unsigned32,
    tFPResIngAclQosEntryTotal        Unsigned32,
    tFPResIngAclQosEntryAlloc        Unsigned32,
    tFPResIngIPv6AclEntryTotal       Unsigned32,
    tFPResIngIPv6AclEntryAlloc       Unsigned32,
    tFPResIngIPv6QosEntryTotal       Unsigned32,
    tFPResIngIPv6QosEntryAlloc       Unsigned32,
    tFPResEgrAclEntryTotal           Unsigned32,
    tFPResEgrAclEntryAlloc           Unsigned32,
    tFPResEgrQosEntryTotal           Unsigned32,
    tFPResEgrQosEntryAlloc           Unsigned32,
    tFPResEgrAclQosEntryTotal        Unsigned32,
    tFPResEgrAclQosEntryAlloc        Unsigned32,
    tFPResEgrIPv6AclEntryTotal       Unsigned32,
    tFPResEgrIPv6AclEntryAlloc       Unsigned32,
    tFPResEgrIPv6QosEntryTotal       Unsigned32,
    tFPResEgrIPv6QosEntryAlloc       Unsigned32,
    tFPResIngAclFilterTotal          Unsigned32,
    tFPResIngAclFilterAlloc          Unsigned32,
    tFPResEgrAclFilterTotal          Unsigned32,
    tFPResEgrAclFilterAlloc          Unsigned32,
    tFPResDynSvcEntryTotal           Unsigned32,
    tFPResDynSvcEntryAlloc           Unsigned32,
    tFPResSubHostTotal               Unsigned32,
    tFPResSubHostAlloc               Unsigned32,
    tFPResEncapGrpMemberTotal        Unsigned32,
    tFPResEncapGrpMemberAlloc        Unsigned32,
    tFPResEgrNetQGrpMapTotal         Unsigned32,
    tFPResEgrNetQGrpMapAlloc         Unsigned32,
    tFPResMacFdbRecTotal             Unsigned32,
    tFPResMacFdbRecAlloc             Unsigned32,
    tFPResResRvplsFdbRecTotal        Unsigned32,
    tFPResResRvplsFdbRecAlloc        Unsigned32,
    tFPResDynQ2NamedPoolTotal        Unsigned32,
    tFPResDynQ2NamedPoolAlloc        Unsigned32,
    tFPResDynQ2NamedPoolIUBI         Unsigned32,
    tFPResDynQ2NamedPoolIUBE         Unsigned32,
    tFPResIngQ1NamedPoolTotal        Unsigned32,
    tFPResIngQ1NamedPoolAlloc        Unsigned32,
    tFPResEgrQ1NamedPoolTotal        Unsigned32,
    tFPResEgrQ1NamedPoolAlloc        Unsigned32,
    tFPResDynQ2WredPoolTotal         Unsigned32,
    tFPResDynQ2WredPoolAlloc         Unsigned32,
    tFPResIngIPv6AclFilterTotal      Unsigned32,
    tFPResIngIPv6AclFilterAlloc      Unsigned32,
    tFPResEgrIPv6AclFilterTotal      Unsigned32,
    tFPResEgrIPv6AclFilterAlloc      Unsigned32,
    tFPResEgrQosBypassTotal          Unsigned32,
    tFPResEgrQosBypassAlloc          Unsigned32,
    tFPResSapInstanceTotal           Unsigned32,
    tFPResSapInstanceAlloc           Unsigned32,
    tFPResEgrHsQGrpTotal             Unsigned32,
    tFPResEgrHsQGrpAlloc             Unsigned32,
    tFPResEgrHsPrimaryShapersTotal   Unsigned32,
    tFPResEgrHsPrimaryShapersAlloc   Unsigned32,
    tFPResEgrHsPrimaryShapersIUBES   Unsigned32,
    tFPResEgrHsPrimaryShapersIUBMS   Unsigned32,
    tFPResEgrHsSecondaryShapersTotal Unsigned32,
    tFPResEgrHsSecondaryShapersAlloc Unsigned32,
    tFPResEgrHsTurboQGrpTotal        Unsigned32,
    tFPResEgrHsTurboQGrpAlloc        Unsigned32,
    tFPResIngQGrpRedirTotal          Unsigned32,
    tFPResIngQGrpRedirAlloc          Unsigned32,
    tFPResSapInstEgrQGrpRedirTotal   Unsigned32,
    tFPResSapInstEgrQGrpRedirAlloc   Unsigned32,
    tFPResEgrUserQueueTotal          Unsigned32,
    tFPResEgrUserQueueAlloc          Unsigned32,
    tFPResEgrUserPolicerTotal        Unsigned32,
    tFPResEgrUserPolicerAlloc        Unsigned32,
    tFPResSLAProfileInstanceTotal    Unsigned32,
    tFPResSLAProfileInstanceAlloc    Unsigned32,
    tFPResCamBanksTotal              Unsigned32,
    tFPResCamBanksAlloc              Unsigned32,
    tFPResIngIPv4QosEntryTotal       Unsigned32,
    tFPResIngIPv4QosEntryAlloc       Unsigned32,
    tFPResIngMacQosEntryTotal        Unsigned32,
    tFPResIngMacQosEntryAlloc        Unsigned32,
    tFPResIngIPv4AclEntryTotal       Unsigned32,
    tFPResIngIPv4AclEntryAlloc       Unsigned32,
    tFPResIngMacAclEntryTotal        Unsigned32,
    tFPResIngMacAclEntryAlloc        Unsigned32,
    tFPResEgrIPv4AclEntryTotal       Unsigned32,
    tFPResEgrIPv4AclEntryAlloc       Unsigned32,
    tFPResEgrMacAclEntryTotal        Unsigned32,
    tFPResEgrMacAclEntryAlloc        Unsigned32,
    tFPResIngClassMapTotal           Unsigned32,
    tFPResIngClassMapAlloc           Unsigned32,
    tFPResIngL2ClassMapTotal         Unsigned32,
    tFPResIngL2ClassMapAlloc         Unsigned32,
    tFPResEgrRemarkMapTotal          Unsigned32,
    tFPResEgrRemarkMapAlloc          Unsigned32,
    tFPResEgrExpRemarkMapTotal       Unsigned32,
    tFPResEgrExpRemarkMapAlloc       Unsigned32,
    tFPResIPv6McastEntryTotal        Unsigned32,
    tFPResIPv6McastEntryAlloc        Unsigned32,
    tFPResEgrDot1pDscpRemarkMapTotal Unsigned32,
    tFPResEgrDot1pDscpRemarkMapAlloc Unsigned32,
    tFPResDot1xHostTotal             Unsigned32,
    tFPResDot1xHostAlloc             Unsigned32,
    tFPResFastDepthMQueuesTotal      Unsigned32,
    tFPResFastDepthMQueuesAlloc      Unsigned32,
    tFPResMepsWithIntMegTotal        Unsigned32,
    tFPResMepsWithIntMegAlloc        Unsigned32,
    tFPResMepsWithIccMegTotal        Unsigned32,
    tFPResMepsWithIccMegAlloc        Unsigned32,
    tFPResMepsWithOtherMegTotal      Unsigned32,
    tFPResMepsWithOtherMegAlloc      Unsigned32,
    tFPResUniqueIccsForMepsTotal     Unsigned32,
    tFPResUniqueIccsForMepsAlloc     Unsigned32,
    tFPResPrefixesOfMepMacsTotal     Unsigned32,
    tFPResPrefixesOfMepMacsAlloc     Unsigned32,
    tFPResIngAclStatTotal            Unsigned32,
    tFPResIngAclStatAlloc            Unsigned32,
    tFPResEgrAclStatTotal            Unsigned32,
    tFPResEgrAclStatAlloc            Unsigned32,
    tFPResEgrHwAssignNonShaperQTotal Unsigned32,
    tFPResEgrHwAssignNonShaperQAlloc Unsigned32,
    tFPResEgrHwAggShapQSetSize8Total Unsigned32,
    tFPResEgrHwAggShapQSetSize8Alloc Unsigned32,
    tFPResEgrHwAggShapersTotal       Unsigned32,
    tFPResEgrHwAggShapersAlloc       Unsigned32,
    tFPResEgrHwAggShaperSchedsTotal  Unsigned32,
    tFPResEgrHwAggShaperSchedsAlloc  Unsigned32,
    tFPResIngClassProfileTotal       Unsigned32,
    tFPResIngClassProfileAlloc       Unsigned32,
    tFPResEgrRemarkProfileTotal      Unsigned32,
    tFPResEgrRemarkProfileAlloc      Unsigned32,
    tFPResIngClassNonEpipeProfAlloc  Unsigned32,
    tFPResIngClassNonEpipeProfTotal  Unsigned32,
    tFPResOamSathTrafGenBandwAlloc   Unsigned32,
    tFPResOamSathTrafGenBandwTotal   Unsigned32,
    tFPResOamSathTrafGenSvcStrmAlloc Unsigned32,
    tFPResOamSathTrafGenSvcStrmTotal Unsigned32,
    tFPResFCDot1pMapIUBE             Unsigned32,
    tFPResFCDscpMapIUBE              Unsigned32,
    tFPResFCLspExpMapIUBE            Unsigned32,
    tFPResDot1pFCMapIUBI             Unsigned32,
    tFPResDscpFCMapIUBI              Unsigned32,
    tFPResLspExpFCMapIUBI            Unsigned32,
    tFPResCamBanksIUBDot1xHostAuth   Unsigned32,
    tFPResMacIPv4CamBanksTotal       Unsigned32,
    tFPResMacIPv4CamBanksAlloc       Unsigned32,
    tFPResIPv6CamBanksTotal          Unsigned32,
    tFPResIPv6CamBanksAlloc          Unsigned32,
    tFPResPortForwardingIdTotal      Unsigned32,
    tFPResPortForwardingIdAlloc      Unsigned32,
    tFPResIngIPv4AclEntryIUBAcl      Unsigned32,
    tFPResIngIPv4AclEntryIUBDcpu     Unsigned32,
    tFPResIngIPv4MacCamOverLoad      TmnxCamOverloadState,
    tFPResIngIPv6CamOverLoad         TmnxCamOverloadState,
    tFPResEgrIPv4MacCamOverLoad      TmnxCamOverloadState,
    tFPResEgrIPv6CamOverLoad         TmnxCamOverloadState,
    tFPResOversub                    BITS,
    tFPResEgrHwAggShapQSetSizeTotal  Unsigned32,
    tFPResEgrHwAggShapQSetSizeAlloc  Unsigned32,
    tFPResEgrHwAggShpDefSapQSetSz    Unsigned32,
    tFPResEgrHwAggShpDefSubQSetSz    Unsigned32,
    tFPResEgrHwAggShpDefQGrpQSetSz   Unsigned32,
    tFPResCamBanksIUBSharedPlcrs     Unsigned32,
    tFPResSharedPlcrCamBanksTotal    Unsigned32,
    tFPResSharedPlcrCamBanksAlloc    Unsigned32,
    tFPResSharedPlcrCamEntryTotal    Unsigned32,
    tFPResSharedPlcrCamEntryAlloc    Unsigned32,
    tFPResCamBanksIUBSrv6TunnelTerm  Unsigned32,
    tFPResEgrHwAggShapQSetSize1Total Unsigned32,
    tFPResEgrHwAggShapQSetSize1Alloc Unsigned32,
    tFPResEgrHwAggShapQSetSize2Total Unsigned32,
    tFPResEgrHwAggShapQSetSize2Alloc Unsigned32,
    tFPResEgrHwAggShapQSetSize3Total Unsigned32,
    tFPResEgrHwAggShapQSetSize3Alloc Unsigned32,
    tFPResEgrHwAggShapQSetSize4Total Unsigned32,
    tFPResEgrHwAggShapQSetSize4Alloc Unsigned32,
    tFPResEgrHwAggShapQSetSize5Total Unsigned32,
    tFPResEgrHwAggShapQSetSize5Alloc Unsigned32,
    tFPResEgrHwAggShapQSetSize6Total Unsigned32,
    tFPResEgrHwAggShapQSetSize6Alloc Unsigned32,
    tFPResEgrHwAggShapQSetSize7Total Unsigned32,
    tFPResEgrHwAggShapQSetSize7Alloc Unsigned32,
    tFPResDCpuProtCamEntryTotal      Unsigned32,
    tFPResDCpuProtCamEntryAlloc      Unsigned32,
    tFPResSapIngAggPolicerTotal      Unsigned32,
    tFPResSapIngAggPolicerAlloc      Unsigned32,
    tFPResBfdMhopIPv4CamEntryTotal   Unsigned32,
    tFPResBfdMhopIPv4CamEntryAlloc   Unsigned32,
    tFPResBfdMhopIPv6CamEntryTotal   Unsigned32,
    tFPResBfdMhopIPv6CamEntryAlloc   Unsigned32,
    tFPResCamBanksIUBSeamlessBfd     Unsigned32,
    tFPResCamBanksIUBEthStormControl Unsigned32,
    tFPResEthStormCtrlCamBanksTotal  Unsigned32,
    tFPResEthStormCtrlCamBanksAlloc  Unsigned32,
    tFPResEthStormCtrlCamEntryTotal  Unsigned32,
    tFPResEthStormCtrlCamEntryAlloc  Unsigned32
}

tFPResSapIngQosPolTotal          OBJECT-TYPE
    SYNTAX      Unsigned32
    MAX-ACCESS  read-only
    STATUS      current
    DESCRIPTION
        "The value of tFPResSapIngQosPolTotal represents the total number of
         sap-ingress QoS policies that are allowed to be in use on this FP."
    ::= { tFPResEntry 1 }

tFPResSapIngQosPolAlloc          OBJECT-TYPE
    SYNTAX      Unsigned32
    MAX-ACCESS  read-only
    STATUS      current
    DESCRIPTION
        "The value of tFPResSapIngQosPolAlloc represents the total number of
         sap-ingress QoS policies that are currently allocated on this FP."
    ::= { tFPResEntry 2 }

tFPResDynEgrClassTotal           OBJECT-TYPE
    SYNTAX      Unsigned32
    MAX-ACCESS  read-only
    STATUS      current
    DESCRIPTION
        "The value of tFPResDynEgrClassTotal represents the total number of QoS
         dynamic egress classification resources that are allowed to be in use
         on this FP."
    ::= { tFPResEntry 3 }

tFPResDynEgrClassAlloc           OBJECT-TYPE
    SYNTAX      Unsigned32
    MAX-ACCESS  read-only
    STATUS      current
    DESCRIPTION
        "The value of tFPResDynEgrClassAlloc represents the total number of QoS
         dynamic egress classification resources that are currently allocated
         on this FP."
    ::= { tFPResEntry 4 }

tFPResDynEgrClassIUBSE           OBJECT-TYPE
    SYNTAX      Unsigned32
    MAX-ACCESS  read-only
    STATUS      current
    DESCRIPTION
        "The value of tFPResDynEgrClassIUBSE represents the subset of resources
         which are currently in use by sap-egress QoS policies out of currently
         allocated QoS dynamic egress classification resources,
         tFPResDynEgrClassAlloc."
    ::= { tFPResEntry 5 }

tFPResDynEgrClassIUBNE           OBJECT-TYPE
    SYNTAX      Unsigned32
    MAX-ACCESS  read-only
    STATUS      current
    DESCRIPTION
        "The value of tFPResDynEgrClassIUBNE represents the subset of resources
         which are currently in use by network egress QoS classification out of
         currently allocated QoS dynamic egress classification resources,
         tFPResDynEgrClassAlloc.

         A network egress QoS classification resource is consumed whenever a
         network QoS policy has at least one egress DSCP or precedence
         classification rule provisioned."
    ::= { tFPResEntry 6 }

tFPResIngQueueTotal              OBJECT-TYPE
    SYNTAX      Unsigned32
    MAX-ACCESS  read-only
    STATUS      current
    DESCRIPTION
        "The value of tFPResIngQueueTotal represents the total number of
         ingress queues that are supported on this FP.

         When the value of tFPResIngQueueTotal is zero, it indicates that this
         resource type is not supported on this FP."
    ::= { tFPResEntry 7 }

tFPResIngQueueAlloc              OBJECT-TYPE
    SYNTAX      Unsigned32
    MAX-ACCESS  read-only
    STATUS      current
    DESCRIPTION
        "The value of tFPResIngQueueAlloc represents the total number of
         ingress queues that are currently allocated on this FP."
    ::= { tFPResEntry 8 }

tFPResEgrQueueTotal              OBJECT-TYPE
    SYNTAX      Unsigned32
    MAX-ACCESS  read-only
    STATUS      current
    DESCRIPTION
        "The value of tFPResEgrQueueTotal represents the total number of egress
         queues that are supported on this FP.

         When the value of tFPResEgrQueueTotal is zero, it indicates that this
         resource type is not supported on this FP."
    ::= { tFPResEntry 9 }

tFPResEgrQueueAlloc              OBJECT-TYPE
    SYNTAX      Unsigned32
    MAX-ACCESS  read-only
    STATUS      current
    DESCRIPTION
        "The value of tFPResEgrQueueAlloc represents the total number of egress
         queues that are currently allocated on this FP."
    ::= { tFPResEntry 10 }

tFPResIngPolicerTotal            OBJECT-TYPE
    SYNTAX      Unsigned32
    MAX-ACCESS  read-only
    STATUS      current
    DESCRIPTION
        "The value of tFPResIngPolicerTotal represents the total number of
         ingress policers that are supported on this FP.

         When the value of tFPResIngPolicerTotal is zero, it indicates that
         this resource type is not supported on this FP."
    ::= { tFPResEntry 11 }

tFPResIngPolicerAlloc            OBJECT-TYPE
    SYNTAX      Unsigned32
    MAX-ACCESS  read-only
    STATUS      current
    DESCRIPTION
        "The value of tFPResIngPolicerAlloc represents the total number of
         ingress policers that are currently allocated on this FP."
    ::= { tFPResEntry 12 }

tFPResEgrPolicerTotal            OBJECT-TYPE
    SYNTAX      Unsigned32
    MAX-ACCESS  read-only
    STATUS      current
    DESCRIPTION
        "The value of tFPResEgrPolicerTotal represents the total number of
         egress policers that are supported on this FP.

         When the value of tFPResEgrPolicerTotal is zero, it indicates that
         this resource type is not supported on this FP."
    ::= { tFPResEntry 13 }

tFPResEgrPolicerAlloc            OBJECT-TYPE
    SYNTAX      Unsigned32
    MAX-ACCESS  read-only
    STATUS      current
    DESCRIPTION
        "The value of tFPResEgrPolicerAlloc represents the total number of
         egress policers that are currently allocated on this FP."
    ::= { tFPResEntry 14 }

tFPResIngPolicerStatTotal        OBJECT-TYPE
    SYNTAX      Unsigned32
    MAX-ACCESS  read-only
    STATUS      current
    DESCRIPTION
        "The value of tFPResIngPolicerStatTotal represents the total number of
         ingress policer stats that are supported on this FP.

         When the value of tFPResIngPolicerStatTotal is zero, it indicates that
         this resource type is not supported on this FP."
    ::= { tFPResEntry 15 }

tFPResIngPolicerStatAlloc        OBJECT-TYPE
    SYNTAX      Unsigned32
    MAX-ACCESS  read-only
    STATUS      current
    DESCRIPTION
        "The value of tFPResIngPolicerStatAlloc represents the total number of
         ingress policer stats that are currently allocated on this FP."
    ::= { tFPResEntry 16 }

tFPResEgrPolicerStatTotal        OBJECT-TYPE
    SYNTAX      Unsigned32
    MAX-ACCESS  read-only
    STATUS      current
    DESCRIPTION
        "The value of tFPResEgrPolicerStatTotal represents the total number of
         egress policer stats that are supported on this FP.

         When the value of tFPResEgrPolicerStatTotal is zero, it indicates that
         this resource type is not supported on this FP."
    ::= { tFPResEntry 17 }

tFPResEgrPolicerStatAlloc        OBJECT-TYPE
    SYNTAX      Unsigned32
    MAX-ACCESS  read-only
    STATUS      current
    DESCRIPTION
        "The value of tFPResEgrPolicerStatAlloc represents the total number of
         egress policer stats that are currently allocated on this FP."
    ::= { tFPResEntry 18 }

tFPResIngRootArbiterTotal        OBJECT-TYPE
    SYNTAX      Unsigned32
    MAX-ACCESS  read-only
    STATUS      current
    DESCRIPTION
        "The value of tFPResIngRootArbiterTotal represents the total number of
         ingress root arbiters that are supported on this FP.

         When the value of tFPResIngRootArbiterTotal is zero, it indicates that
         this resource type is not supported on this FP."
    ::= { tFPResEntry 19 }

tFPResIngRootArbiterAlloc        OBJECT-TYPE
    SYNTAX      Unsigned32
    MAX-ACCESS  read-only
    STATUS      current
    DESCRIPTION
        "The value of tFPResIngRootArbiterAlloc represents the total number of
         ingress root arbiters that are currently allocated on this FP."
    ::= { tFPResEntry 20 }

tFPResEgrRootArbiterTotal        OBJECT-TYPE
    SYNTAX      Unsigned32
    MAX-ACCESS  read-only
    STATUS      current
    DESCRIPTION
        "The value of tFPResEgrRootArbiterTotal represents the total number of
         egress root arbiters that are supported on this FP.

         When the value of tFPResEgrRootArbiterTotal is zero, it indicates that
         this resource type is not supported on this FP."
    ::= { tFPResEntry 21 }

tFPResEgrRootArbiterAlloc        OBJECT-TYPE
    SYNTAX      Unsigned32
    MAX-ACCESS  read-only
    STATUS      current
    DESCRIPTION
        "The value of tFPResEgrRootArbiterAlloc represents the total number of
         egress root arbiters that are currently allocated on this FP."
    ::= { tFPResEntry 22 }

tFPResIntArbiterTotal            OBJECT-TYPE
    SYNTAX      Unsigned32
    MAX-ACCESS  read-only
    STATUS      obsolete
    DESCRIPTION
        "The value of tFPResIntArbiterTotal represents the total number of
         intermediate arbiters that are supported on this FP.

         When the value of tFPResIntArbiterTotal is zero, it indicates that
         this resource type is not supported on this FP.

         This object is obsoleted on 16.0R1 release and replaced by
         tCardResIntArbiterTotal."
    ::= { tFPResEntry 23 }

tFPResIntArbiterAlloc            OBJECT-TYPE
    SYNTAX      Unsigned32
    MAX-ACCESS  read-only
    STATUS      obsolete
    DESCRIPTION
        "The value of tFPResIntArbiterAlloc represents the total number of
         intermediate arbiters that are currently allocated on this FP.

         This object is obsoleted on 16.0R1 release and replaced by
         tCardResIntArbiterAlloc."
    ::= { tFPResEntry 24 }

tFPResDynQueueTotal              OBJECT-TYPE
    SYNTAX      Unsigned32
    MAX-ACCESS  read-only
    STATUS      current
    DESCRIPTION
        "The value of tFPResDynQueueTotal represents the total number of
         dynamic queues that are supported on this FP.

         When the value of tFPResEgrRootArbiterTotal is zero, it indicates that
         this resource type is not supported on this FP."
    ::= { tFPResEntry 25 }

tFPResDynQueueAlloc              OBJECT-TYPE
    SYNTAX      Unsigned32
    MAX-ACCESS  read-only
    STATUS      current
    DESCRIPTION
        "The value of tFPResDynQueueAlloc represents the total number of
         dynamic queues that are currently allocated on this FP."
    ::= { tFPResEntry 26 }

tFPResDynQueueIUBI               OBJECT-TYPE
    SYNTAX      Unsigned32
    MAX-ACCESS  read-only
    STATUS      current
    DESCRIPTION
        "The value of tFPResDynQueueIUBI represents the subset of resources
         which are currently in use by ingress queues out of currently
         allocated dynamic queue resources, tFPResDynQueueAlloc."
    ::= { tFPResEntry 27 }

tFPResDynQueueIUBE               OBJECT-TYPE
    SYNTAX      Unsigned32
    MAX-ACCESS  read-only
    STATUS      current
    DESCRIPTION
        "The value of tFPResDynQueueIUBE represents the subset of resources
         which are currently in use by egress queues out of currently allocated
         dynamic queue resources, tFPResDynQueueAlloc."
    ::= { tFPResEntry 28 }

tFPResDynPolicerTotal            OBJECT-TYPE
    SYNTAX      Unsigned32
    MAX-ACCESS  read-only
    STATUS      current
    DESCRIPTION
        "The value of tFPResDynPolicerTotal represents the total number of
         dynamic policer that are supported on this FP.

         When the value of tFPResDynPolicerTotal is zero, it indicates that
         this resource type is not supported on this FP."
    ::= { tFPResEntry 29 }

tFPResDynPolicerAlloc            OBJECT-TYPE
    SYNTAX      Unsigned32
    MAX-ACCESS  read-only
    STATUS      current
    DESCRIPTION
        "The value of tFPResDynPolicerAlloc represents the total number of
         dynamic policers that are currently allocated on this FP."
    ::= { tFPResEntry 30 }

tFPResDynPolicerIUBI             OBJECT-TYPE
    SYNTAX      Unsigned32
    MAX-ACCESS  read-only
    STATUS      current
    DESCRIPTION
        "The value of tFPResDynPolicerIUBI represents the subset of resources
         which are currently in use by ingress policer out of currently
         allocated dynamic policer resources, tFPResDynPolicerAlloc."
    ::= { tFPResEntry 31 }

tFPResDynPolicerIUBE             OBJECT-TYPE
    SYNTAX      Unsigned32
    MAX-ACCESS  read-only
    STATUS      current
    DESCRIPTION
        "The value of tFPResDynPolicerIUBE represents the subset of resources
         which are currently in use by egress policer out of currently
         allocated dynamic policer resources, tFPResDynPolicerAlloc."
    ::= { tFPResEntry 32 }

tFPResDynPolicerStatTotal        OBJECT-TYPE
    SYNTAX      Unsigned32
    MAX-ACCESS  read-only
    STATUS      current
    DESCRIPTION
        "The value of tFPResDynPolicerStatTotal represents the total number of
         dynamic policer stats that are supported on this FP.

         When the value of tFPResDynPolicerStatTotal is zero, it indicates that
         this resource type is not supported on this FP."
    ::= { tFPResEntry 33 }

tFPResDynPolicerStatAlloc        OBJECT-TYPE
    SYNTAX      Unsigned32
    MAX-ACCESS  read-only
    STATUS      current
    DESCRIPTION
        "The value of tFPResDynPolicerStatAlloc represents the total number of
         dynamic policers stats that are currently allocated on this FP."
    ::= { tFPResEntry 34 }

tFPResDynPolicerStatIUBI         OBJECT-TYPE
    SYNTAX      Unsigned32
    MAX-ACCESS  read-only
    STATUS      current
    DESCRIPTION
        "The value of tFPResDynPolicerStatIUBI represents the subset of
         resources which are currently in use by ingress policer stats out of
         currently allocated dynamic policer stats resources,
         tFPResDynPolicerStatAlloc."
    ::= { tFPResEntry 35 }

tFPResDynPolicerStatIUBE         OBJECT-TYPE
    SYNTAX      Unsigned32
    MAX-ACCESS  read-only
    STATUS      current
    DESCRIPTION
        "The value of tFPResDynPolicerStatIUBE represents the subset of
         resources which are currently in use by egress policer stats out of
         currently allocated dynamic policer stats resources,
         tFPResDynPolicerStatAlloc."
    ::= { tFPResEntry 36 }

tFPResIngAclEntryTotal           OBJECT-TYPE
    SYNTAX      Unsigned32
    MAX-ACCESS  read-only
    STATUS      current
    DESCRIPTION
        "The value of tFPResIngAclEntryTotal represents the total number of
         ingress ACL CAM entries that are supported on this FP.

         When the value of tFPResIngAclEntryTotal is zero, it indicates that
         this resource type is not supported on this FP."
    ::= { tFPResEntry 37 }

tFPResIngAclEntryAlloc           OBJECT-TYPE
    SYNTAX      Unsigned32
    MAX-ACCESS  read-only
    STATUS      current
    DESCRIPTION
        "The value of tFPResIngAclEntryAlloc represents the total number of
         ingress ACL CAM entries that are currently allocated on this FP."
    ::= { tFPResEntry 38 }

tFPResIngQosEntryTotal           OBJECT-TYPE
    SYNTAX      Unsigned32
    MAX-ACCESS  read-only
    STATUS      current
    DESCRIPTION
        "The value of tFPResIngQosEntryTotal represents the total number of
         ingress QoS CAM entries that are supported on this FP.

         When the value of tFPResIngQosEntryTotal is zero, it indicates that
         this resource type is not supported on this FP."
    ::= { tFPResEntry 39 }

tFPResIngQosEntryAlloc           OBJECT-TYPE
    SYNTAX      Unsigned32
    MAX-ACCESS  read-only
    STATUS      current
    DESCRIPTION
        "The value of tFPResIngQosEntryAlloc represents the total number of
         ingress QoS CAM entries that are currently allocated on this FP."
    ::= { tFPResEntry 40 }

tFPResIngAclQosEntryTotal        OBJECT-TYPE
    SYNTAX      Unsigned32
    MAX-ACCESS  read-only
    STATUS      obsolete
    DESCRIPTION
        "The value of tFPResIngAclQosEntryTotal represents the total number of
         combined ingress ACL and QoS CAM entries that are supported on this
         FP.

         When the value of tFPResIngAclQosEntryTotal is zero, it indicates that
         this resource type is not supported on this FP."
    ::= { tFPResEntry 41 }

tFPResIngAclQosEntryAlloc        OBJECT-TYPE
    SYNTAX      Unsigned32
    MAX-ACCESS  read-only
    STATUS      obsolete
    DESCRIPTION
        "The value of tFPResIngAclQosEntryAlloc represents the total number of
         combined ingress ACL and QoS CAM entries that are currently allocated
         on this FP."
    ::= { tFPResEntry 42 }

tFPResIngIPv6AclEntryTotal       OBJECT-TYPE
    SYNTAX      Unsigned32
    MAX-ACCESS  read-only
    STATUS      current
    DESCRIPTION
        "The value of tFPResIngIPv6AclEntryTotal represents the total number of
         IPv6 ingress ACL CAM entries that are supported on this FP.

         When the value of tFPResIngIPv6AclEntryTotal is zero, it indicates
         that this resource type is not supported on this FP."
    ::= { tFPResEntry 43 }

tFPResIngIPv6AclEntryAlloc       OBJECT-TYPE
    SYNTAX      Unsigned32
    MAX-ACCESS  read-only
    STATUS      current
    DESCRIPTION
        "The value of tFPResIngIPv6AclEntryAlloc represents the total number of
         IPv6 ingress ACL CAM entries that are currently allocated on this FP."
    ::= { tFPResEntry 44 }

tFPResIngIPv6QosEntryTotal       OBJECT-TYPE
    SYNTAX      Unsigned32
    MAX-ACCESS  read-only
    STATUS      current
    DESCRIPTION
        "The value of tFPResIngIPv6QosEntryTotal represents the total number of
         IPv6 ingress QoS CAM entries that are supported on this FP.

         When the value of tFPResIngIPv6QosEntryTotal is zero, it indicates
         that this resource type is not supported on this FP."
    ::= { tFPResEntry 45 }

tFPResIngIPv6QosEntryAlloc       OBJECT-TYPE
    SYNTAX      Unsigned32
    MAX-ACCESS  read-only
    STATUS      current
    DESCRIPTION
        "The value of tFPResIngIPv6QosEntryAlloc represents the total number of
         IPv6 ingress QoS CAM entries that are currently allocated on this FP."
    ::= { tFPResEntry 46 }

tFPResEgrAclEntryTotal           OBJECT-TYPE
    SYNTAX      Unsigned32
    MAX-ACCESS  read-only
    STATUS      current
    DESCRIPTION
        "The value of tFPResEgrAclEntryTotal represents the total number of
         egress ACL CAM entries that are supported on this FP.

         When the value of tFPResEgrAclEntryTotal is zero, it indicates that
         this resource type is not supported on this FP."
    ::= { tFPResEntry 47 }

tFPResEgrAclEntryAlloc           OBJECT-TYPE
    SYNTAX      Unsigned32
    MAX-ACCESS  read-only
    STATUS      current
    DESCRIPTION
        "The value of tFPResEgrAclEntryAlloc represents the total number of
         egress ACL CAM entries that are currently allocated on this FP."
    ::= { tFPResEntry 48 }

tFPResEgrQosEntryTotal           OBJECT-TYPE
    SYNTAX      Unsigned32
    MAX-ACCESS  read-only
    STATUS      current
    DESCRIPTION
        "The value of tFPResEgrQosEntryTotal represents the total number of
         egress QoS CAM entries that are supported on this FP.

         When the value of tFPResEgrQosEntryTotal is zero, it indicates that
         this resource type is not supported on this FP."
    ::= { tFPResEntry 49 }

tFPResEgrQosEntryAlloc           OBJECT-TYPE
    SYNTAX      Unsigned32
    MAX-ACCESS  read-only
    STATUS      current
    DESCRIPTION
        "The value of tFPResEgrQosEntryAlloc represents the total number of
         egress QoS CAM entries that are currently allocated on this FP."
    ::= { tFPResEntry 50 }

tFPResEgrAclQosEntryTotal        OBJECT-TYPE
    SYNTAX      Unsigned32
    MAX-ACCESS  read-only
    STATUS      obsolete
    DESCRIPTION
        "The value of tFPResEgrAclQosEntryTotal represents the total number of
         combined egress ACL and QoS CAM entries that are supported on this FP.

         When the value of tFPResEgrAclQosEntryTotal is zero, it indicates that
         this resource type is not supported on this FP."
    ::= { tFPResEntry 51 }

tFPResEgrAclQosEntryAlloc        OBJECT-TYPE
    SYNTAX      Unsigned32
    MAX-ACCESS  read-only
    STATUS      obsolete
    DESCRIPTION
        "The value of tFPResEgrAclQosEntryAlloc represents the total number of
         combined egress ACL and QoS CAM entries that are currently allocated
         on this FP."
    ::= { tFPResEntry 52 }

tFPResEgrIPv6AclEntryTotal       OBJECT-TYPE
    SYNTAX      Unsigned32
    MAX-ACCESS  read-only
    STATUS      current
    DESCRIPTION
        "The value of tFPResEgrIPv6AclEntryTotal represents the total number of
         IPv6 egress ACL CAM entries that are supported on this FP.

         When the value of tFPResEgrIPv6AclEntryTotal is zero, it indicates
         that this resource type is not supported on this FP."
    ::= { tFPResEntry 53 }

tFPResEgrIPv6AclEntryAlloc       OBJECT-TYPE
    SYNTAX      Unsigned32
    MAX-ACCESS  read-only
    STATUS      current
    DESCRIPTION
        "The value of tFPResEgrIPv6AclEntryAlloc represents the total number of
         IPv6 egress ACL CAM entries that are currently allocated on this FP."
    ::= { tFPResEntry 54 }

tFPResEgrIPv6QosEntryTotal       OBJECT-TYPE
    SYNTAX      Unsigned32
    MAX-ACCESS  read-only
    STATUS      current
    DESCRIPTION
        "The value of tFPResEgrIPv6QosEntryTotal represents the total number of
         IPv6 egress QoS CAM entries that are supported on this FP.

         When the value of tFPResEgrIPv6QosEntryTotal is zero, it indicates
         that this resource type is not supported on this FP."
    ::= { tFPResEntry 55 }

tFPResEgrIPv6QosEntryAlloc       OBJECT-TYPE
    SYNTAX      Unsigned32
    MAX-ACCESS  read-only
    STATUS      current
    DESCRIPTION
        "The value of tFPResEgrIPv6QosEntryAlloc represents the total number of
         IPv6 egress QoS CAM entries that are currently allocated on this FP."
    ::= { tFPResEntry 56 }

tFPResIngAclFilterTotal          OBJECT-TYPE
    SYNTAX      Unsigned32
    MAX-ACCESS  read-only
    STATUS      current
    DESCRIPTION
        "The value of tFPResIngAclFilterTotal represents the total number of
         ingress MAC + IP ACL filter policies that are supported on this FP.

         Note that on 7750 SR-c4/c12 the CPM enforced limit for the total
         number of ACL filter policies is lower than the value of this object."
    ::= { tFPResEntry 57 }

tFPResIngAclFilterAlloc          OBJECT-TYPE
    SYNTAX      Unsigned32
    MAX-ACCESS  read-only
    STATUS      current
    DESCRIPTION
        "The value of tFPResIngAclFilterAlloc represents the total number of
         ingress MAC + IP ACL filter policies that are currently allocated on
         this FP."
    ::= { tFPResEntry 58 }

tFPResEgrAclFilterTotal          OBJECT-TYPE
    SYNTAX      Unsigned32
    MAX-ACCESS  read-only
    STATUS      current
    DESCRIPTION
        "The value of tFPResEgrAclFilterTotal represents the total number of
         egress MAC + IP ACL filter policies that are supported on this FP.

         Note that on 7750 SR-c4/c12 the CPM enforced limit for the total
         number of ACL filter policies is lower than the value of this object."
    ::= { tFPResEntry 59 }

tFPResEgrAclFilterAlloc          OBJECT-TYPE
    SYNTAX      Unsigned32
    MAX-ACCESS  read-only
    STATUS      current
    DESCRIPTION
        "The value of tFPResEgrAclFilterAlloc represents the total number of
         egress MAC + IP ACL filter policies that are currently allocated on
         this FP."
    ::= { tFPResEntry 60 }

tFPResDynSvcEntryTotal           OBJECT-TYPE
    SYNTAX      Unsigned32
    MAX-ACCESS  read-only
    STATUS      current
    DESCRIPTION
        "The value of tFPResDynSvcEntryTotal represents the total number of
         dynamic services that are supported on this FP.

         When the value of tFPResDynSvcEntryTotal is zero, it indicates that
         this resource type is not supported on this FP.

         The value of tFPResDynSvcEntryTotal will always equal to the sum of
         tFPResSubHostTotal, tFPResEncapGrpMemberTotal,
         tFPResEgrNetQGrpMapTotal and tFPResDot1xHostTotal since subscriber
         host resources, encap-group members resources and egress network
         queue-group mappings resources are subsets of dynamic service entry
         resources."
    ::= { tFPResEntry 61 }

tFPResDynSvcEntryAlloc           OBJECT-TYPE
    SYNTAX      Unsigned32
    MAX-ACCESS  read-only
    STATUS      current
    DESCRIPTION
        "The value of tFPResDynSvcEntryAlloc represents the total number of
         dynamic services that are currently allocated on this FP.

         The value of tFPResDynSvcEntryAlloc will always equal to the sum of
         tFPResSubHostAlloc, tFPResEncapGrpMemberAlloc,
         tFPResEgrNetQGrpMapAlloc and tFPResDot1xHostAlloc since subscriber
         host resources, encap-group members resources and egress network
         queue-group mappings resources are subsets of dynamic service entry
         resources."
    ::= { tFPResEntry 62 }

tFPResSubHostTotal               OBJECT-TYPE
    SYNTAX      Unsigned32
    MAX-ACCESS  read-only
    STATUS      current
    DESCRIPTION
        "The value of tFPResSubHostTotal represents the total number of
         subscriber hosts that are supported on this FP.

         When the value of tFPResSubHostTotal is zero, it indicates that this
         resource type is not supported on this FP.

         The value of tFPResSubHostTotal will always be less than or equal to
         tFPResDynSvcEntryTotal since subscriber host resources are subset of
         dynamic service entry resources."
    ::= { tFPResEntry 63 }

tFPResSubHostAlloc               OBJECT-TYPE
    SYNTAX      Unsigned32
    MAX-ACCESS  read-only
    STATUS      current
    DESCRIPTION
        "The value of tFPResSubHostAlloc represents the total number of
         subscriber hosts that are currently allocated on this FP.

         The value of tFPResSubHostAlloc will always be less than or equal to
         tFPResDynSvcEntryAlloc since subscriber host resources are subset of
         dynamic service entry resources."
    ::= { tFPResEntry 64 }

tFPResEncapGrpMemberTotal        OBJECT-TYPE
    SYNTAX      Unsigned32
    MAX-ACCESS  read-only
    STATUS      current
    DESCRIPTION
        "The value of tFPResEncapGrpMemberTotal represents the total number of
         encap group members that are supported on this FP.

         When the value of tFPResEncapGrpMemberTotal is zero, it indicates that
         this resource type is not supported on this FP.

         The value of tFPResEncapGrpMemberTotal will always be less than or
         equal to tFPResDynSvcEntryTotal since encap group members are subset
         of dynamic service entry resources."
    ::= { tFPResEntry 65 }

tFPResEncapGrpMemberAlloc        OBJECT-TYPE
    SYNTAX      Unsigned32
    MAX-ACCESS  read-only
    STATUS      current
    DESCRIPTION
        "The value of tFPResEncapGrpMemberAlloc represents the total number of
         encap group members that are currently allocated on this FP.

         The value of tFPResEncapGrpMemberAlloc will always be less than or
         equal to tFPResDynSvcEntryAlloc since encap group members are subset
         of dynamic service entry resources."
    ::= { tFPResEntry 66 }

tFPResEgrNetQGrpMapTotal         OBJECT-TYPE
    SYNTAX      Unsigned32
    MAX-ACCESS  read-only
    STATUS      current
    DESCRIPTION
        "The value of tFPResEgrNetQGrpMapTotal represents the total number of
         egress network queue-group mappings that are supported on this FP.

         When the value of tFPResEgrNetQGrpMapTotal is zero, it indicates that
         this resource type is not supported on this FP.

         The value of tFPResEgrNetQGrpMapTotal will always be less than or
         equal to tFPResDynSvcEntryTotal since egress network queue-group
         mappings are subset of dynamic service entry resources."
    ::= { tFPResEntry 67 }

tFPResEgrNetQGrpMapAlloc         OBJECT-TYPE
    SYNTAX      Unsigned32
    MAX-ACCESS  read-only
    STATUS      current
    DESCRIPTION
        "The value of tFPResEgrNetQGrpMapAlloc represents the total number of
         egress network queue-group mappings that are currently allocated on
         this FP.

         The value of tFPResEgrNetQGrpMapAlloc will always be less than or
         equal to tFPResDynSvcEntryAlloc since egress network queue-group
         mappings are subset of dynamic service entry resources."
    ::= { tFPResEntry 68 }

tFPResMacFdbRecTotal             OBJECT-TYPE
    SYNTAX      Unsigned32
    MAX-ACCESS  read-only
    STATUS      current
    DESCRIPTION
        "The value of tFPResMacFdbRecTotal represents the total number of MAC
         Forwarding Data-Base (FDB) records that are supported on this FP.

         When the value of tFPResMacFdbRecTotal is zero, it indicates that this
         resource type is not supported on this FP."
    ::= { tFPResEntry 69 }

tFPResMacFdbRecAlloc             OBJECT-TYPE
    SYNTAX      Unsigned32
    MAX-ACCESS  read-only
    STATUS      current
    DESCRIPTION
        "The value of tFPResMacFdbRecAlloc represents the total number of MAC
         Forwarding Data-Base (FDB) records that are currently allocated on
         this FP."
    ::= { tFPResEntry 70 }

tFPResResRvplsFdbRecTotal        OBJECT-TYPE
    SYNTAX      Unsigned32
    MAX-ACCESS  read-only
    STATUS      obsolete
    DESCRIPTION
        "The value of tFPResResRvplsFdbRecTotal represents the total number of
         reserved R-VPLS Forwarding Data-Base (FDB) records that are supported
         on this FP.

         When the value of tFPResResRvplsFdbRecTotal is zero, it indicates that
         this resource type is not supported on this FP."
    ::= { tFPResEntry 71 }

tFPResResRvplsFdbRecAlloc        OBJECT-TYPE
    SYNTAX      Unsigned32
    MAX-ACCESS  read-only
    STATUS      obsolete
    DESCRIPTION
        "The value of tFPResResRvplsFdbRecAlloc represents the total number of
         reserved R-VPLS Forwarding Data-Base (FDB) records that are currently
         allocated on this FP."
    ::= { tFPResEntry 72 }

tFPResDynQ2NamedPoolTotal        OBJECT-TYPE
    SYNTAX      Unsigned32
    MAX-ACCESS  read-only
    STATUS      obsolete
    DESCRIPTION
        "The value of tFPResDynQ2NamedPoolTotal represents the total number of
         dynamic Q2 named pools that are supported on this FP.

         When the value of tFPResDynQ2NamedPoolTotal is zero, it indicates that
         this resource type is not supported on this FP.

         This object is obsolete in 20.2 release."
    ::= { tFPResEntry 73 }

tFPResDynQ2NamedPoolAlloc        OBJECT-TYPE
    SYNTAX      Unsigned32
    MAX-ACCESS  read-only
    STATUS      obsolete
    DESCRIPTION
        "The value of tFPResDynQ2NamedPoolAlloc represents the total number of
         dynamic Q2 named pools that are currently allocated on this FP.

         This object is obsolete in 20.2 release."
    ::= { tFPResEntry 74 }

tFPResDynQ2NamedPoolIUBI         OBJECT-TYPE
    SYNTAX      Unsigned32
    MAX-ACCESS  read-only
    STATUS      obsolete
    DESCRIPTION
        "The value of tFPResDynQ2NamedPoolIUBI represents the subset of
         resources which are currently in use by ingress Q2 named pools out of
         currently allocated dynamic Q2 named pools resources,
         tFPResDynQ2NamedPoolAlloc.

         This object is obsolete in 20.2 release."
    ::= { tFPResEntry 75 }

tFPResDynQ2NamedPoolIUBE         OBJECT-TYPE
    SYNTAX      Unsigned32
    MAX-ACCESS  read-only
    STATUS      obsolete
    DESCRIPTION
        "The value of tFPResDynQ2NamedPoolIUBE represents the subset of
         resources which are currently in use by egress Q2 named pools out of
         currently allocated dynamic Q2 named pools resources,
         tFPResDynQ2NamedPoolAlloc.

         This object is obsolete in 20.2 release."
    ::= { tFPResEntry 76 }

tFPResIngQ1NamedPoolTotal        OBJECT-TYPE
    SYNTAX      Unsigned32
    MAX-ACCESS  read-only
    STATUS      obsolete
    DESCRIPTION
        "The value of tFPResIngQ1NamedPoolTotal represents the total number of
         ingress Q1 named pools that are supported on this FP.

         When the value of tFPResIngQ1NamedPoolTotal is zero, it indicates that
         this resource type is not supported on this FP.

         This object is obsolete in 16.0 release."
    ::= { tFPResEntry 77 }

tFPResIngQ1NamedPoolAlloc        OBJECT-TYPE
    SYNTAX      Unsigned32
    MAX-ACCESS  read-only
    STATUS      obsolete
    DESCRIPTION
        "The value of tFPResIngQ1NamedPoolAlloc represents the total number of
         ingress Q1 named pools that are currently allocated on this FP.

         This object is obsolete in 16.0 release."
    ::= { tFPResEntry 78 }

tFPResEgrQ1NamedPoolTotal        OBJECT-TYPE
    SYNTAX      Unsigned32
    MAX-ACCESS  read-only
    STATUS      obsolete
    DESCRIPTION
        "The value of tFPResEgrQ1NamedPoolTotal represents the total number of
         egress Q1 named pools that are supported on this FP.

         When the value of tFPResEgrQ1NamedPoolTotal is zero, it indicates that
         this resource type is not supported on this FP.

         This object is obsolete in 16.0 release."
    ::= { tFPResEntry 79 }

tFPResEgrQ1NamedPoolAlloc        OBJECT-TYPE
    SYNTAX      Unsigned32
    MAX-ACCESS  read-only
    STATUS      obsolete
    DESCRIPTION
        "The value of tFPResEgrQ1NamedPoolAlloc represents the total number of
         egress Q1 named pools that are currently allocated on this FP.

         This object is obsolete in 16.0 release."
    ::= { tFPResEntry 80 }

tFPResDynQ2WredPoolTotal         OBJECT-TYPE
    SYNTAX      Unsigned32
    MAX-ACCESS  read-only
    STATUS      current
    DESCRIPTION
        "The value of tFPResDynQ2WredPoolTotal represents the total number of
         dynamic Q2 wred pools that are supported on this FP.

         When the value of tFPResDynQ2WredPoolTotal is zero, it indicates that
         this resource type is not supported on this FP."
    ::= { tFPResEntry 81 }

tFPResDynQ2WredPoolAlloc         OBJECT-TYPE
    SYNTAX      Unsigned32
    MAX-ACCESS  read-only
    STATUS      current
    DESCRIPTION
        "The value of tFPResDynQ2WredPoolAlloc represents the total number of
         dynamic Q2 wred pools that are currently allocated on this FP."
    ::= { tFPResEntry 82 }

tFPResIngIPv6AclFilterTotal      OBJECT-TYPE
    SYNTAX      Unsigned32
    MAX-ACCESS  read-only
    STATUS      current
    DESCRIPTION
        "The value of tFPResIngIPv6AclFilterTotal represents the total number
         of ingress IPv6 ACL filter policies that are supported on this FP.

         Note that on 7750 SR-c4/c12 the CPM enforced limit for the total
         number of ACL filter policies is lower than the value of this object."
    ::= { tFPResEntry 83 }

tFPResIngIPv6AclFilterAlloc      OBJECT-TYPE
    SYNTAX      Unsigned32
    MAX-ACCESS  read-only
    STATUS      current
    DESCRIPTION
        "The value of tFPResIngIPv6AclFilterAlloc represents the total number
         of ingress IPv6 ACL filter policies that are currently allocated on
         this FP."
    ::= { tFPResEntry 84 }

tFPResEgrIPv6AclFilterTotal      OBJECT-TYPE
    SYNTAX      Unsigned32
    MAX-ACCESS  read-only
    STATUS      current
    DESCRIPTION
        "The value of tFPResEgrIPv6AclFilterTotal represents the total number
         of egress IPv6 ACL filter policies that are supported on this FP.

         Note that on 7750 SR-c4/c12 the CPM enforced limit for the total
         number of ACL filter policies is lower than the value of this object."
    ::= { tFPResEntry 85 }

tFPResEgrIPv6AclFilterAlloc      OBJECT-TYPE
    SYNTAX      Unsigned32
    MAX-ACCESS  read-only
    STATUS      current
    DESCRIPTION
        "The value of tFPResEgrIPv6AclFilterAlloc represents the total number
         of egress IPv6 ACL filter policies that are currently allocated on
         this FP."
    ::= { tFPResEntry 86 }

tFPResEgrQosBypassTotal          OBJECT-TYPE
    SYNTAX      Unsigned32
    MAX-ACCESS  read-only
    STATUS      current
    DESCRIPTION
        "The value of tFPResEgrQosBypassTotal represents the total number of
         egress qos bypass entries that are supported on this FP.

         When the value of tFPResEgrQosBypassTotal is zero, it indicates that
         this resource type is not supported on this FP."
    ::= { tFPResEntry 87 }

tFPResEgrQosBypassAlloc          OBJECT-TYPE
    SYNTAX      Unsigned32
    MAX-ACCESS  read-only
    STATUS      current
    DESCRIPTION
        "The value of tFPResEgrQosBypassAlloc represents the total number of
         egress qos bypass entries that are currently allocated on this FP."
    ::= { tFPResEntry 88 }

tFPResSapInstanceTotal           OBJECT-TYPE
    SYNTAX      Unsigned32
    MAX-ACCESS  read-only
    STATUS      current
    DESCRIPTION
        "The value of tFPResSapInstanceTotal represents the total number of SAP
         instances that are supported on this FP.

         When the value of tFPResSapInstanceTotal is zero, it indicates that
         this resource type is not supported on this FP."
    ::= { tFPResEntry 89 }

tFPResSapInstanceAlloc           OBJECT-TYPE
    SYNTAX      Unsigned32
    MAX-ACCESS  read-only
    STATUS      current
    DESCRIPTION
        "The value of tFPResSapInstanceAlloc represents the total number of SAP
         instances that are currently allocated on this FP."
    ::= { tFPResEntry 90 }

tFPResEgrHsQGrpTotal             OBJECT-TYPE
    SYNTAX      Unsigned32
    MAX-ACCESS  read-only
    STATUS      current
    DESCRIPTION
        "The value of tFPResEgrHsQGrpTotal represents the total number of HS
         egress queue-group resources that are supported on this FP.

         When the value of tFPResEgrHsQGrpTotal is zero, it indicates that this
         resource type is not supported on this FP."
    ::= { tFPResEntry 91 }

tFPResEgrHsQGrpAlloc             OBJECT-TYPE
    SYNTAX      Unsigned32
    MAX-ACCESS  read-only
    STATUS      current
    DESCRIPTION
        "The value of tFPResEgrHsQGrpAlloc represents the total number of HS
         egress queue-group resources that are allocated on this FP."
    ::= { tFPResEntry 92 }

tFPResEgrHsPrimaryShapersTotal   OBJECT-TYPE
    SYNTAX      Unsigned32
    MAX-ACCESS  read-only
    STATUS      current
    DESCRIPTION
        "The value of tFPResEgrHsPrimaryShapersTotal represents the total
         number of HS Primary Shapers that are supported on this FP.

         When the value of tFPResEgrHsPrimaryShapersTotal is zero, it indicates
         that this resource type is not supported on this FP."
    ::= { tFPResEntry 93 }

tFPResEgrHsPrimaryShapersAlloc   OBJECT-TYPE
    SYNTAX      Unsigned32
    MAX-ACCESS  read-only
    STATUS      current
    DESCRIPTION
        "The value of tFPResEgrHsPrimaryShapersAlloc represents the total
         number of HS Primary Shapers that are allocated on this FP."
    ::= { tFPResEntry 94 }

tFPResEgrHsPrimaryShapersIUBES   OBJECT-TYPE
    SYNTAX      Unsigned32
    MAX-ACCESS  read-only
    STATUS      current
    DESCRIPTION
        "The value of tFPResEgrHsPrimaryShapersIUBES represents the subset of
         resources which are currently in use by HS Explicit Shapers out of
         currently allocated Primary Shapers."
    ::= { tFPResEntry 95 }

tFPResEgrHsPrimaryShapersIUBMS   OBJECT-TYPE
    SYNTAX      Unsigned32
    MAX-ACCESS  read-only
    STATUS      current
    DESCRIPTION
        "The value of tFPResEgrHsPrimaryShapersIUBMS represents the subset of
         resources which are currently in use by HS Managed Shapers out of
         currently allocated Primary Shapers."
    ::= { tFPResEntry 96 }

tFPResEgrHsSecondaryShapersTotal OBJECT-TYPE
    SYNTAX      Unsigned32
    MAX-ACCESS  read-only
    STATUS      current
    DESCRIPTION
        "The value of tFPResEgrHsSecondaryShapersTotal represents the total
         number of HS Secondary Shapers that are supported on this FP.

         When the value of tFPResEgrHsSecondaryShapersTotal is zero, it
         indicates that this resource type is not supported on this FP."
    ::= { tFPResEntry 97 }

tFPResEgrHsSecondaryShapersAlloc OBJECT-TYPE
    SYNTAX      Unsigned32
    MAX-ACCESS  read-only
    STATUS      current
    DESCRIPTION
        "The value of tFPResEgrHsSecondaryShapersAlloc represents the total
         number of HS Secondary Shapers that are allocated on this FP."
    ::= { tFPResEntry 98 }

tFPResEgrHsTurboQGrpTotal        OBJECT-TYPE
    SYNTAX      Unsigned32
    MAX-ACCESS  read-only
    STATUS      current
    DESCRIPTION
        "The value of tFPResEgrHsTurboQGrpTotal represents the total number of
         HS egress turbo queue-group resources that are supported on this FP.

         When the value of tFPResEgrHsTurboQGrpTotal is zero, it indicates that
         this resource type is not supported on this FP."
    ::= { tFPResEntry 99 }

tFPResEgrHsTurboQGrpAlloc        OBJECT-TYPE
    SYNTAX      Unsigned32
    MAX-ACCESS  read-only
    STATUS      current
    DESCRIPTION
        "The value of tFPResEgrHsTurboQGrpAlloc represents the total number of
         HS egress turbo queue-group resources that are allocated on this FP."
    ::= { tFPResEntry 100 }

tFPResIngQGrpRedirTotal          OBJECT-TYPE
    SYNTAX      Unsigned32
    MAX-ACCESS  read-only
    STATUS      current
    DESCRIPTION
        "The value of tFPResIngQGrpRedirTotal represents the total number of
         Ingress Queue Group Redirect List Entries that are supported on this
         FP.

         When the value of tFPResIngQGrpRedirTotal is zero, it indicates that
         this resource type is not supported on this FP."
    ::= { tFPResEntry 101 }

tFPResIngQGrpRedirAlloc          OBJECT-TYPE
    SYNTAX      Unsigned32
    MAX-ACCESS  read-only
    STATUS      current
    DESCRIPTION
        "The value of tFPResIngQGrpRedirAlloc represents the total number of
         Ingress Queue Group Redirect List Entries that are currently allocated
         on this FP."
    ::= { tFPResEntry 102 }

tFPResSapInstEgrQGrpRedirTotal   OBJECT-TYPE
    SYNTAX      Unsigned32
    MAX-ACCESS  read-only
    STATUS      current
    DESCRIPTION
        "The value of tFPResIngQGrpRedirTotal represents the total number of
         per-SAP instance Egress Queue Group Redirect List Entries that are
         supported on this FP.

         When the value of tFPResSapInstEgrQGrpRedirTotal is zero, it indicates
         that this resource type is not supported on this FP."
    ::= { tFPResEntry 103 }

tFPResSapInstEgrQGrpRedirAlloc   OBJECT-TYPE
    SYNTAX      Unsigned32
    MAX-ACCESS  read-only
    STATUS      current
    DESCRIPTION
        "The value of tFPResSapInstEgrQGrpRedirAlloc represents the total
         number of per-SAP instance Egress Queue Group Redirect List Entries
         that are currently allocated on this FP."
    ::= { tFPResEntry 104 }

tFPResEgrUserQueueTotal          OBJECT-TYPE
    SYNTAX      Unsigned32
    MAX-ACCESS  read-only
    STATUS      current
    DESCRIPTION
        "The value of tFPResEgrUserQueueTotal represents the total number of
         user provisionable egress queues that are supported on this FP.

         When the value of tFPResEgrUserQueueTotal is zero, it indicates that
         this resource type is not supported on this FP."
    ::= { tFPResEntry 105 }

tFPResEgrUserQueueAlloc          OBJECT-TYPE
    SYNTAX      Unsigned32
    MAX-ACCESS  read-only
    STATUS      current
    DESCRIPTION
        "The value of tFPResEgrUserQueueAlloc represents the total number of
         user provisionable egress queues that are currently allocated on this
         FP."
    ::= { tFPResEntry 106 }

tFPResEgrUserPolicerTotal        OBJECT-TYPE
    SYNTAX      Unsigned32
    MAX-ACCESS  read-only
    STATUS      current
    DESCRIPTION
        "The value of tFPResEgrUserPolicerTotal represents the total number of
         user provisionable egress policers that are supported on this FP.

         When the value of tFPResEgrUserPolicerTotal is zero, it indicates that
         this resource type is not supported on this FP."
    ::= { tFPResEntry 107 }

tFPResEgrUserPolicerAlloc        OBJECT-TYPE
    SYNTAX      Unsigned32
    MAX-ACCESS  read-only
    STATUS      current
    DESCRIPTION
        "The value of tFPResEgrUserPolicerAlloc represents the total number of
         user provisionable egress policers that are currently allocated on
         this FP."
    ::= { tFPResEntry 108 }

tFPResSLAProfileInstanceTotal    OBJECT-TYPE
    SYNTAX      Unsigned32
    MAX-ACCESS  read-only
    STATUS      current
    DESCRIPTION
        "The value of tFPResSLAProfileInstanceTotal represents the total number
         of subscriber SLA profile instances that are supported on this FP.

         When the value of tFPResSLAProfileInstanceTotal is zero, it indicates
         that this resource type is not supported on this FP."
    ::= { tFPResEntry 109 }

tFPResSLAProfileInstanceAlloc    OBJECT-TYPE
    SYNTAX      Unsigned32
    MAX-ACCESS  read-only
    STATUS      current
    DESCRIPTION
        "The value of tFPResSLAProfileInstanceAlloc represents the total number
         of subscriber SLA profile instances that are currently allocated on
         this FP."
    ::= { tFPResEntry 110 }

tFPResCamBanksTotal              OBJECT-TYPE
    SYNTAX      Unsigned32
    MAX-ACCESS  read-only
    STATUS      current
    DESCRIPTION
        "The value of tFPResCamBanksTotal represents the total number of CAM
         banks that are allowed to be in use on this FP."
    ::= { tFPResEntry 111 }

tFPResCamBanksAlloc              OBJECT-TYPE
    SYNTAX      Unsigned32
    MAX-ACCESS  read-only
    STATUS      current
    DESCRIPTION
        "The value of tFPResCamBanksAlloc represents the total number of CAM
         banks that are currently allocated on this FP."
    ::= { tFPResEntry 112 }

tFPResIngIPv4QosEntryTotal       OBJECT-TYPE
    SYNTAX      Unsigned32
    MAX-ACCESS  read-only
    STATUS      current
    DESCRIPTION
        "The value of tFPResIngIPv4QosEntryTotal represents the total number of
         ingress IPv4 QoS CAM entries that are supported on this FP.

         When the value of tFPResIngIPv4QosEntryTotal is zero, it indicates
         that this resource type is not supported on this FP."
    ::= { tFPResEntry 113 }

tFPResIngIPv4QosEntryAlloc       OBJECT-TYPE
    SYNTAX      Unsigned32
    MAX-ACCESS  read-only
    STATUS      current
    DESCRIPTION
        "The value of tFPResIngIPv4QosEntryAlloc represents the total number of
         ingress IPv4 QoS CAM entries that are currently allocated on this FP."
    ::= { tFPResEntry 114 }

tFPResIngMacQosEntryTotal        OBJECT-TYPE
    SYNTAX      Unsigned32
    MAX-ACCESS  read-only
    STATUS      current
    DESCRIPTION
        "The value of tFPResIngMacQosEntryTotal represents the total number of
         ingress MAC QoS CAM entries that are supported on this FP.

         When the value of tFPResIngMacQosEntryTotal is zero, it indicates that
         this resource type is not supported on this FP."
    ::= { tFPResEntry 115 }

tFPResIngMacQosEntryAlloc        OBJECT-TYPE
    SYNTAX      Unsigned32
    MAX-ACCESS  read-only
    STATUS      current
    DESCRIPTION
        "The value of tFPResIngMacQosEntryAlloc represents the total number of
         ingress MAC QoS CAM entries that are currently allocated on this FP."
    ::= { tFPResEntry 116 }

tFPResIngIPv4AclEntryTotal       OBJECT-TYPE
    SYNTAX      Unsigned32
    MAX-ACCESS  read-only
    STATUS      current
    DESCRIPTION
        "The value of tFPResIngIPv4AclEntryTotal represents the total number of
         ingress IPv4 ACL CAM entries that are supported on this FP.

         When the value of tFPResIngIPv4AclEntryTotal is zero, it indicates
         that this resource type is not supported on this FP."
    ::= { tFPResEntry 117 }

tFPResIngIPv4AclEntryAlloc       OBJECT-TYPE
    SYNTAX      Unsigned32
    MAX-ACCESS  read-only
    STATUS      current
    DESCRIPTION
        "The value of tFPResIngIPv4AclEntryAlloc represents the total number of
         ingress IPv4 ACL CAM entries that are currently allocated on this FP."
    ::= { tFPResEntry 118 }

tFPResIngMacAclEntryTotal        OBJECT-TYPE
    SYNTAX      Unsigned32
    MAX-ACCESS  read-only
    STATUS      current
    DESCRIPTION
        "The value of tFPResIngMacAclEntryTotal represents the total number of
         ingress MAC ACL CAM entries that are supported on this FP.

         When the value of tFPResIngMacAclEntryTotal is zero, it indicates that
         this resource type is not supported on this FP."
    ::= { tFPResEntry 119 }

tFPResIngMacAclEntryAlloc        OBJECT-TYPE
    SYNTAX      Unsigned32
    MAX-ACCESS  read-only
    STATUS      current
    DESCRIPTION
        "The value of tFPResIngMacAclEntryAlloc represents the total number of
         ingress MAC ACL CAM entries that are currently allocated on this FP."
    ::= { tFPResEntry 120 }

tFPResEgrIPv4AclEntryTotal       OBJECT-TYPE
    SYNTAX      Unsigned32
    MAX-ACCESS  read-only
    STATUS      current
    DESCRIPTION
        "The value of tFPResEgrIPv4AclEntryTotal represents the total number of
         egress IPv4 ACL CAM entries that are supported on this FP.

         When the value of tFPResEgrIPv4AclEntryTotal is zero, it indicates
         that this resource type is not supported on this FP."
    ::= { tFPResEntry 121 }

tFPResEgrIPv4AclEntryAlloc       OBJECT-TYPE
    SYNTAX      Unsigned32
    MAX-ACCESS  read-only
    STATUS      current
    DESCRIPTION
        "The value of tFPResEgrIPv4AclEntryAlloc represents the total number of
         egress IPv4 ACL CAM entries that are currently allocated on this FP."
    ::= { tFPResEntry 122 }

tFPResEgrMacAclEntryTotal        OBJECT-TYPE
    SYNTAX      Unsigned32
    MAX-ACCESS  read-only
    STATUS      current
    DESCRIPTION
        "The value of tFPResEgrMacAclEntryTotal represents the total number of
         egress MAC ACL CAM entries that are supported on this FP.

         When the value of tFPResEgrMacAclEntryTotal is zero, it indicates that
         this resource type is not supported on this FP."
    ::= { tFPResEntry 123 }

tFPResEgrMacAclEntryAlloc        OBJECT-TYPE
    SYNTAX      Unsigned32
    MAX-ACCESS  read-only
    STATUS      current
    DESCRIPTION
        "The value of tFPResEgrMacAclEntryAlloc represents the total number of
         egress MAC ACL CAM entries that are currently allocated on this FP."
    ::= { tFPResEntry 124 }

tFPResIngClassMapTotal           OBJECT-TYPE
    SYNTAX      Unsigned32
    MAX-ACCESS  read-only
    STATUS      current
    DESCRIPTION
        "The value of tFPResIngClassMapTotal represents the total number of
         ingress classification maps that are supported on this FP.

         When the value of tFPResIngClassMapTotal is zero, it indicates that
         this resource type is not supported on this FP."
    ::= { tFPResEntry 125 }

tFPResIngClassMapAlloc           OBJECT-TYPE
    SYNTAX      Unsigned32
    MAX-ACCESS  read-only
    STATUS      current
    DESCRIPTION
        "The value of tFPResIngClassMapAlloc represents the total number of
         ingress classification maps that are currently allocated on this FP."
    ::= { tFPResEntry 126 }

tFPResIngL2ClassMapTotal         OBJECT-TYPE
    SYNTAX      Unsigned32
    MAX-ACCESS  read-only
    STATUS      current
    DESCRIPTION
        "The value of tFPResIngL2ClassMapTotal represents the total number of
         ingress L2 classification maps that are supported on this FP.

         When the value of tFPResIngL2ClassMapTotal is zero, it indicates that
         this resource type is not supported on this FP."
    ::= { tFPResEntry 127 }

tFPResIngL2ClassMapAlloc         OBJECT-TYPE
    SYNTAX      Unsigned32
    MAX-ACCESS  read-only
    STATUS      current
    DESCRIPTION
        "The value of tFPResIngL2ClassMapAlloc represents the total number of
         ingress L2 classification maps that are currently allocated on this
         FP."
    ::= { tFPResEntry 128 }

tFPResEgrRemarkMapTotal          OBJECT-TYPE
    SYNTAX      Unsigned32
    MAX-ACCESS  read-only
    STATUS      current
    DESCRIPTION
        "The value of tFPResEgrRemarkMapTotal represents the total number of
         egress remark maps that are supported on this FP.

         When the value of tFPResEgrRemarkMapTotal is zero, it indicates that
         this resource type is not supported on this FP."
    ::= { tFPResEntry 129 }

tFPResEgrRemarkMapAlloc          OBJECT-TYPE
    SYNTAX      Unsigned32
    MAX-ACCESS  read-only
    STATUS      current
    DESCRIPTION
        "The value of tFPResEgrRemarkMapAlloc represents the total number of
         egress remark maps that are currently allocated on this FP."
    ::= { tFPResEntry 130 }

tFPResEgrExpRemarkMapTotal       OBJECT-TYPE
    SYNTAX      Unsigned32
    MAX-ACCESS  read-only
    STATUS      current
    DESCRIPTION
        "The value of tFPResEgrExpRemarkMapTotal represents the total number of
         egress lsp-exp remark maps that are supported on this FP.

         When the value of tFPResEgrExpRemarkMapTotal is zero, it indicates
         that this resource type is not supported on this FP."
    ::= { tFPResEntry 131 }

tFPResEgrExpRemarkMapAlloc       OBJECT-TYPE
    SYNTAX      Unsigned32
    MAX-ACCESS  read-only
    STATUS      current
    DESCRIPTION
        "The value of tFPResEgrExpRemarkMapAlloc represents the total number of
         egress lsp-esp remark maps that are currently allocated on this FP."
    ::= { tFPResEntry 132 }

tFPResIPv6McastEntryTotal        OBJECT-TYPE
    SYNTAX      Unsigned32
    MAX-ACCESS  read-only
    STATUS      current
    DESCRIPTION
        "The value of tFPResIPv6McastEntryTotal represents the total number of
         IPv6 multicast CAM entries reserved on this FP."
    ::= { tFPResEntry 133 }

tFPResIPv6McastEntryAlloc        OBJECT-TYPE
    SYNTAX      Unsigned32
    MAX-ACCESS  read-only
    STATUS      current
    DESCRIPTION
        "The value of tFPResIPv6McastEntryTotal represents the total number of
         IPv6 multicast CAM entries that are currently allocated on this FP."
    ::= { tFPResEntry 134 }

tFPResEgrDot1pDscpRemarkMapTotal OBJECT-TYPE
    SYNTAX      Unsigned32
    MAX-ACCESS  read-only
    STATUS      current
    DESCRIPTION
        "The value of tFPResEgrDot1pDscpRemarkMapTotal represents the total
         number of egress dot1p and dscp remark maps that are supported on this
         FP.

         When the value of tFPResEgrDot1pDscpRemarkMapTotal is zero, it
         indicates that this resource type is not supported on this FP."
    ::= { tFPResEntry 135 }

tFPResEgrDot1pDscpRemarkMapAlloc OBJECT-TYPE
    SYNTAX      Unsigned32
    MAX-ACCESS  read-only
    STATUS      current
    DESCRIPTION
        "The value of tFPResEgrDot1pDscpRemarkMapAlloc represents the total
         number of egress dot1p and dscp remark maps that are currently
         allocated on this FP."
    ::= { tFPResEntry 136 }

tFPResDot1xHostTotal             OBJECT-TYPE
    SYNTAX      Unsigned32
    MAX-ACCESS  read-only
    STATUS      current
    DESCRIPTION
        "The value of tFPResDot1xHostTotal represents the total number of dot1x
         authenticated hosts that are supported on this FP.

         When the value of tFPResDot1xHostTotal is zero, it indicates that this
         resource type is not supported on this FP.

         The value of tFPResDot1xHostTotal will always be less than or equal to
         tFPResDynSvcEntryTotal since dot1x authenticated host resources are
         subset of dynamic service entry resources."
    ::= { tFPResEntry 137 }

tFPResDot1xHostAlloc             OBJECT-TYPE
    SYNTAX      Unsigned32
    MAX-ACCESS  read-only
    STATUS      current
    DESCRIPTION
        "The value of tFPResDot1xHostAlloc represents the total number of dot1x
         authenticated hosts that are currently allocated on this FP.

         The value of tFPResDot1xHostAlloc will always be less than or equal to
         tFPResDynSvcEntryAlloc since dot1x authenticated host resources are
         subset of dynamic service entry resources."
    ::= { tFPResEntry 138 }

tFPResFastDepthMQueuesTotal      OBJECT-TYPE
    SYNTAX      Unsigned32
    MAX-ACCESS  read-only
    STATUS      current
    DESCRIPTION
        "The value of tFPResFastDepthMQueuesTotal represents the total number
         of fast polled queue depth monitored queue resources that are allowed
         to be provisioned on this FP.

         When the value of tFPResFastDepthMQueuesTotal is zero, it indicates
         that this resource type is not supported on this FP."
    ::= { tFPResEntry 139 }

tFPResFastDepthMQueuesAlloc      OBJECT-TYPE
    SYNTAX      Unsigned32
    MAX-ACCESS  read-only
    STATUS      current
    DESCRIPTION
        "The value of tFPResFastDepthMQueuesAlloc represents the total number
         of fast polled queue depth monitored queue resources that are
         currently provisioned on this FP."
    ::= { tFPResEntry 140 }

tFPResMepsWithIntMegTotal        OBJECT-TYPE
    SYNTAX      Unsigned32
    MAX-ACCESS  read-only
    STATUS      current
    DESCRIPTION
        "The value of tFPResMepsWithIntMegTotal indicates the total number of
         Maintenance End Points (MEP) of Maintenance Entity Groups (MEG) with
         tmnxDot1agCfmMaMgmtFormat being 'unsignedInt16' that are allowed to be
         provisioned on this FP."
    ::= { tFPResEntry 141 }

tFPResMepsWithIntMegAlloc        OBJECT-TYPE
    SYNTAX      Unsigned32
    MAX-ACCESS  read-only
    STATUS      current
    DESCRIPTION
        "The value of tFPResMepsWithIntMegAlloc indicates the total number of
         Maintenance End Points (MEPs) of Maintenance Entity Groups (MEG) with
         tmnxDot1agCfmMaMgmtFormat being 'unsignedInt16' that are currently
         provisioned on this FP."
    ::= { tFPResEntry 142 }

tFPResMepsWithIccMegTotal        OBJECT-TYPE
    SYNTAX      Unsigned32
    MAX-ACCESS  read-only
    STATUS      current
    DESCRIPTION
        "The value of tFPResMepsWithIccMegTotal indicates the total number of
         Maintenance End Points (MEP) of Maintenance Entity Groups (MEG) with
         tmnxDot1agCfmMaMgmtFormat being 'iccBased' that are allowed to be
         provisioned on this FP."
    ::= { tFPResEntry 143 }

tFPResMepsWithIccMegAlloc        OBJECT-TYPE
    SYNTAX      Unsigned32
    MAX-ACCESS  read-only
    STATUS      current
    DESCRIPTION
        "The value of tFPResMepsWithIccMegAlloc indicates the total number of
         Maintenance End Points (MEP) of Maintenance Entity Groups (MEG) with
         tmnxDot1agCfmMaMgmtFormat being 'iccBased' that are currently
         provisioned on this FP."
    ::= { tFPResEntry 144 }

tFPResMepsWithOtherMegTotal      OBJECT-TYPE
    SYNTAX      Unsigned32
    MAX-ACCESS  read-only
    STATUS      current
    DESCRIPTION
        "The value of tFPResMepsWithOtherMegTotal indicates the total number of
         Maintenance End Points (MEP) of Maintenance Entity Groups (MEG) with
         tmnxDot1agCfmMaMgmtFormat not being 'unsignedInt16' nor 'iccBased'
         that are allowed to be provisioned on this FP."
    ::= { tFPResEntry 145 }

tFPResMepsWithOtherMegAlloc      OBJECT-TYPE
    SYNTAX      Unsigned32
    MAX-ACCESS  read-only
    STATUS      current
    DESCRIPTION
        "The value of tFPResMepsWithOtherMegAlloc indicates the total number of
         Maintenance End Points (MEP) of Maintenance Entity Groups (MEG) with
         tmnxDot1agCfmMaMgmtFormat not being 'unsignedInt16' nor 'iccBased'
         that are currently provisioned on this FP."
    ::= { tFPResEntry 146 }

tFPResUniqueIccsForMepsTotal     OBJECT-TYPE
    SYNTAX      Unsigned32
    MAX-ACCESS  read-only
    STATUS      current
    DESCRIPTION
        "The value of tFPResUniqueIccsForMepsTotal indicates the total number
         of unique ICC values for the Maintenance End Points (MEP) that are
         allowed to be provisioned on this FP."
    ::= { tFPResEntry 147 }

tFPResUniqueIccsForMepsAlloc     OBJECT-TYPE
    SYNTAX      Unsigned32
    MAX-ACCESS  read-only
    STATUS      current
    DESCRIPTION
        "The value of tFPResUniqueIccsForMepsAlloc indicates the total number
         of unique ICC values for the Maintenance End Points (MEP) that are
         currently provisioned on this FP."
    ::= { tFPResEntry 148 }

tFPResPrefixesOfMepMacsTotal     OBJECT-TYPE
    SYNTAX      Unsigned32
    MAX-ACCESS  read-only
    STATUS      current
    DESCRIPTION
        "The value of tFPResPrefixesOfMepMacsTotal indicates the total number
         of Prefixes (5 bytes) of Maintenance End Points (MEP) Mac Addresses
         that are allowed to be provisioned on this FP."
    ::= { tFPResEntry 149 }

tFPResPrefixesOfMepMacsAlloc     OBJECT-TYPE
    SYNTAX      Unsigned32
    MAX-ACCESS  read-only
    STATUS      current
    DESCRIPTION
        "The value of tFPResPrefixesOfMepMacsAlloc indicates the total number
         of Prefixes (5 bytes) of Maintenance End Points (MEP) Mac Addresses
         that are currently provisioned on this FP."
    ::= { tFPResEntry 150 }

tFPResIngAclStatTotal            OBJECT-TYPE
    SYNTAX      Unsigned32
    MAX-ACCESS  read-only
    STATUS      current
    DESCRIPTION
        "The value of tFPResIngAclStatTotal indicates the total number of
         ingress ACL stats reserved on this FP.

         When the value of tFPResIngAclStatTotal is zero, it indicates that
         this resource type is not supported on this FP."
    ::= { tFPResEntry 151 }

tFPResIngAclStatAlloc            OBJECT-TYPE
    SYNTAX      Unsigned32
    MAX-ACCESS  read-only
    STATUS      current
    DESCRIPTION
        "The value of tFPResIngAclStatAlloc indicates the total number of
         ingress ACL stats that are currently allocated on this FP"
    ::= { tFPResEntry 152 }

tFPResEgrAclStatTotal            OBJECT-TYPE
    SYNTAX      Unsigned32
    MAX-ACCESS  read-only
    STATUS      current
    DESCRIPTION
        "The value of tFPResEgrAclStatTotal indicates the total number egress
         ACL stats reserved on this FP

         When the value of tFPResEgrAclStatTotal is zero, it indicates that
         this resource type is not supported on this FP."
    ::= { tFPResEntry 153 }

tFPResEgrAclStatAlloc            OBJECT-TYPE
    SYNTAX      Unsigned32
    MAX-ACCESS  read-only
    STATUS      current
    DESCRIPTION
        "The value of tFPResEgrAclStatAlloc indicates the total number egress
         ACL stats that are currently allocated on this FP"
    ::= { tFPResEntry 154 }

tFPResEgrHwAssignNonShaperQTotal OBJECT-TYPE
    SYNTAX      Unsigned32
    MAX-ACCESS  read-only
    STATUS      current
    DESCRIPTION
        "The value of tFPResEgrHwAssignNonShaperQTotal indicates the total
         number of assigned non shaper egress queues that are supported on this
         FP.

         When the value of tFPResEgrHwAssignNonShaperQTotal is zero, it
         indicates that this resource type is not supported on this FP."
    ::= { tFPResEntry 155 }

tFPResEgrHwAssignNonShaperQAlloc OBJECT-TYPE
    SYNTAX      Unsigned32
    MAX-ACCESS  read-only
    STATUS      current
    DESCRIPTION
        "The value of tFPResEgrHwAssignNonShaperQAlloc indicates the total
         number of non aggregate shaper egress queues that are currently
         allocated on this FP"
    ::= { tFPResEntry 156 }

tFPResEgrHwAggShapQSetSize8Total OBJECT-TYPE
    SYNTAX      Unsigned32
    MAX-ACCESS  read-only
    STATUS      current
    DESCRIPTION
        "The value of tFPResEgrHwAggShapQSetSize8Total indicates the total
         number of user provisionable size eight queue groups that are
         supported on this FP. Each Queue Group has a eight Queues allocated as
         part of single resource.

         When the value of tFPResEgrHwAggShapQSetSize8Total is zero, it
         indicates that this resource type is not supported on this FP."
    ::= { tFPResEntry 157 }

tFPResEgrHwAggShapQSetSize8Alloc OBJECT-TYPE
    SYNTAX      Unsigned32
    MAX-ACCESS  read-only
    STATUS      current
    DESCRIPTION
        "The value of tFPResEgrHwAggShapQSetSize8Alloc indicates the total
         number of user provisionable size eight queue groups that are
         currently allocated on this FP"
    ::= { tFPResEntry 158 }

tFPResEgrHwAggShapersTotal       OBJECT-TYPE
    SYNTAX      Unsigned32
    MAX-ACCESS  read-only
    STATUS      current
    DESCRIPTION
        "The value of tFPResEgrHwAggShapersTotal indicates the total number of
         user provisionable hardware aggregate shapers that are supported on
         this FP.

         When the value of tFPResEgrHwAggShapersTotal is zero, it indicates
         that this resource type is not supported on this FP."
    ::= { tFPResEntry 159 }

tFPResEgrHwAggShapersAlloc       OBJECT-TYPE
    SYNTAX      Unsigned32
    MAX-ACCESS  read-only
    STATUS      current
    DESCRIPTION
        "The value of tFPResEgrHwAggShapersAlloc indicates the total number of
         user provisionable hardware aggregate shapers that are currently
         allocated on this FP"
    ::= { tFPResEntry 160 }

tFPResEgrHwAggShaperSchedsTotal  OBJECT-TYPE
    SYNTAX      Unsigned32
    MAX-ACCESS  read-only
    STATUS      current
    DESCRIPTION
        "The value of tFPResEgrHwAggShaperSchedsTotal gives the total number of
         hardware aggregate shaper schedulers that are supported on this FP.
         When the value of tFPResEgrHwAggShaperSchedsTotal is zero then this
         means that this resource type is not supported on this FP."
    ::= { tFPResEntry 161 }

tFPResEgrHwAggShaperSchedsAlloc  OBJECT-TYPE
    SYNTAX      Unsigned32
    MAX-ACCESS  read-only
    STATUS      current
    DESCRIPTION
        "The value of tFPResEgrHwAggShaperSchedsAlloc gives the total number of
         hardware aggregate shaper schedulers that are currently allocated on
         this FP"
    ::= { tFPResEntry 162 }

tFPResIngClassProfileTotal       OBJECT-TYPE
    SYNTAX      Unsigned32
    MAX-ACCESS  read-only
    STATUS      current
    DESCRIPTION
        "The value of tFPResIngClassProfileTotal represents the total number of
         ingress classification profile that are supported on this FP.

         When the value of tFPResIngClassProfileTotal is zero, it indicates
         that this resource type is not supported on this FP."
    ::= { tFPResEntry 163 }

tFPResIngClassProfileAlloc       OBJECT-TYPE
    SYNTAX      Unsigned32
    MAX-ACCESS  read-only
    STATUS      current
    DESCRIPTION
        "The value of tFPResIngClassProfileAlloc represents the total number of
         ingress classification profile that are currently allocated on this
         FP."
    ::= { tFPResEntry 164 }

tFPResEgrRemarkProfileTotal      OBJECT-TYPE
    SYNTAX      Unsigned32
    MAX-ACCESS  read-only
    STATUS      current
    DESCRIPTION
        "The value of tFPResEgrRemarkProfileTotal represents the total number
         of egress remark policy profiles that are supported on this FP.

         When the value of tFPResEgrRemarkProfileTotal is zero, it indicates
         that this resource type is not supported on this FP."
    ::= { tFPResEntry 165 }

tFPResEgrRemarkProfileAlloc      OBJECT-TYPE
    SYNTAX      Unsigned32
    MAX-ACCESS  read-only
    STATUS      current
    DESCRIPTION
        "The value of tFPResEgrRemarkProfileAlloc represents the total number
         of egress remark policy profiles that are currently allocated on this
         FP."
    ::= { tFPResEntry 166 }

tFPResIngClassNonEpipeProfAlloc  OBJECT-TYPE
    SYNTAX      Unsigned32
    MAX-ACCESS  read-only
    STATUS      current
    DESCRIPTION
        "The value of tFPResIngClassNonEpipeProfAlloc represents the total
         number of non-epipe ingress classification profile that are supported
         on this FP.

         When the value of tFPResIngClassNonEpipeProfAlloc is zero, it
         indicates that this resource type is not supported on this FP."
    ::= { tFPResEntry 167 }

tFPResIngClassNonEpipeProfTotal  OBJECT-TYPE
    SYNTAX      Unsigned32
    MAX-ACCESS  read-only
    STATUS      current
    DESCRIPTION
        "The value of tFPResIngClassNonEpipeProfTotal represents the total
         number of non-epipe ingress classification profile that are currently
         allocated on this FP."
    ::= { tFPResEntry 168 }

tFPResOamSathTrafGenBandwAlloc   OBJECT-TYPE
    SYNTAX      Unsigned32
    UNITS       "kilobps"
    MAX-ACCESS  read-only
    STATUS      current
    DESCRIPTION
        "The value of tFPResOamSathTrafGenBandwAlloc indicates the in-use
         bandwidth dedicated to traffic generation for OAM service activation
         test runs on this FP.

         See the DESCRIPTION of tFPResOamSathTrafGenBandwTotal for more
         information."
    ::= { tFPResEntry 169 }

tFPResOamSathTrafGenBandwTotal   OBJECT-TYPE
    SYNTAX      Unsigned32
    UNITS       "kilobps"
    MAX-ACCESS  read-only
    STATUS      current
    DESCRIPTION
        "The value of tFPResOamSathTrafGenBandwTotal indicates the total
         supported bandwidth dedicated to traffic generation for OAM service
         activation test runs on this FP.

         An OAM service activation test run is started using
         TIMETRA-OAM-SERV-ACTIV-TEST-MIB::tmnxOamSathCfgSvcTestRunOprState.

         The bandwidth limit is enforced.
         For example, suppose
             tFPResOamSathTrafGenBandwTotal = 15,000,000 kilobps
             tFPResOamSathTrafGenBandwAlloc = 14,600,000 kilobps.
         Then, an attempt to start an OAM service activation test run (on this
         FP) needing 500,000 kilobps will be rejected."
    ::= { tFPResEntry 170 }

tFPResOamSathTrafGenSvcStrmAlloc OBJECT-TYPE
    SYNTAX      Unsigned32
    UNITS       "service-streams"
    MAX-ACCESS  read-only
    STATUS      current
    DESCRIPTION
        "The value of tFPResOamSathTrafGenSvcStrmAlloc indicates the in-use
         service-stream count for OAM service activation test runs on this FP.

         See the DESCRIPTION of tFPResOamSathTrafGenSvcStrmTotal for more
         information."
    ::= { tFPResEntry 171 }

tFPResOamSathTrafGenSvcStrmTotal OBJECT-TYPE
    SYNTAX      Unsigned32
    UNITS       "service-streams"
    MAX-ACCESS  read-only
    STATUS      current
    DESCRIPTION
        "The value of tFPResOamSathTrafGenSvcStrmTotal indicates the total
         supported service-stream count for OAM service activation test runs on
         this FP.

         An OAM service activation test run is started using
         TIMETRA-OAM-SERV-ACTIV-TEST-MIB::tmnxOamSathCfgSvcTestRunOprState.

         The limit is enforced.
         For example, suppose
             tFPResOamSathTrafGenSvcStrmTotal = 8 service-streams
             tFPResOamSathTrafGenSvcStrmAlloc = 7 service-streams.
         Then, an attempt to start an OAM service activation test run
         (on this FP) with two enabled service-streams will be rejected."
    ::= { tFPResEntry 172 }

tFPResFCDot1pMapIUBE             OBJECT-TYPE
    SYNTAX      Unsigned32
    MAX-ACCESS  read-only
    STATUS      current
    DESCRIPTION
        "The value of tFPResFCDot1pMapIUBE represents the total number of
         egress dot1p remark maps that are currently allocated on this FP."
    ::= { tFPResEntry 173 }

tFPResFCDscpMapIUBE              OBJECT-TYPE
    SYNTAX      Unsigned32
    MAX-ACCESS  read-only
    STATUS      current
    DESCRIPTION
        "The value of tFPResFCDscpMapIUBE represents the total number of egress
         dscp remark maps that are currently allocated on this FP."
    ::= { tFPResEntry 174 }

tFPResFCLspExpMapIUBE            OBJECT-TYPE
    SYNTAX      Unsigned32
    MAX-ACCESS  read-only
    STATUS      current
    DESCRIPTION
        "The value of tFPResFCLspExpMapIUBE represents the total number of
         egress exp class maps that are currently allocated on this FP."
    ::= { tFPResEntry 175 }

tFPResDot1pFCMapIUBI             OBJECT-TYPE
    SYNTAX      Unsigned32
    MAX-ACCESS  read-only
    STATUS      current
    DESCRIPTION
        "The value of tFPResDot1pFCMapIUBI represents the total number of
         ingress dot1p class maps that are currently allocated on this FP."
    ::= { tFPResEntry 176 }

tFPResDscpFCMapIUBI              OBJECT-TYPE
    SYNTAX      Unsigned32
    MAX-ACCESS  read-only
    STATUS      current
    DESCRIPTION
        "The value of tFPResDscpFCMapIUBI represents the total number of
         ingress dscp class maps that are currently allocated on this FP."
    ::= { tFPResEntry 177 }

tFPResLspExpFCMapIUBI            OBJECT-TYPE
    SYNTAX      Unsigned32
    MAX-ACCESS  read-only
    STATUS      current
    DESCRIPTION
        "The value of tFPResLspExpFCMapIUBI represents the total number of
         ingress exp class maps that are currently allocated on this FP."
    ::= { tFPResEntry 178 }

tFPResCamBanksIUBDot1xHostAuth   OBJECT-TYPE
    SYNTAX      Unsigned32
    MAX-ACCESS  read-only
    STATUS      current
    DESCRIPTION
        "The value of tFPResCamBanksIUBDot1xHostAuth represents the total
         number of CAM banks that are currently allocated on this FP for dot1x
         per host authentication."
    ::= { tFPResEntry 179 }

tFPResMacIPv4CamBanksTotal       OBJECT-TYPE
    SYNTAX      Unsigned32
    MAX-ACCESS  read-only
    STATUS      current
    DESCRIPTION
        "The value of tFPResMacIPv4CamBanksTotal represents the total number of
         CAM banks reserved for MAC and IPv4 filters on this FP."
    ::= { tFPResEntry 180 }

tFPResMacIPv4CamBanksAlloc       OBJECT-TYPE
    SYNTAX      Unsigned32
    MAX-ACCESS  read-only
    STATUS      current
    DESCRIPTION
        "The value of tFPResMacIPv4CamBanksAlloc represents the total number of
         CAM banks currently being used by MAC and IPv4 filters on this FP."
    ::= { tFPResEntry 181 }

tFPResIPv6CamBanksTotal          OBJECT-TYPE
    SYNTAX      Unsigned32
    MAX-ACCESS  read-only
    STATUS      current
    DESCRIPTION
        "The value of tFPResIPv6CamBanksTotal represents the total number of
         CAM banks reserved for IPv6 filters on this FP."
    ::= { tFPResEntry 182 }

tFPResIPv6CamBanksAlloc          OBJECT-TYPE
    SYNTAX      Unsigned32
    MAX-ACCESS  read-only
    STATUS      current
    DESCRIPTION
        "The value of tFPResIPv6CamBanksAlloc represents the total number of
         CAM banks currently being used by IPv6  filters on this FP."
    ::= { tFPResEntry 183 }

tFPResPortForwardingIdTotal      OBJECT-TYPE
    SYNTAX      Unsigned32
    MAX-ACCESS  read-only
    STATUS      current
    DESCRIPTION
        "The value of tFPResPortForwardingIdTotal indicates the total number of
         internal port forwarding ID resources available to be used by
         satellite, PXC and ESA ports that are supported on this FP.

         When the value of tFPResPortForwardingIdTotal is zero, it indicates
         that this resource type is not supported on this FP."
    ::= { tFPResEntry 184 }

tFPResPortForwardingIdAlloc      OBJECT-TYPE
    SYNTAX      Unsigned32
    MAX-ACCESS  read-only
    STATUS      current
    DESCRIPTION
        "The value of tFPResPortForwardingIdAlloc indicates the total number of
         internal port forwarding ID resources currently allocated on this FP"
    ::= { tFPResEntry 185 }

tFPResIngIPv4AclEntryIUBAcl      OBJECT-TYPE
    SYNTAX      Unsigned32
    MAX-ACCESS  read-only
    STATUS      current
    DESCRIPTION
        "The value of tFPResIngIPv4AclEntryIUBAcl represents the total number
         of ingress IPv4 ACL entries that are currently being used by ACLs."
    ::= { tFPResEntry 186 }

tFPResIngIPv4AclEntryIUBDcpu     OBJECT-TYPE
    SYNTAX      Unsigned32
    MAX-ACCESS  read-only
    STATUS      current
    DESCRIPTION
        "The value of tFPResIngIPv4AclEntryIUBDcpu represents the total number
         of ingress IPv4 ACL entries that are currently being used by
         distributed CPU protection."
    ::= { tFPResEntry 187 }

tFPResIngIPv4MacCamOverLoad      OBJECT-TYPE
    SYNTAX      TmnxCamOverloadState
    MAX-ACCESS  read-only
    STATUS      current
    DESCRIPTION
        "The value of tFPResIngIPv4MacCamOverLoad represents overload state of
         CAM currently being used by MAC and IPv4 filters on ingress on this
         FP."
    ::= { tFPResEntry 188 }

tFPResIngIPv6CamOverLoad         OBJECT-TYPE
    SYNTAX      TmnxCamOverloadState
    MAX-ACCESS  read-only
    STATUS      current
    DESCRIPTION
        "The value of tFPResIngIPv6CamOverLoad represents overload state of CAM
         currently being used by IPv6 filters on ingress on this FP."
    ::= { tFPResEntry 189 }

tFPResEgrIPv4MacCamOverLoad      OBJECT-TYPE
    SYNTAX      TmnxCamOverloadState
    MAX-ACCESS  read-only
    STATUS      current
    DESCRIPTION
        "The value of tFPResEgrIPv4MacCamOverLoad represents overload state of
         CAM currently being used by MAC and IPv4 filters on egress on this FP."
    ::= { tFPResEntry 190 }

tFPResEgrIPv6CamOverLoad         OBJECT-TYPE
    SYNTAX      TmnxCamOverloadState
    MAX-ACCESS  read-only
    STATUS      current
    DESCRIPTION
        "The value of tFPResEgrIPv6CamOverLoad represents overload state of CAM
         currently being used by IPv6 filters on egress on this FP."
    ::= { tFPResEntry 191 }

tFPResOversub                    OBJECT-TYPE
    SYNTAX      BITS {
        sramBuf             (0),
        sramPdb             (1),
        dramBdb             (2),
        dramBandwidth       (3),
        coreProcessPipeline (4),
        meshFabricBandwidth (5)
    }
    MAX-ACCESS  read-only
    STATUS      current
    DESCRIPTION
        "The value of tFPResOversub indicates which resources are
         oversubscribed on this FP. When no bits are set, none of the FP's
         resources are exhausted."
    ::= { tFPResEntry 192 }

tFPResEgrHwAggShapQSetSizeTotal  OBJECT-TYPE
    SYNTAX      Unsigned32
    MAX-ACCESS  read-only
    STATUS      obsolete
    DESCRIPTION
        "The value of tFPResEgrHwAggShapQSetSizeTotal indicates the total queue
         sets of default size at this FP.

         When the value of tFPResEgrHwAggShapQSetSizeTotal is zero, it
         indicates that this resource type is not supported on this FP."
    ::= { tFPResEntry 193 }

tFPResEgrHwAggShapQSetSizeAlloc  OBJECT-TYPE
    SYNTAX      Unsigned32
    MAX-ACCESS  read-only
    STATUS      obsolete
    DESCRIPTION
        "The value of tFPResEgrHwAggShapQSetSizeAlloc indicates the allocated
         queue sets of default size at this FP."
    ::= { tFPResEntry 194 }

tFPResEgrHwAggShpDefSapQSetSz    OBJECT-TYPE
    SYNTAX      Unsigned32
    MAX-ACCESS  read-only
    STATUS      current
    DESCRIPTION
        "The value of tFPResEgrHwAggShpDefSapQSetSz indicates default queue set
         size for this SAP at FP level when hardware aggregate shapers are
         enabled.

         When the value of tFPResEgrHwAggShpDefSapQSetSz is zero, it indicates
         non shaper queues. It can range between two to eight."
    ::= { tFPResEntry 195 }

tFPResEgrHwAggShpDefSubQSetSz    OBJECT-TYPE
    SYNTAX      Unsigned32
    MAX-ACCESS  read-only
    STATUS      current
    DESCRIPTION
        "The value of tFPResEgrHwAggShpDefSubQSetSz indicates default queue set
         size for this Subscriber at FP level when hardware aggregate shapers
         are enabled.

         When the value of tFPResEgrHwAggShpDefSubQSetSz is zero, it indicates
         non shaper queues. It can range between two to eight."
    ::= { tFPResEntry 196 }

tFPResEgrHwAggShpDefQGrpQSetSz   OBJECT-TYPE
    SYNTAX      Unsigned32
    MAX-ACCESS  read-only
    STATUS      current
    DESCRIPTION
        "The value of tFPResEgrHwAggShpDefQGrpQSetSz indicates default queue
         set size for this Queue Group at FP level when hardware aggregate
         shapers are enabled.

         When the value of tFPResEgrHwAggShpDefQGrpQSetSz is zero, it indicates
         non shaper queues. It can range between two to eight."
    ::= { tFPResEntry 197 }

tFPResCamBanksIUBSharedPlcrs     OBJECT-TYPE
    SYNTAX      Unsigned32
    MAX-ACCESS  read-only
    STATUS      current
    DESCRIPTION
        "The value of tFPResCamBanksIUBSharedPlcrs represents the total number
         of CAM banks that are currently reserved for shared policers on this
         FP."
    ::= { tFPResEntry 198 }

tFPResSharedPlcrCamBanksTotal    OBJECT-TYPE
    SYNTAX      Unsigned32
    MAX-ACCESS  read-only
    STATUS      current
    DESCRIPTION
        "The value of tFPResSharedPlcrCamBanksTotal represents the total number
         of CAM banks that can be used for shared policers on this FP."
    ::= { tFPResEntry 199 }

tFPResSharedPlcrCamBanksAlloc    OBJECT-TYPE
    SYNTAX      Unsigned32
    MAX-ACCESS  read-only
    STATUS      current
    DESCRIPTION
        "The value of tFPResSharedPlcrCamBanksAlloc represents the total number
         of CAM banks currently being used by shared policers on this FP."
    ::= { tFPResEntry 200 }

tFPResSharedPlcrCamEntryTotal    OBJECT-TYPE
    SYNTAX      Unsigned32
    MAX-ACCESS  read-only
    STATUS      current
    DESCRIPTION
        "The value of tFPResSharedPlcrCamEntryTotal represents the total number
         of CAM entries on this FP that are reserved for shared policers.

         When the value of tFPResSharedPlcrCamEntryTotal is zero, it indicates
         that this resource type is not supported on this FP."
    ::= { tFPResEntry 201 }

tFPResSharedPlcrCamEntryAlloc    OBJECT-TYPE
    SYNTAX      Unsigned32
    MAX-ACCESS  read-only
    STATUS      current
    DESCRIPTION
        "The value of tFPResSharedPlcrCamEntryAlloc represents the total number
         of CAM entries that are currently allocated for shared policers on
         this FP."
    ::= { tFPResEntry 202 }

tFPResCamBanksIUBSrv6TunnelTerm  OBJECT-TYPE
    SYNTAX      Unsigned32
    MAX-ACCESS  read-only
    STATUS      current
    DESCRIPTION
        "The value of tFPResCamBanksIUBSrv6TunnelTerm represents the total
         number of large CAM banks that are currently allocated on this FP for
         srv6 tunnel termination."
    ::= { tFPResEntry 203 }

tFPResEgrHwAggShapQSetSize1Total OBJECT-TYPE
    SYNTAX      Unsigned32
    MAX-ACCESS  read-only
    STATUS      obsolete
    DESCRIPTION
        "The value of tFPResEgrHwAggShapQSetSize1Total indicates the total
         number of user provisionable size one queue set resources on this FP.

         When the value of tFPResEgrHwAggShapQSetSize1Total is zero, it
         indicates that this resource type is not supported on this FP."
    ::= { tFPResEntry 204 }

tFPResEgrHwAggShapQSetSize1Alloc OBJECT-TYPE
    SYNTAX      Unsigned32
    MAX-ACCESS  read-only
    STATUS      obsolete
    DESCRIPTION
        "The value of tFPResEgrHwAggShapQSetSize1Alloc indicates the allocated
         number of user provisionable size one queue set resources on this FP."
    ::= { tFPResEntry 205 }

tFPResEgrHwAggShapQSetSize2Total OBJECT-TYPE
    SYNTAX      Unsigned32
    MAX-ACCESS  read-only
    STATUS      current
    DESCRIPTION
        "The value of tFPResEgrHwAggShapQSetSize2Total indicates the total
         number of user provisionable size two queue set resources on this FP.

         When the value of tFPResEgrHwAggShapQSetSize2Total is zero, it
         indicates that this resource type is not supported on this FP."
    ::= { tFPResEntry 206 }

tFPResEgrHwAggShapQSetSize2Alloc OBJECT-TYPE
    SYNTAX      Unsigned32
    MAX-ACCESS  read-only
    STATUS      current
    DESCRIPTION
        "The value of tFPResEgrHwAggShapQSetSize2Alloc indicates the allocated
         number of user provisionable size two queue set resources on this FP."
    ::= { tFPResEntry 207 }

tFPResEgrHwAggShapQSetSize3Total OBJECT-TYPE
    SYNTAX      Unsigned32
    MAX-ACCESS  read-only
    STATUS      current
    DESCRIPTION
        "The value of tFPResEgrHwAggShapQSetSize3Total indicates the total
         number of user provisionable size three queue set resources on this
         FP.

         When the value of tFPResEgrHwAggShapQSetSize3Total is zero, it
         indicates that this resource type is not supported on this FP."
    ::= { tFPResEntry 208 }

tFPResEgrHwAggShapQSetSize3Alloc OBJECT-TYPE
    SYNTAX      Unsigned32
    MAX-ACCESS  read-only
    STATUS      current
    DESCRIPTION
        "The value of tFPResEgrHwAggShapQSetSize3Alloc indicates the allocated
         number of user provisionable size three queue set resources on this
         FP."
    ::= { tFPResEntry 209 }

tFPResEgrHwAggShapQSetSize4Total OBJECT-TYPE
    SYNTAX      Unsigned32
    MAX-ACCESS  read-only
    STATUS      current
    DESCRIPTION
        "The value of tFPResEgrHwAggShapQSetSize4Total indicates the total
         number of user provisionable size four queue set resources on this FP.

         When the value of tFPResEgrHwAggShapQSetSize4Total is zero, it
         indicates that this resource type is not supported on this FP."
    ::= { tFPResEntry 210 }

tFPResEgrHwAggShapQSetSize4Alloc OBJECT-TYPE
    SYNTAX      Unsigned32
    MAX-ACCESS  read-only
    STATUS      current
    DESCRIPTION
        "The value of tFPResEgrHwAggShapQSetSize4Alloc indicates the allocated
         number of user provisionable size four queue set resources on this FP."
    ::= { tFPResEntry 211 }

tFPResEgrHwAggShapQSetSize5Total OBJECT-TYPE
    SYNTAX      Unsigned32
    MAX-ACCESS  read-only
    STATUS      current
    DESCRIPTION
        "The value of tFPResEgrHwAggShapQSetSize5Total indicates the total
         number of user provisionable size five queue set resources on this FP.

         When the value of tFPResEgrHwAggShapQSetSize5Total is zero, it
         indicates that this resource type is not supported on this FP."
    ::= { tFPResEntry 212 }

tFPResEgrHwAggShapQSetSize5Alloc OBJECT-TYPE
    SYNTAX      Unsigned32
    MAX-ACCESS  read-only
    STATUS      current
    DESCRIPTION
        "The value of tFPResEgrHwAggShapQSetSize5Alloc indicates the allocated
         number of user provisionable size five queue set resources on this FP."
    ::= { tFPResEntry 213 }

tFPResEgrHwAggShapQSetSize6Total OBJECT-TYPE
    SYNTAX      Unsigned32
    MAX-ACCESS  read-only
    STATUS      current
    DESCRIPTION
        "The value of tFPResEgrHwAggShapQSetSize6Total indicates the total
         number of user provisionable size six queue set resources on this FP.

         When the value of tFPResEgrHwAggShapQSetSize6Total is zero, it
         indicates that this resource type is not supported on this FP."
    ::= { tFPResEntry 214 }

tFPResEgrHwAggShapQSetSize6Alloc OBJECT-TYPE
    SYNTAX      Unsigned32
    MAX-ACCESS  read-only
    STATUS      current
    DESCRIPTION
        "The value of tFPResEgrHwAggShapQSetSize6Alloc indicates the allocated
         number of user provisionable size six queue set resources on this FP."
    ::= { tFPResEntry 215 }

tFPResEgrHwAggShapQSetSize7Total OBJECT-TYPE
    SYNTAX      Unsigned32
    MAX-ACCESS  read-only
    STATUS      current
    DESCRIPTION
        "The value of tFPResEgrHwAggShapQSetSize7Total indicates the total
         number of user provisionable size seven queue set resources on this
         FP.

         When the value of tFPResEgrHwAggShapQSetSize7Total is zero, it
         indicates that this resource type is not supported on this FP."
    ::= { tFPResEntry 216 }

tFPResEgrHwAggShapQSetSize7Alloc OBJECT-TYPE
    SYNTAX      Unsigned32
    MAX-ACCESS  read-only
    STATUS      current
    DESCRIPTION
        "The value of tFPResEgrHwAggShapQSetSize7Alloc indicates the allocated
         number of user provisionable size seven queue set resources on this
         FP."
    ::= { tFPResEntry 217 }

tFPResDCpuProtCamEntryTotal      OBJECT-TYPE
    SYNTAX      Unsigned32
    MAX-ACCESS  read-only
    STATUS      current
    DESCRIPTION
        "The value of tFPResDCpuProtCamEntryTotal represents the total number
         of distributed CPU protection CAM entries that are supported on this
         FP."
    ::= { tFPResEntry 218 }

tFPResDCpuProtCamEntryAlloc      OBJECT-TYPE
    SYNTAX      Unsigned32
    MAX-ACCESS  read-only
    STATUS      current
    DESCRIPTION
        "The value of tFPResDCpuProtCamEntryAlloc represents the total number
         of distributed CPU protection CAM entries that are currently allocated
         on this FP."
    ::= { tFPResEntry 219 }

tFPResSapIngAggPolicerTotal      OBJECT-TYPE
    SYNTAX      Unsigned32
    MAX-ACCESS  read-only
    STATUS      current
    DESCRIPTION
        "The value of tFPResSapIngAggPolicerTotal represents the total number
         of SAP ingress aggregate policers that are supported on this FP"
    ::= { tFPResEntry 220 }

tFPResSapIngAggPolicerAlloc      OBJECT-TYPE
    SYNTAX      Unsigned32
    MAX-ACCESS  read-only
    STATUS      current
    DESCRIPTION
        "The value of tFPResSapIngAggPolicerAlloc represents the total number
         of SAP ingress aggregate policers that are currently allocated on this
         FP"
    ::= { tFPResEntry 221 }

tFPResBfdMhopIPv4CamEntryTotal   OBJECT-TYPE
    SYNTAX      Unsigned32
    MAX-ACCESS  read-only
    STATUS      current
    DESCRIPTION
        "The value of tFPResBfdMhopIPv4CamEntryTotal represents the total
         number of IPv4 multi-hop BFD CAM entries that are supported on this
         FP."
    ::= { tFPResEntry 222 }

tFPResBfdMhopIPv4CamEntryAlloc   OBJECT-TYPE
    SYNTAX      Unsigned32
    MAX-ACCESS  read-only
    STATUS      current
    DESCRIPTION
        "The value of tFPResBfdMhopIPv4CamEntryAlloc represents the total
         number of IPv4 multi-hop BFD CAM entries that are currently allocated
         on this FP."
    ::= { tFPResEntry 223 }

tFPResBfdMhopIPv6CamEntryTotal   OBJECT-TYPE
    SYNTAX      Unsigned32
    MAX-ACCESS  read-only
    STATUS      current
    DESCRIPTION
        "The value of tFPResBfdMhopIPv6CamEntryTotal represents the total
         number of IPv6 multi-hop BFD CAM entries that are supported on this
         FP."
    ::= { tFPResEntry 224 }

tFPResBfdMhopIPv6CamEntryAlloc   OBJECT-TYPE
    SYNTAX      Unsigned32
    MAX-ACCESS  read-only
    STATUS      current
    DESCRIPTION
        "The value of tFPResBfdMhopIPv6CamEntryAlloc represents the total
         number of IPv6 multi-hop BFD CAM entries that are currently allocated
         on this FP."
    ::= { tFPResEntry 225 }

tFPResCamBanksIUBSeamlessBfd     OBJECT-TYPE
    SYNTAX      Unsigned32
    MAX-ACCESS  read-only
    STATUS      current
    DESCRIPTION
        "The value of tFPResCamBanksIUBSeamlessBfd represents the total number
         of large CAM banks that are currently allocated on this FP for
         seamless BFD."
    ::= { tFPResEntry 226 }

tFPResCamBanksIUBEthStormControl OBJECT-TYPE
    SYNTAX      Unsigned32
    MAX-ACCESS  read-only
    STATUS      current
    DESCRIPTION
        "The value of tFPResCamBanksIUBEthStormControl represents the total
         number of CAM banks that are currently allocated on this FP for
         ethernet storm control."
    ::= { tFPResEntry 227 }

tFPResEthStormCtrlCamBanksTotal  OBJECT-TYPE
    SYNTAX      Unsigned32
    MAX-ACCESS  read-only
    STATUS      current
    DESCRIPTION
        "The value of tFPResEthStormCtrlCamBanksTotal represents the total
         number of CAM banks that can be used for ethernet storm control on
         this FP."
    ::= { tFPResEntry 228 }

tFPResEthStormCtrlCamBanksAlloc  OBJECT-TYPE
    SYNTAX      Unsigned32
    MAX-ACCESS  read-only
    STATUS      current
    DESCRIPTION
        "The value of tFPResEthStormCtrlCamBanksAlloc represents the total
         number of CAM banks currently being used for ethernet storm control on
         this FP."
    ::= { tFPResEntry 229 }

tFPResEthStormCtrlCamEntryTotal  OBJECT-TYPE
    SYNTAX      Unsigned32
    MAX-ACCESS  read-only
    STATUS      current
    DESCRIPTION
        "The value of tFPResEthStormCtrlCamEntryTotal represents the total
         number of CAM entries that are reserved for ethernet storm control on
         this FP."
    ::= { tFPResEntry 230 }

tFPResEthStormCtrlCamEntryAlloc  OBJECT-TYPE
    SYNTAX      Unsigned32
    MAX-ACCESS  read-only
    STATUS      current
    DESCRIPTION
        "The value of tFPResEthStormCtrlCamEntryAlloc represents the total
         number of CAM banks that are currently allocated for ethernet storm
         control on this FP."
    ::= { tFPResEntry 231 }

tMDAResTable                     OBJECT-TYPE
    SYNTAX      SEQUENCE OF TMDAResEntry
    MAX-ACCESS  not-accessible
    STATUS      current
    DESCRIPTION
        "The value of tMDAResTable represents system resource information that
         are specific to MDA for a particular card on a given chassis."
    ::= { tmnxCardObjs 47 }

tMDAResEntry                     OBJECT-TYPE
    SYNTAX      TMDAResEntry
    MAX-ACCESS  not-accessible
    STATUS      current
    DESCRIPTION
        "The value of tMDAResEntry represents MDA specific system resource
         information."
    INDEX       {
        tmnxChassisIndex,
        tmnxCardSlotNum,
        tmnxMDASlotNum
    }
    ::= { tMDAResTable 1 }

TMDAResEntry                     ::= SEQUENCE
{
    tMDAResSapInstanceTotal          Unsigned32,
    tMDAResSapInstanceAlloc          Unsigned32,
    tMDAResPortForwardingIdTotal     Unsigned32,
    tMDAResPortForwardingIdAlloc     Unsigned32
}

tMDAResSapInstanceTotal          OBJECT-TYPE
    SYNTAX      Unsigned32
    MAX-ACCESS  read-only
    STATUS      current
    DESCRIPTION
        "The value of tMDAResSapInstanceTotal represents the total number of
         SAP instances that are supported on this MDA.

         When the value of tMDAResSapInstanceTotal is zero, it indicates that
         this resource type is not supported on this MDA."
    ::= { tMDAResEntry 5 }

tMDAResSapInstanceAlloc          OBJECT-TYPE
    SYNTAX      Unsigned32
    MAX-ACCESS  read-only
    STATUS      current
    DESCRIPTION
        "The value of tMDAResSapInstanceAlloc represents the total number of
         SAP instances that are currently allocated on this MDA."
    ::= { tMDAResEntry 6 }

tMDAResPortForwardingIdTotal     OBJECT-TYPE
    SYNTAX      Unsigned32
    MAX-ACCESS  read-only
    STATUS      current
    DESCRIPTION
        "The value of tMDAResPortForwardingIdTotal indicates the total number
         of internal port forwarding ID resources available to be used by
         satellite, PXC and ESA ports that are supported on this MDA.

         When the value of tMDAResPortForwardingIdTotal is zero, it indicates
         that this resource type is not supported on this MDA."
    ::= { tMDAResEntry 7 }

tMDAResPortForwardingIdAlloc     OBJECT-TYPE
    SYNTAX      Unsigned32
    MAX-ACCESS  read-only
    STATUS      current
    DESCRIPTION
        "The value of tMDAResPortForwardingIdAlloc indicates the total number
         of internal port forwarding ID resources currently allocated on this
         MDA"
    ::= { tMDAResEntry 8 }

tFPEgressFwdEngDRStatsTable      OBJECT-TYPE
    SYNTAX      SEQUENCE OF TFPEgressFwdEngDRStatsEntry
    MAX-ACCESS  not-accessible
    STATUS      current
    DESCRIPTION
        "The value of tFPEgressFwdEngDRStatsTable specifies per-reason drop
         statistics for the packets dropped by the forwarding engine."
    ::= { tmnxCardObjs 52 }

tFPEgressFwdEngDRStatsEntry      OBJECT-TYPE
    SYNTAX      TFPEgressFwdEngDRStatsEntry
    MAX-ACCESS  not-accessible
    STATUS      current
    DESCRIPTION
        "The value of tFPEgressFwdEngDRStatsEntry specifies per-reason drop
         statistics for the packets dropped by the forwarding engine."
    INDEX       {
        tmnxChassisIndex,
        tmnxCardSlotNum,
        tmnxFPNum
    }
    ::= { tFPEgressFwdEngDRStatsTable 1 }

TFPEgressFwdEngDRStatsEntry      ::= SEQUENCE
{
    tFwdEngDREgrEncapExceeded        Counter64,
    tFwdEngDREgrMtuExceeded          Counter64,
    tFwdEngDREgrPortMtuExceeded      Counter64
}

tFwdEngDREgrEncapExceeded        OBJECT-TYPE
    SYNTAX      Counter64
    MAX-ACCESS  read-only
    STATUS      current
    DESCRIPTION
        "The value of tFwdEngDREgrEncapExceeded indicates the total number of
         packets dropped by the forwarding engine due to the packet header size
         exceeding the egress encapsulation limit."
    ::= { tFPEgressFwdEngDRStatsEntry 1 }

tFwdEngDREgrMtuExceeded          OBJECT-TYPE
    SYNTAX      Counter64
    MAX-ACCESS  read-only
    STATUS      current
    DESCRIPTION
        "The value of tFwdEngDREgrMtuExceeded indicates the total number of
         exceptions at egress that need an ICMP cannot fragment response."
    ::= { tFPEgressFwdEngDRStatsEntry 2 }

tFwdEngDREgrPortMtuExceeded      OBJECT-TYPE
    SYNTAX      Counter64
    MAX-ACCESS  read-only
    STATUS      current
    DESCRIPTION
        "The value of tFwdEngDREgrPortMtuExceeded indicates the total number of
         packets dropped by the forwarding engine due to the final frame
         exceeding the port MTU size."
    ::= { tFPEgressFwdEngDRStatsEntry 3 }

tmnxCardVFpStatsTable            OBJECT-TYPE
    SYNTAX      SEQUENCE OF TmnxCardVFpStatsEntry
    MAX-ACCESS  not-accessible
    STATUS      current
    DESCRIPTION
        "The value of tmnxCardVFpStatsTable contains CPU statistics for the
         virtual forwarding plane (vFP) of a given card."
    ::= { tmnxCardObjs 53 }

tmnxCardVFpStatsEntry            OBJECT-TYPE
    SYNTAX      TmnxCardVFpStatsEntry
    MAX-ACCESS  not-accessible
    STATUS      current
    DESCRIPTION
        "The value of tmnxCardVFpStatsEntry consists of CPU statistics for a
         virtual forwarding plane (vFP) task on a card."
    INDEX       {
        tmnxChassisIndex,
        tmnxCardSlotNum,
        tmnxCardVFpTaskType
    }
    ::= { tmnxCardVFpStatsTable 1 }

TmnxCardVFpStatsEntry            ::= SEQUENCE
{
    tmnxCardVFpTaskType              INTEGER,
    tmnxCardVFpCpuCount              Unsigned32,
    tmnxCardVFpAvgUtilization        Unsigned32,
    tmnxCardVFpMaxUtilization        Unsigned32
}

tmnxCardVFpTaskType              OBJECT-TYPE
    SYNTAX      INTEGER {
        nic       (1),
        worker    (2),
        scheduler (3),
        collapsed (4),
        combined  (5),
        dispatch  (6),
        bman      (7)
    }
    MAX-ACCESS  not-accessible
    STATUS      current
    DESCRIPTION
        "The value of tmnxCardVFpTaskType specifies the virtual forwarding
         plane (vFP) task type.

         Values:
            nic       - task includes only network interface card work
            worker    - task includes only worker work
            scheduler - task includes only scheduler work
            collapsed - task includes NIC and scheduler work
            combined  - task includes NIC, scheduler and worker work
            dispatch  - task includes only dispatcher work
            bman      - task includes only buffer manager work"
    ::= { tmnxCardVFpStatsEntry 1 }

tmnxCardVFpCpuCount              OBJECT-TYPE
    SYNTAX      Unsigned32
    MAX-ACCESS  read-only
    STATUS      current
    DESCRIPTION
        "The value of tmnxCardVFpCpuCount indicates the number of virtual CPUs
         that the vFP task is running on for the card."
    ::= { tmnxCardVFpStatsEntry 2 }

tmnxCardVFpAvgUtilization        OBJECT-TYPE
    SYNTAX      Unsigned32
    UNITS       "centipercent"
    MAX-ACCESS  read-only
    STATUS      current
    DESCRIPTION
        "The value of tmnxCardVFpAvgUtilization indicates the average CPU
         utilization of the vFP task on the card."
    ::= { tmnxCardVFpStatsEntry 3 }

tmnxCardVFpMaxUtilization        OBJECT-TYPE
    SYNTAX      Unsigned32
    UNITS       "centipercent"
    MAX-ACCESS  read-only
    STATUS      current
    DESCRIPTION
        "The value of tmnxCardVFpMaxUtilization indicates the maximum CPU
         utilization of the vFP task on the card."
    ::= { tmnxCardVFpStatsEntry 4 }

tmnxCardVCpuSchedStatsTable      OBJECT-TYPE
    SYNTAX      SEQUENCE OF TmnxCardVCpuSchedStatsEntry
    MAX-ACCESS  not-accessible
    STATUS      current
    DESCRIPTION
        "The value of tmnxCardVCpuSchedStatsTable contains virtual CPU
         scheduling statistics for a given card."
    ::= { tmnxCardObjs 54 }

tmnxCardVCpuSchedStatsEntry      OBJECT-TYPE
    SYNTAX      TmnxCardVCpuSchedStatsEntry
    MAX-ACCESS  not-accessible
    STATUS      current
    DESCRIPTION
        "The value of tmnxCardVCpuSchedStatsEntry consists of virtual CPU
         scheduling statistics for a card."
    INDEX       {
        tmnxChassisIndex,
        tmnxCardSlotNum
    }
    ::= { tmnxCardVCpuSchedStatsTable 1 }

TmnxCardVCpuSchedStatsEntry      ::= SEQUENCE
{
    tmnxCardVCpuSchedHealth          Unsigned32,
    tmnxCardVCpuSchedLastClearedTime TimeStamp
}

tmnxCardVCpuSchedHealth          OBJECT-TYPE
    SYNTAX      Unsigned32
    UNITS       "centipercent"
    MAX-ACCESS  read-only
    STATUS      current
    DESCRIPTION
        "The value of tmnxCardVCpuSchedHealth indicates the scheduling health
         of the virtual CPU on the card."
    ::= { tmnxCardVCpuSchedStatsEntry 1 }

tmnxCardVCpuSchedLastClearedTime OBJECT-TYPE
    SYNTAX      TimeStamp
    MAX-ACCESS  read-only
    STATUS      current
    DESCRIPTION
        "The value of tmnxCardVCpuSchedLastClearedTime indicates the time,
         since system startup, when tmnxCardVCpuSchedStatsEntry was last
         cleared."
    ::= { tmnxCardVCpuSchedStatsEntry 2 }

tmnxCardComplexStatsTable        OBJECT-TYPE
    SYNTAX      SEQUENCE OF TmnxCardComplexStatsEntry
    MAX-ACCESS  not-accessible
    STATUS      current
    DESCRIPTION
        "The tmnxCardComplexStatsTable contains statistics for all the IOM
         complexes in the system."
    ::= { tmnxCardObjs 55 }

tmnxCardComplexStatsEntry        OBJECT-TYPE
    SYNTAX      TmnxCardComplexStatsEntry
    MAX-ACCESS  not-accessible
    STATUS      current
    DESCRIPTION
        "The tmnxCardComplexStatsEntry consists of statistics for the given
         complex and given IOM card."
    INDEX       {
        tmnxCardSlotNum,
        tmnxCardComplexNum
    }
    ::= { tmnxCardComplexStatsTable 1 }

TmnxCardComplexStatsEntry        ::= SEQUENCE
{
    tmnxCardComplexNum               Unsigned32,
    tmnxCardComplexIngFcsError       Counter32,
    tmnxCardComplexIngFcsErrTime     TimeStamp,
    tmnxCardComplexEgrFcsError       Counter32,
    tmnxCardComplexEgrFcsErrTime     TimeStamp,
    tmnxCardComplexMemParError       Counter32,
    tmnxCardComplexMemParErrTime     TimeStamp,
    tmnxCardComplexCamError          Counter32,
    tmnxCardComplexCamErrTime        TimeStamp,
    tmnxCardComplexBufMemError       Counter32,
    tmnxCardComplexBufMemErrTime     TimeStamp,
    tmnxCardComplexStatsMemError     Counter32,
    tmnxCardComplexStatsMemErrTime   TimeStamp,
    tmnxCardComplexIntMemError       Counter32,
    tmnxCardComplexIntMemErrTime     TimeStamp,
    tmnxCardComplexIntDatapathError  Counter32,
    tmnxCardComplexIntDatapthErrTime TimeStamp,
    tmnxCardComplexIntDpCellError    Counter32,
    tmnxCardComplexIntDpCellErrTime  TimeStamp,
    tmnxCardComplexSrcSlotsEgFcsErr  TmnxCardSlotBitMap
}

tmnxCardComplexNum               OBJECT-TYPE
    SYNTAX      Unsigned32
    MAX-ACCESS  not-accessible
    STATUS      current
    DESCRIPTION
        "The value of tmnxCardComplexNum specifies the number which uniquely
         identifies the complex on the IOM card."
    ::= { tmnxCardComplexStatsEntry 1 }

tmnxCardComplexIngFcsError       OBJECT-TYPE
    SYNTAX      Counter32
    MAX-ACCESS  read-only
    STATUS      current
    DESCRIPTION
        "The value of tmnxCardComplexIngFcsError indicates the number of times
         the complex experienced a FCS error in the ingress direction since
         startup, last clear, or card reboot."
    ::= { tmnxCardComplexStatsEntry 2 }

tmnxCardComplexIngFcsErrTime     OBJECT-TYPE
    SYNTAX      TimeStamp
    MAX-ACCESS  read-only
    STATUS      current
    DESCRIPTION
        "The value of tmnxCardComplexIngFcsErrTime indicates the last time
         tmnxCardComplexIngFcsError incremented."
    ::= { tmnxCardComplexStatsEntry 3 }

tmnxCardComplexEgrFcsError       OBJECT-TYPE
    SYNTAX      Counter32
    MAX-ACCESS  read-only
    STATUS      current
    DESCRIPTION
        "The value of tmnxCardComplexEgrFcsError indicates the number of times
         the complex experienced a FCS error in the egress direction since
         startup, last clear, or card reboot."
    ::= { tmnxCardComplexStatsEntry 4 }

tmnxCardComplexEgrFcsErrTime     OBJECT-TYPE
    SYNTAX      TimeStamp
    MAX-ACCESS  read-only
    STATUS      current
    DESCRIPTION
        "The value of tmnxCardComplexEgrFcsErrTime indicates the last time
         tmnxCardComplexEgrFcsError incremented."
    ::= { tmnxCardComplexStatsEntry 5 }

tmnxCardComplexMemParError       OBJECT-TYPE
    SYNTAX      Counter32
    MAX-ACCESS  read-only
    STATUS      current
    DESCRIPTION
        "The value of tmnxCardComplexMemParError indicates the number of times
         the complex experienced a memory parity error since startup, last
         clear, or card reboot."
    ::= { tmnxCardComplexStatsEntry 6 }

tmnxCardComplexMemParErrTime     OBJECT-TYPE
    SYNTAX      TimeStamp
    MAX-ACCESS  read-only
    STATUS      current
    DESCRIPTION
        "The value of tmnxCardComplexMemParErrTime indicates the last time
         tmnxCardComplexMemParError incremented."
    ::= { tmnxCardComplexStatsEntry 7 }

tmnxCardComplexCamError          OBJECT-TYPE
    SYNTAX      Counter32
    MAX-ACCESS  read-only
    STATUS      current
    DESCRIPTION
        "The value of tmnxCardComplexCamError indicates the number of times the
         complex experienced a CAM error since startup, last clear, or card
         reboot."
    ::= { tmnxCardComplexStatsEntry 8 }

tmnxCardComplexCamErrTime        OBJECT-TYPE
    SYNTAX      TimeStamp
    MAX-ACCESS  read-only
    STATUS      current
    DESCRIPTION
        "The value of tmnxCardComplexCamErrTime indicates the last time
         tmnxCardComplexCamError incremented."
    ::= { tmnxCardComplexStatsEntry 9 }

tmnxCardComplexBufMemError       OBJECT-TYPE
    SYNTAX      Counter32
    MAX-ACCESS  read-only
    STATUS      current
    DESCRIPTION
        "The value of tmnxCardComplexBufMemError indicates the number of times
         the complex experienced a buffer memory error since startup, last
         clear, or card reboot."
    ::= { tmnxCardComplexStatsEntry 10 }

tmnxCardComplexBufMemErrTime     OBJECT-TYPE
    SYNTAX      TimeStamp
    MAX-ACCESS  read-only
    STATUS      current
    DESCRIPTION
        "The value of tmnxCardComplexBufMemErrTime indicates the last time
         tmnxCardComplexBufMemError incremented."
    ::= { tmnxCardComplexStatsEntry 11 }

tmnxCardComplexStatsMemError     OBJECT-TYPE
    SYNTAX      Counter32
    MAX-ACCESS  read-only
    STATUS      current
    DESCRIPTION
        "The value of tmnxCardComplexStatsMemError indicates the number of
         times the complex experienced a statistics memory error since startup,
         last clear, or card reboot."
    ::= { tmnxCardComplexStatsEntry 12 }

tmnxCardComplexStatsMemErrTime   OBJECT-TYPE
    SYNTAX      TimeStamp
    MAX-ACCESS  read-only
    STATUS      current
    DESCRIPTION
        "The value of tmnxCardComplexStatsMemErrTime indicates the last time
         tmnxCardComplexStatsMemError incremented."
    ::= { tmnxCardComplexStatsEntry 13 }

tmnxCardComplexIntMemError       OBJECT-TYPE
    SYNTAX      Counter32
    MAX-ACCESS  read-only
    STATUS      current
    DESCRIPTION
        "The value of tmnxCardComplexIntMemError indicates the number of times
         the complex experienced an internal memory error since startup, last
         clear, or card reboot."
    ::= { tmnxCardComplexStatsEntry 14 }

tmnxCardComplexIntMemErrTime     OBJECT-TYPE
    SYNTAX      TimeStamp
    MAX-ACCESS  read-only
    STATUS      current
    DESCRIPTION
        "The value of tmnxCardComplexIntMemErrTime indicates the last time
         tmnxCardComplexIntMemError incremented."
    ::= { tmnxCardComplexStatsEntry 15 }

tmnxCardComplexIntDatapathError  OBJECT-TYPE
    SYNTAX      Counter32
    MAX-ACCESS  read-only
    STATUS      current
    DESCRIPTION
        "The value of tmnxCardComplexIntDatapathError indicates the number of
         times the complex experienced an internal datapath error since
         startup, last clear, or card reboot."
    ::= { tmnxCardComplexStatsEntry 16 }

tmnxCardComplexIntDatapthErrTime OBJECT-TYPE
    SYNTAX      TimeStamp
    MAX-ACCESS  read-only
    STATUS      current
    DESCRIPTION
        "The value of tmnxCardComplexIntDatapthErrTime indicates the last time
         tmnxCardComplexIntDatapathError incremented."
    ::= { tmnxCardComplexStatsEntry 17 }

tmnxCardComplexIntDpCellError    OBJECT-TYPE
    SYNTAX      Counter32
    MAX-ACCESS  read-only
    STATUS      current
    DESCRIPTION
        "The value of tmnxCardComplexIntDpCellError indicates the number of
         times the complex experienced an internal datapath cell error since
         startup, last clear, or card reboot."
    ::= { tmnxCardComplexStatsEntry 18 }

tmnxCardComplexIntDpCellErrTime  OBJECT-TYPE
    SYNTAX      TimeStamp
    MAX-ACCESS  read-only
    STATUS      current
    DESCRIPTION
        "The value of tmnxCardComplexIntDpCellErrTime indicates the last time
         tmnxCardComplexIntDpCellError incremented."
    ::= { tmnxCardComplexStatsEntry 19 }

tmnxCardComplexSrcSlotsEgFcsErr  OBJECT-TYPE
    SYNTAX      TmnxCardSlotBitMap
    MAX-ACCESS  read-only
    STATUS      current
    DESCRIPTION
        "The value of tmnxCardComplexSrcSlotsEgFcsErr indicates the source
         slots reported from the last time tmnxCardComplexEgrFcsError
         incremented."
    ::= { tmnxCardComplexStatsEntry 20 }

tmnxCardLevelTable               OBJECT-TYPE
    SYNTAX      SEQUENCE OF TmnxCardLevelEntry
    MAX-ACCESS  not-accessible
    STATUS      current
    DESCRIPTION
        "The card level table has an entry for each card model variant that is
         supported by the system. Some example card levels are: 'he-d1',
         'cr-d3'"
    ::= { tmnxCardObjs 56 }

tmnxCardLevelEntry               OBJECT-TYPE
    SYNTAX      TmnxCardLevelEntry
    MAX-ACCESS  not-accessible
    STATUS      current
    DESCRIPTION
        "Each row entry represents an Nokia SROS series Card model variant.
         Rows in this table are created by the agent at initialization and
         cannot be created or destroyed by SNMP Get or Set requests."
    INDEX       {
        tmnxCardTypeIndex,
        tmnxCardLevelIndex
    }
    ::= { tmnxCardLevelTable 1 }

TmnxCardLevelEntry               ::= SEQUENCE
{
    tmnxCardLevelIndex               Unsigned32,
    tmnxCardLevelName                TNamedItemOrEmpty,
    tmnxCardLevelId                  TmnxCardFunctionalLevel,
    tmnxCardLevelDescription         TItemDescription,
    tmnxCardLevelStatus              TruthValue
}

tmnxCardLevelIndex               OBJECT-TYPE
    SYNTAX      Unsigned32
    MAX-ACCESS  not-accessible
    STATUS      current
    DESCRIPTION
        "The unique index value which identifies this type of Nokia SROS series
         card model functional variant."
    ::= { tmnxCardLevelEntry 1 }

tmnxCardLevelName                OBJECT-TYPE
    SYNTAX      TNamedItemOrEmpty
    MAX-ACCESS  read-only
    STATUS      current
    DESCRIPTION
        "The administrative name that identifies this type of Nokia
         SROS series card model functional variant.  This name string may be used in
         CLI commands to specify a particular card model level."
    ::= { tmnxCardLevelEntry 2 }

tmnxCardLevelId                  OBJECT-TYPE
    SYNTAX      TmnxCardFunctionalLevel
    MAX-ACCESS  read-only
    STATUS      current
    DESCRIPTION
        "The numeric identifier of this type of Nokia SROS series card model
         functional variant."
    ::= { tmnxCardLevelEntry 3 }

tmnxCardLevelDescription         OBJECT-TYPE
    SYNTAX      TItemDescription
    MAX-ACCESS  read-only
    STATUS      current
    DESCRIPTION
        "A detailed description of this Nokia SROS series card model functional
         variant."
    ::= { tmnxCardLevelEntry 4 }

tmnxCardLevelStatus              OBJECT-TYPE
    SYNTAX      TruthValue
    MAX-ACCESS  read-only
    STATUS      current
    DESCRIPTION
        "When tmnxCardLevelStatus has a value of 'true' it indicates that
         this card level is supported in this revision of the management
         software.  When it has a value of 'false' there is no support."
    ::= { tmnxCardLevelEntry 5 }

tmnxMdaLevelTable                OBJECT-TYPE
    SYNTAX      SEQUENCE OF TmnxMdaLevelEntry
    MAX-ACCESS  not-accessible
    STATUS      current
    DESCRIPTION
        "The MDA level table has an entry for each MDA card model functional
         variant supported by the system."
    ::= { tmnxCardObjs 57 }

tmnxMdaLevelEntry                OBJECT-TYPE
    SYNTAX      TmnxMdaLevelEntry
    MAX-ACCESS  not-accessible
    STATUS      current
    DESCRIPTION
        "Each row entry represents an Nokia SROS series MDA card
         model.  Rows in this table are created by the agent at initialization
         and cannot be created or destroyed by SNMP Get or Set requests."
    INDEX       {
        tmnxMdaTypeIndex,
        tmnxMdaLevelIndex
    }
    ::= { tmnxMdaLevelTable 1 }

TmnxMdaLevelEntry                ::= SEQUENCE
{
    tmnxMdaLevelIndex                Unsigned32,
    tmnxMdaLevelName                 TNamedItemOrEmpty,
    tmnxMdaLevelId                   TmnxMDAFunctionalLevel,
    tmnxMdaLevelDescription          TItemDescription,
    tmnxMdaLevelStatus               TruthValue
}

tmnxMdaLevelIndex                OBJECT-TYPE
    SYNTAX      Unsigned32
    MAX-ACCESS  not-accessible
    STATUS      current
    DESCRIPTION
        "The unique index value which identifies this type of Nokia SROS series
         MDA card model functional variant."
    ::= { tmnxMdaLevelEntry 1 }

tmnxMdaLevelName                 OBJECT-TYPE
    SYNTAX      TNamedItemOrEmpty
    MAX-ACCESS  read-only
    STATUS      current
    DESCRIPTION
        "The administrative name that identifies this type of Nokia
         SROS series MDA card model functional variant.  This name
         string may be used in CLI commands to specify a particular
         MDA card model level."
    ::= { tmnxMdaLevelEntry 2 }

tmnxMdaLevelId                   OBJECT-TYPE
    SYNTAX      TmnxMDAFunctionalLevel
    MAX-ACCESS  read-only
    STATUS      current
    DESCRIPTION
        "The numeric identifier of this type of Nokia SROS series MDA model
         functional variant."
    ::= { tmnxMdaLevelEntry 3 }

tmnxMdaLevelDescription          OBJECT-TYPE
    SYNTAX      TItemDescription
    MAX-ACCESS  read-only
    STATUS      current
    DESCRIPTION
        "A detailed description of this Nokia SROS series MDA card model
         functional variant."
    ::= { tmnxMdaLevelEntry 4 }

tmnxMdaLevelStatus               OBJECT-TYPE
    SYNTAX      TruthValue
    MAX-ACCESS  read-only
    STATUS      current
    DESCRIPTION
        "When tmnxMdaLevelStatus has a value of 'true' it indicates that
         this MDA card level is supported in this revision of the management
         software.  When it has a value of 'false' there is no support."
    ::= { tmnxMdaLevelEntry 5 }

tmnxGnssTableLastChange          OBJECT-TYPE
    SYNTAX      TimeStamp
    MAX-ACCESS  read-only
    STATUS      current
    DESCRIPTION
        "The value of tmnxGnssTableLastChange indicates the time, since system
         startup, when a row in the tmnxGnssTable last changed configuration."
    ::= { tmnxCardObjs 58 }

tmnxGnssTable                    OBJECT-TYPE
    SYNTAX      SEQUENCE OF TmnxGnssEntry
    MAX-ACCESS  not-accessible
    STATUS      current
    DESCRIPTION
        "The table tmnxGnssTable contains configuration for each Global
         Navigation Satellite System (GNSS) receiver in the system."
    ::= { tmnxCardObjs 59 }

tmnxGnssEntry                    OBJECT-TYPE
    SYNTAX      TmnxGnssEntry
    MAX-ACCESS  not-accessible
    STATUS      current
    DESCRIPTION
        "Each row entry represents a GNSS receiver.  The GNSS receiver is
         modeled as being contained within an MDA of the system.

         Entries are created/deleted automatically by the system."
    INDEX       {
        tmnxCardSlotNum,
        tmnxMDASlotNum
    }
    ::= { tmnxGnssTable 1 }

TmnxGnssEntry                    ::= SEQUENCE
{
    tmnxGnssCfgLastChanged           TimeStamp,
    tmnxGnssAdminState               TmnxAdminState,
    tmnxGnssConstellation            TmnxGnssConstellation,
    tmnxGnssNmeaAdminState           TmnxAdminState,
    tmnxGnssNmeaSentenceTypes        BITS,
    tmnxGnssNmeaSentenceInterval     Unsigned32,
    tmnxGnssSyncSysTime              TruthValue
}

tmnxGnssCfgLastChanged           OBJECT-TYPE
    SYNTAX      TimeStamp
    MAX-ACCESS  read-only
    STATUS      current
    DESCRIPTION
        "The value of tmnxGnssCfgLastChanged indicates the time, since system
         startup, that the configuration of the GNSS receiver was last
         modified."
    ::= { tmnxGnssEntry 1 }

tmnxGnssAdminState               OBJECT-TYPE
    SYNTAX      TmnxAdminState
    MAX-ACCESS  read-write
    STATUS      current
    DESCRIPTION
        "The value of tmnxGnssAdminState specifies the administrative state of
         the GNSS receiver.

         When tmnxGnssAdminState has a value of 'outOfService', the GNSS
         receiver is powered down.  When tmnxGnssAdminState is 'inService', the
         GNSS receiver attempts to acquire a fix from the satellites
         specified by tmnxGnssConstellation.

         Changing the value of tmnxGnssAdminState to 'inService' may require
         the system to reset the MDA in order for GNSS to become operational.
         The system will automatically reset the MDA if necessary."
    DEFVAL      { outOfService }
    ::= { tmnxGnssEntry 2 }

tmnxGnssConstellation            OBJECT-TYPE
    SYNTAX      TmnxGnssConstellation
    MAX-ACCESS  read-write
    STATUS      current
    DESCRIPTION
        "The value of tmnxGnssConstellation specifies the type of satellites
         that the GNSS receiver will use to acquire a fix.  The value 'gps'
         specifies that the receiver will only use the United States' Global
         Positioning System (GPS) satellites.  The value 'gps-glonass' specifies
         that the receiver will use both GPS and Russia's GLONASS satellites.

         Changing the satellite constellation requires the MDA to be reset. The
         MDA will reset automatically when GNSS is enabled after changing the
         constellation."
    DEFVAL      { gps }
    ::= { tmnxGnssEntry 3 }

tmnxGnssNmeaAdminState           OBJECT-TYPE
    SYNTAX      TmnxAdminState
    MAX-ACCESS  read-write
    STATUS      current
    DESCRIPTION
        "The value of tmnxGnssNmeaAdminState specifies whether the system
         will stream National Marine Electronics Association (NMEA) sentences
         generated by the GNSS receiver.  When the state is 'inService',
         and there is an IP transport configured with aluIpTransportPortId
         corresponding to the GNSS receiver, the system will stream NMEA
         sentences at the rate specified by tmnxGnssNmeaSentenceInterval to the
         remote hosts configured in the IP transport."
    DEFVAL      { outOfService }
    ::= { tmnxGnssEntry 4 }

tmnxGnssNmeaSentenceTypes        OBJECT-TYPE
    SYNTAX      BITS {
        gga (0),
        rmc (1),
        vtg (2),
        gns (3)
    }
    MAX-ACCESS  read-write
    STATUS      current
    DESCRIPTION
        "The value of tmnxGnssNmeaSentenceTypes specifies the type of NMEA
         sentences that the system will generate and send through an associated
         IP transport.

         If multiple bits are set, the system will send multiple NMEA sentence
         types."
    REFERENCE
        "'NMEA 0183', National Marine Electronics Association, March 1983."
    DEFVAL      { { gga } }
    ::= { tmnxGnssEntry 5 }

tmnxGnssNmeaSentenceInterval     OBJECT-TYPE
    SYNTAX      Unsigned32 (1..3600)
    UNITS       "seconds"
    MAX-ACCESS  read-write
    STATUS      current
    DESCRIPTION
        "The value of tmnxGnssNmeaSentenceInterval specifies the interval
         between sentences sent by the system to the remote hosts specified in
         the associated IP transport."
    DEFVAL      { 5 }
    ::= { tmnxGnssEntry 6 }

tmnxGnssSyncSysTime              OBJECT-TYPE
    SYNTAX      TruthValue
    MAX-ACCESS  read-write
    STATUS      current
    DESCRIPTION
        "The value of tmnxGnssSyncSysTime specifies whether the system time is
         synchronized on the GNSS MDA."
    DEFVAL      { false }
    ::= { tmnxGnssEntry 7 }

tmnxGnssOperTable                OBJECT-TYPE
    SYNTAX      SEQUENCE OF TmnxGnssOperEntry
    MAX-ACCESS  not-accessible
    STATUS      current
    DESCRIPTION
        "The table tmnxGnssOperTable contains operational information for each
         Global Navigation Satellite System (GNSS) receiver in the system."
    ::= { tmnxCardObjs 60 }

tmnxGnssOperEntry                OBJECT-TYPE
    SYNTAX      TmnxGnssOperEntry
    MAX-ACCESS  not-accessible
    STATUS      current
    DESCRIPTION
        "Each row entry represents a GNSS receiver.  The GNSS receiver is
         modeled as being contained within an MDA of the system.

         Entries are created/deleted automatically by the system."
    INDEX       {
        tmnxCardSlotNum,
        tmnxMDASlotNum
    }
    ::= { tmnxGnssOperTable 1 }

TmnxGnssOperEntry                ::= SEQUENCE
{
    tmnxGnssOperState                TmnxOperState,
    tmnxGnssPositionValid            TruthValue,
    tmnxGnssDateTime                 DateAndTime,
    tmnxGnssLatitude                 Integer32,
    tmnxGnssLongitude                Integer32,
    tmnxGnssAltitude                 Integer32,
    tmnxGnssHeading                  Unsigned32,
    tmnxGnssSpeed                    Unsigned32
}

tmnxGnssOperState                OBJECT-TYPE
    SYNTAX      TmnxOperState
    MAX-ACCESS  read-only
    STATUS      current
    DESCRIPTION
        "The value of tmnxGnssOperState indicates the operational state
         operational state of the GNSS receiver.  In order for the operational
         state to be 'inService(2)', tmnxGnssAdminState must be 'inService(2)',
         and tmnxHwAdminState for the corresponding MDA must also be 'inService(2)'."
    ::= { tmnxGnssOperEntry 1 }

tmnxGnssPositionValid            OBJECT-TYPE
    SYNTAX      TruthValue
    MAX-ACCESS  read-only
    STATUS      current
    DESCRIPTION
        "The value of tmnxGnssPositionValid indicates whether the GNSS receiver
         has acquired a position fix."
    ::= { tmnxGnssOperEntry 2 }

tmnxGnssDateTime                 OBJECT-TYPE
    SYNTAX      DateAndTime (SIZE (8))
    MAX-ACCESS  read-only
    STATUS      current
    DESCRIPTION
        "The value of tmnxGnssDateTime indicates the GNSS date and time
         corresponding to the most recent position fixed by the GNSS receiver.

         If the receiver has not obtained a fix, tmnxGnssDateTime has a value
         of '0000000000000000'H."
    ::= { tmnxGnssOperEntry 3 }

tmnxGnssLatitude                 OBJECT-TYPE
    SYNTAX      Integer32 (-9000000..9000000)
    UNITS       "0.00001 degrees"
    MAX-ACCESS  read-only
    STATUS      current
    DESCRIPTION
        "The value of tmnxGnssLatitude indicates the latitude of the GNSS
         receiver obtained from the last fix.

         Positive values indicate degrees north of the equator, while negative
         values indicate degrees south.

         If the receiver has not obtained a fix, tmnxGnssPositionValid is
         false, and tmnxGnssLatitude has a value of 0."
    ::= { tmnxGnssOperEntry 4 }

tmnxGnssLongitude                OBJECT-TYPE
    SYNTAX      Integer32 (-18000000..18000000)
    UNITS       "0.00001 degrees"
    MAX-ACCESS  read-only
    STATUS      current
    DESCRIPTION
        "The value of tmnxGnssLongitude indicates the longitude of the GNSS
         receiver obtained from the last fix.

         Positive values indicate degrees east of the prime meridian, while
         negative values indicate degrees west.

         If the receiver has not obtained a fix, tmnxGnssPositionValid is
         false, and tmnxGnssLongitude has a value of 0."
    ::= { tmnxGnssOperEntry 5 }

tmnxGnssAltitude                 OBJECT-TYPE
    SYNTAX      Integer32 (-10000..100000)
    UNITS       "decimeters"
    MAX-ACCESS  read-only
    STATUS      current
    DESCRIPTION
        "The value of tmnxGnssAltitude indicates the altitude above mean sea
         level of the GNSS receiver obtained from the last fix.

         If the receiver has not obtained a fix, tmnxGnssAltitude has a value
         of 0."
    ::= { tmnxGnssOperEntry 6 }

tmnxGnssHeading                  OBJECT-TYPE
    SYNTAX      Unsigned32 (0..3600)
    UNITS       "decidegrees"
    MAX-ACCESS  read-only
    STATUS      current
    DESCRIPTION
        "The value of tmnxGnssHeading indicates the true heading of the system,
         as measured by the GNSS receiver."
    ::= { tmnxGnssOperEntry 7 }

tmnxGnssSpeed                    OBJECT-TYPE
    SYNTAX      Unsigned32
    UNITS       "decameters per hour"
    MAX-ACCESS  read-only
    STATUS      current
    DESCRIPTION
        "The value of tmnxGnssSpeed indicates the speed of the system, as
         measured by the GNSS receiver."
    ::= { tmnxGnssOperEntry 8 }

tmnxGnssSatelliteTable           OBJECT-TYPE
    SYNTAX      SEQUENCE OF TmnxGnssSatelliteEntry
    MAX-ACCESS  not-accessible
    STATUS      current
    DESCRIPTION
        "The table tmnxGnssSatelliteTable contains information for each
         satellite that is visible to the GNSS receiver."
    ::= { tmnxCardObjs 61 }

tmnxGnssSatelliteEntry           OBJECT-TYPE
    SYNTAX      TmnxGnssSatelliteEntry
    MAX-ACCESS  not-accessible
    STATUS      current
    DESCRIPTION
        "Each row entry represents a satellite that is visible to the GNSS
         receiver.

         Entries are created/deleted automatically by the system."
    INDEX       {
        tmnxCardSlotNum,
        tmnxMDASlotNum,
        tmnxGnssSatelliteNumber
    }
    ::= { tmnxGnssSatelliteTable 1 }

TmnxGnssSatelliteEntry           ::= SEQUENCE
{
    tmnxGnssSatelliteNumber          Unsigned32,
    tmnxGnssSatelliteType            INTEGER,
    tmnxGnssSatelliteElevation       Unsigned32,
    tmnxGnssSatelliteAzimuth         Unsigned32,
    tmnxGnssSatelliteSnr             Unsigned32
}

tmnxGnssSatelliteNumber          OBJECT-TYPE
    SYNTAX      Unsigned32
    MAX-ACCESS  not-accessible
    STATUS      current
    DESCRIPTION
        "The value of tmnxGnssSatelliteNumber indicates the satellite number of
         this satellite.

         GPS satellites have a satellite number in the range 1-32. GLONASS
         satellites have a satellite number in the range 65-96.

         These satellite numbers are sometimes referred to as NMEA IDs."
    REFERENCE
        "'NMEA 0183 - Standard for Interfacing Marine Electronic Devices',
         Version 3.01, National Marine Electronics Association, 2002."
    ::= { tmnxGnssSatelliteEntry 1 }

tmnxGnssSatelliteType            OBJECT-TYPE
    SYNTAX      INTEGER {
        gps     (1),
        glonass (2)
    }
    MAX-ACCESS  read-only
    STATUS      current
    DESCRIPTION
        "The value of tmnxGnssSatelliteType indicates the type of this
         satellite."
    ::= { tmnxGnssSatelliteEntry 2 }

tmnxGnssSatelliteElevation       OBJECT-TYPE
    SYNTAX      Unsigned32 (0..90)
    UNITS       "degrees"
    MAX-ACCESS  read-only
    STATUS      current
    DESCRIPTION
        "The value of tmnxGnssSatelliteElevation indicates the elevation of the
         satellite."
    ::= { tmnxGnssSatelliteEntry 3 }

tmnxGnssSatelliteAzimuth         OBJECT-TYPE
    SYNTAX      Unsigned32 (0..360)
    UNITS       "degrees"
    MAX-ACCESS  read-only
    STATUS      current
    DESCRIPTION
        "The value of tmnxGnssSatelliteAzimuth indicates the azimuth of the
         satellite."
    ::= { tmnxGnssSatelliteEntry 4 }

tmnxGnssSatelliteSnr             OBJECT-TYPE
    SYNTAX      Unsigned32 (0..100)
    UNITS       "dB"
    MAX-ACCESS  read-only
    STATUS      current
    DESCRIPTION
        "The value of tmnxGnssSatelliteSnr indicates the signal-to-noise ratio
         of the signal from the satellite to the GNSS receiver."
    ::= { tmnxGnssSatelliteEntry 5 }

tmnxMdaFlexObjs                  OBJECT IDENTIFIER ::= { tmnxCardObjs 62 }

tmnxMdaFlexTimestamps            OBJECT IDENTIFIER ::= { tmnxMdaFlexObjs 1 }

tmnxMdaFlexGroupTableLastChanged OBJECT-TYPE
    SYNTAX      TimeStamp
    MAX-ACCESS  read-only
    STATUS      current
    DESCRIPTION
        "The value of tmnxMdaFlexGroupTableLastChanged indicates the time,
         since system startup, when tmnxMdaFlexGroupTable last changed
         configuration."
    ::= { tmnxMdaFlexTimestamps 1 }

tmnxMdaFlexMemberTableLastChngd  OBJECT-TYPE
    SYNTAX      TimeStamp
    MAX-ACCESS  read-only
    STATUS      current
    DESCRIPTION
        "The value of tmnxMdaFlexMemberTableLastChngd indicates the time, since
         system startup, when tmnxMdaFlexMemberTable last changed
         configuration."
    ::= { tmnxMdaFlexTimestamps 2 }

tmnxMdaFlexClientTableLastChngd  OBJECT-TYPE
    SYNTAX      TimeStamp
    MAX-ACCESS  read-only
    STATUS      current
    DESCRIPTION
        "The value of tmnxMdaFlexClientTableLastChngd indicates the time, since
         system startup, when tmnxMdaFlexClientTable last changed
         configuration."
    ::= { tmnxMdaFlexTimestamps 3 }

tmnxMdaFlexGroupTable            OBJECT-TYPE
    SYNTAX      SEQUENCE OF TmnxMdaFlexGroupEntry
    MAX-ACCESS  not-accessible
    STATUS      current
    DESCRIPTION
        "The tmnxMdaFlexGroupTable consists of Flex groups that can be used to
         bond multiple 400G physical ports to create a single Ethernet port of
         up to 1.6 Terabit/s."
    ::= { tmnxMdaFlexObjs 2 }

tmnxMdaFlexGroupEntry            OBJECT-TYPE
    SYNTAX      TmnxMdaFlexGroupEntry
    MAX-ACCESS  not-accessible
    STATUS      current
    DESCRIPTION
        "The tmnxMdaFlexGroupEntry consists of configurable objects for a given
         Flex group."
    INDEX       {
        tmnxCardSlotNum,
        tmnxMDASlotNum,
        tmnxMdaFlexGroupId
    }
    ::= { tmnxMdaFlexGroupTable 1 }

TmnxMdaFlexGroupEntry            ::= SEQUENCE
{
    tmnxMdaFlexGroupId               Unsigned32,
    tmnxMdaFlexGroupRowStatus        RowStatus,
    tmnxMdaFlexGroupEntryLastChanged TimeStamp,
    tmnxMdaFlexGroupAdminState       TmnxAdminState,
    tmnxMdaFlexGroupOperState        TmnxOperState,
    tmnxMdaFlexGroupDescription      TItemLongDescription,
    tmnxMdaFlexGroupNumber           Unsigned32,
    tmnxMdaFlexGroupCurrentAlarm     TmnxMdaFlexGroupErrors,
    tmnxMdaFlexGroupMaxBandwidth     Unsigned32,
    tmnxMdaFlexGroupReportAlarm      TmnxMdaFlexGroupErrors,
    tmnxMdaFlexGroupReportedAlarm    TmnxMdaFlexGroupErrors
}

tmnxMdaFlexGroupId               OBJECT-TYPE
    SYNTAX      Unsigned32 (1..24)
    MAX-ACCESS  not-accessible
    STATUS      current
    DESCRIPTION
        "The value of tmnxMdaFlexGroupId specifies the Flex group identifier."
    ::= { tmnxMdaFlexGroupEntry 1 }

tmnxMdaFlexGroupRowStatus        OBJECT-TYPE
    SYNTAX      RowStatus
    MAX-ACCESS  read-create
    STATUS      current
    DESCRIPTION
        "The value of tmnxMdaFlexGroupRowStatus specifies the row status. It
         allows the creation and deletion of Flex group entries."
    ::= { tmnxMdaFlexGroupEntry 2 }

tmnxMdaFlexGroupEntryLastChanged OBJECT-TYPE
    SYNTAX      TimeStamp
    MAX-ACCESS  read-only
    STATUS      current
    DESCRIPTION
        "The value of tmnxMdaFlexGroupEntryLastChanged indicates the time,
         since system startup, that the configuration of the row was last
         modified."
    ::= { tmnxMdaFlexGroupEntry 3 }

tmnxMdaFlexGroupAdminState       OBJECT-TYPE
    SYNTAX      TmnxAdminState
    MAX-ACCESS  read-create
    STATUS      current
    DESCRIPTION
        "The value of tmnxMdaFlexGroupAdminState specifies the administrative
         state of the Flex group."
    DEFVAL      { outOfService }
    ::= { tmnxMdaFlexGroupEntry 5 }

tmnxMdaFlexGroupOperState        OBJECT-TYPE
    SYNTAX      TmnxOperState
    MAX-ACCESS  read-only
    STATUS      current
    DESCRIPTION
        "The value of tmnxMdaFlexGroupOperState indicates the operational state
         of the Flex group."
    ::= { tmnxMdaFlexGroupEntry 6 }

tmnxMdaFlexGroupDescription      OBJECT-TYPE
    SYNTAX      TItemLongDescription (SIZE (0..160))
    MAX-ACCESS  read-create
    STATUS      current
    DESCRIPTION
        "The value of tmnxMdaFlexGroupDescription specifies the description of
         this Flex group."
    DEFVAL      { "" }
    ::= { tmnxMdaFlexGroupEntry 7 }

tmnxMdaFlexGroupNumber           OBJECT-TYPE
    SYNTAX      Unsigned32 (0..1048573)
    MAX-ACCESS  read-create
    STATUS      current
    DESCRIPTION
        "The value of tmnxMdaFlexGroupNumber indicates a 20-bit FlexE group
         number used in the FlexE overhead to identify this group."
    DEFVAL      { 0 }
    ::= { tmnxMdaFlexGroupEntry 9 }

tmnxMdaFlexGroupCurrentAlarm     OBJECT-TYPE
    SYNTAX      TmnxMdaFlexGroupErrors
    MAX-ACCESS  read-only
    STATUS      current
    DESCRIPTION
        "The value of tmnxMdaFlexGroupCurrentAlarm indicates the active error
         conditions related to this Flex group."
    ::= { tmnxMdaFlexGroupEntry 10 }

tmnxMdaFlexGroupMaxBandwidth     OBJECT-TYPE
    SYNTAX      Unsigned32
    UNITS       "gigabps"
    MAX-ACCESS  read-only
    STATUS      current
    DESCRIPTION
        "The value of tmnxMdaFlexGroupMaxBandwidth indicates the maximum
         bandwidth of this Flex group."
    ::= { tmnxMdaFlexGroupEntry 11 }

tmnxMdaFlexGroupReportAlarm      OBJECT-TYPE
    SYNTAX      TmnxMdaFlexGroupErrors
    MAX-ACCESS  read-create
    STATUS      current
    DESCRIPTION
        "The value of tmnxMdaFlexGroupReportAlarm specifies which errors
         conditions will be used to generate tmnxEqPortFlexEGroupAlrm and
         tmnxEqPortFlexEGroupAlrmClr."
    DEFVAL      { {flexEMapMismatch, overheadFrameNotLocked, deskewFailed, remotePhyFault, badGroupNumber,
                 badPhyNumber, badPhyInstanceNumber, clientCalendarError, calendarInUseError} }
    ::= { tmnxMdaFlexGroupEntry 12 }

tmnxMdaFlexGroupReportedAlarm    OBJECT-TYPE
    SYNTAX      TmnxMdaFlexGroupErrors
    MAX-ACCESS  read-only
    STATUS      current
    DESCRIPTION
        "The value of tmnxMdaFlexGroupReportedAlarm indicates the active error
         conditions currently logged on this Flex group. This field reports the
         active alarms raised in tmnxMdaFlexGroupCurrentAlarm which are also
         user-enabled in tmnxMdaFlexGroupReportAlarm."
    ::= { tmnxMdaFlexGroupEntry 13 }

tmnxMdaFlexMemberTable           OBJECT-TYPE
    SYNTAX      SEQUENCE OF TmnxMdaFlexMemberEntry
    MAX-ACCESS  not-accessible
    STATUS      current
    DESCRIPTION
        "The tmnxMdaFlexMemberTable consists of Flex member ports."
    ::= { tmnxMdaFlexObjs 3 }

tmnxMdaFlexMemberEntry           OBJECT-TYPE
    SYNTAX      TmnxMdaFlexMemberEntry
    MAX-ACCESS  not-accessible
    STATUS      current
    DESCRIPTION
        "The tmnxMdaFlexMemberEntry consists of configurable objects for a
         given Flex member."
    INDEX       {
        tmnxCardSlotNum,
        tmnxMDASlotNum,
        tmnxMdaFlexGroupId,
        tmnxMdaFlexMemberPortId
    }
    ::= { tmnxMdaFlexMemberTable 1 }

TmnxMdaFlexMemberEntry           ::= SEQUENCE
{
    tmnxMdaFlexMemberPortId          TmnxPortID,
    tmnxMdaFlexMemberRowStatus       RowStatus,
    tmnxMdaFlexMemberEntryLastChngd  TimeStamp,
    tmnxMdaFlexMemberPhyNumber       Unsigned32,
    tmnxMdaFlexMemberReportAlarm     TmnxMdaFlexMemberErrors,
    tmnxMdaFlexMemberCurrentAlarm    TmnxMdaFlexMemberErrors,
    tmnxMdaFlexMemberReportedAlarm   TmnxMdaFlexMemberErrors,
    tmnxMdaFlexMemberPhyReportAlarm  TmnxMdaFlexMbrInstErrors
}

tmnxMdaFlexMemberPortId          OBJECT-TYPE
    SYNTAX      TmnxPortID
    MAX-ACCESS  not-accessible
    STATUS      current
    DESCRIPTION
        "The value of tmnxMdaFlexMemberPortId specifies the port identifier of
         the port associated with this Flex member entry."
    ::= { tmnxMdaFlexMemberEntry 1 }

tmnxMdaFlexMemberRowStatus       OBJECT-TYPE
    SYNTAX      RowStatus
    MAX-ACCESS  read-create
    STATUS      current
    DESCRIPTION
        "The value of tmnxMdaFlexMemberRowStatus specifies the row status. It
         allows the creation and deletion of Flex member entries."
    ::= { tmnxMdaFlexMemberEntry 2 }

tmnxMdaFlexMemberEntryLastChngd  OBJECT-TYPE
    SYNTAX      TimeStamp
    MAX-ACCESS  read-only
    STATUS      current
    DESCRIPTION
        "The value of tmnxMdaFlexMemberEntryLastChngd indicates the time, since
         system startup, that the configuration of the row was last modified."
    ::= { tmnxMdaFlexMemberEntry 3 }

tmnxMdaFlexMemberPhyNumber       OBJECT-TYPE
    SYNTAX      Unsigned32 (1..62)
    MAX-ACCESS  read-create
    STATUS      current
    DESCRIPTION
        "The value of tmnxMdaFlexMemberPhyNumber specifies the Flex member PHY
         number."
    ::= { tmnxMdaFlexMemberEntry 4 }

tmnxMdaFlexMemberReportAlarm     OBJECT-TYPE
    SYNTAX      TmnxMdaFlexMemberErrors
    MAX-ACCESS  read-create
    STATUS      current
    DESCRIPTION
        "The value of tmnxMdaFlexMemberReportAlarm specifies which errors
         conditions will be used to generate tmnxEqPortFlexEMemberAlrm and
         tmnxEqPortFlexEMemberAlrmClr."
    DEFVAL      { {} }
    ::= { tmnxMdaFlexMemberEntry 7 }

tmnxMdaFlexMemberCurrentAlarm    OBJECT-TYPE
    SYNTAX      TmnxMdaFlexMemberErrors
    MAX-ACCESS  read-only
    STATUS      current
    DESCRIPTION
        "The value of tmnxMdaFlexMemberCurrentAlarm indicates the active error
         conditions related to this Flex member port."
    ::= { tmnxMdaFlexMemberEntry 8 }

tmnxMdaFlexMemberReportedAlarm   OBJECT-TYPE
    SYNTAX      TmnxMdaFlexMemberErrors
    MAX-ACCESS  read-only
    STATUS      current
    DESCRIPTION
        "The value of tmnxMdaFlexMemberReportedAlarm indicates the active error
         conditions currently logged on this Flex member port. This field
         reports the active alarms raised in tmnxMdaFlexMemberCurrentAlarm
         which are also user-enabled in tmnxMdaFlexMemberReportAlarm."
    ::= { tmnxMdaFlexMemberEntry 9 }

tmnxMdaFlexMemberPhyReportAlarm  OBJECT-TYPE
    SYNTAX      TmnxMdaFlexMbrInstErrors
    MAX-ACCESS  read-create
    STATUS      current
    DESCRIPTION
        "The value of tmnxMdaFlexMemberPhyReportAlarm specifies which errors
         conditions will be used to generate tmnxEqPortFlexEMbrPhyInstAlrm and
         tmnxEqPortFlexEMbrPhyInstAlrmClr."
    DEFVAL      { {} }
    ::= { tmnxMdaFlexMemberEntry 10 }

tmnxMdaFlexClientTable           OBJECT-TYPE
    SYNTAX      SEQUENCE OF TmnxMdaFlexClientEntry
    MAX-ACCESS  not-accessible
    STATUS      current
    DESCRIPTION
        "The tmnxMdaFlexClientTable consists of Flex clients used to reference
         the aggregated Ethernet port containing all the bandwidth of the
         group."
    ::= { tmnxMdaFlexObjs 4 }

tmnxMdaFlexClientEntry           OBJECT-TYPE
    SYNTAX      TmnxMdaFlexClientEntry
    MAX-ACCESS  not-accessible
    STATUS      current
    DESCRIPTION
        "The tmnxMdaFlexClientEntry consists of configurable objects for a
         given Flex client."
    INDEX       {
        tmnxCardSlotNum,
        tmnxMDASlotNum,
        tmnxMdaFlexGroupId,
        tmnxMdaFlexClientIndex
    }
    ::= { tmnxMdaFlexClientTable 1 }

TmnxMdaFlexClientEntry           ::= SEQUENCE
{
    tmnxMdaFlexClientIndex           Unsigned32,
    tmnxMdaFlexClientRowStatus       RowStatus,
    tmnxMdaFlexClientEntryLastChngd  TimeStamp
}

tmnxMdaFlexClientIndex           OBJECT-TYPE
    SYNTAX      Unsigned32 (1)
    MAX-ACCESS  not-accessible
    STATUS      current
    DESCRIPTION
        "The value of tmnxMdaFlexClientIndex specifies the Flex client index."
    ::= { tmnxMdaFlexClientEntry 1 }

tmnxMdaFlexClientRowStatus       OBJECT-TYPE
    SYNTAX      RowStatus
    MAX-ACCESS  read-create
    STATUS      current
    DESCRIPTION
        "The value of tmnxMdaFlexClientRowStatus specifies the row status. It
         allows the creation and deletion of Flex client entries."
    ::= { tmnxMdaFlexClientEntry 2 }

tmnxMdaFlexClientEntryLastChngd  OBJECT-TYPE
    SYNTAX      TimeStamp
    MAX-ACCESS  read-only
    STATUS      current
    DESCRIPTION
        "The value of tmnxMdaFlexClientEntryLastChngd indicates the time, since
         system startup, that the configuration of the row was last modified."
    ::= { tmnxMdaFlexClientEntry 3 }

tMdaFlexMbrInstOperTable         OBJECT-TYPE
    SYNTAX      SEQUENCE OF TMdaFlexMbrInstOperEntry
    MAX-ACCESS  not-accessible
    STATUS      current
    DESCRIPTION
        "The tMdaFlexMbrInstOperTable consists of statistics data for a given
         100G FlexE instance within a Flex member."
    ::= { tmnxMdaFlexObjs 5 }

tMdaFlexMbrInstOperEntry         OBJECT-TYPE
    SYNTAX      TMdaFlexMbrInstOperEntry
    MAX-ACCESS  not-accessible
    STATUS      current
    DESCRIPTION
        "The tMdaFlexMbrInstOperEntry consists of statistics objects for a
         given 100G FlexE instance within a Flex member."
    INDEX       {
        tmnxCardSlotNum,
        tmnxMDASlotNum,
        tmnxMdaFlexGroupId,
        tmnxMdaFlexMemberPortId,
        tmnxMdaFlexMbrInstIndex
    }
    ::= { tMdaFlexMbrInstOperTable 1 }

TMdaFlexMbrInstOperEntry         ::= SEQUENCE
{
    tmnxMdaFlexMbrInstIndex          Unsigned32,
    tMdaFlexMbrInstOperInstNum       Unsigned32,
    tMdaFlexMbrInstOperCurrentAlarm  TmnxMdaFlexMbrInstErrors,
    tMdaFlexMbrInstOperReportedAlm   TmnxMdaFlexMbrInstErrors,
    tMdaFlexMbrInstOperDeskewDepth   Gauge32,
    tMdaFlexMbrInstOperInfoValid     TruthValue,
    tMdaFlexMbrInstOperCalInUse      INTEGER,
    tMdaFlexMbrInstOperFlexEMap      OCTET STRING,
    tMdaFlexMbrInstOperCalASlots     OCTET STRING,
    tMdaFlexMbrInstOperCalBSlots     OCTET STRING,
    tMdaFlexMbrInstOperRcvdGrpNum    Unsigned32,
    tMdaFlexMbrInstOperRcvdInstNum   Unsigned32
}

tmnxMdaFlexMbrInstIndex          OBJECT-TYPE
    SYNTAX      Unsigned32 (1..4)
    MAX-ACCESS  not-accessible
    STATUS      current
    DESCRIPTION
        "The value of tmnxMdaFlexMbrInstIndex specifies the index of a 100G
         FlexE instance within a flex member."
    ::= { tMdaFlexMbrInstOperEntry 1 }

tMdaFlexMbrInstOperInstNum       OBJECT-TYPE
    SYNTAX      Unsigned32
    MAX-ACCESS  read-only
    STATUS      current
    DESCRIPTION
        "The value of tMdaFlexMbrInstOperInstNum indicates the 100G FlexE
         instance number created from the flex member phys number and the index
         of the 100G FlexE instance. This is used in the FlexE overhead to
         identify the 100G FlexE instance."
    ::= { tMdaFlexMbrInstOperEntry 2 }

tMdaFlexMbrInstOperCurrentAlarm  OBJECT-TYPE
    SYNTAX      TmnxMdaFlexMbrInstErrors
    MAX-ACCESS  read-only
    STATUS      current
    DESCRIPTION
        "The value of tMdaFlexMbrInstOperCurrentAlarm indicates the active
         error conditions related to this 100G FlexE instance."
    ::= { tMdaFlexMbrInstOperEntry 3 }

tMdaFlexMbrInstOperReportedAlm   OBJECT-TYPE
    SYNTAX      TmnxMdaFlexMbrInstErrors
    MAX-ACCESS  read-only
    STATUS      current
    DESCRIPTION
        "The value of tMdaFlexMbrInstOperReportedAlm indicates the active error
         conditions currently logged on this 100G FlexE instance. This field
         reports the active alarms raised in tMdaFlexMbrInstOperCurrentAlarm
         which are also user-enabled in tmnxMdaFlexMemberPhyReportAlarm"
    ::= { tMdaFlexMbrInstOperEntry 4 }

tMdaFlexMbrInstOperDeskewDepth   OBJECT-TYPE
    SYNTAX      Gauge32
    UNITS       "picoseconds"
    MAX-ACCESS  read-only
    STATUS      current
    DESCRIPTION
        "The value of tMdaFlexMbrInstOperDeskewDepth indicates the deskew depth
         related to this 100G FlexE instance."
    ::= { tMdaFlexMbrInstOperEntry 5 }

tMdaFlexMbrInstOperInfoValid     OBJECT-TYPE
    SYNTAX      TruthValue
    MAX-ACCESS  read-only
    STATUS      current
    DESCRIPTION
        "The value of tMdaFlexMbrInstOperInfoValid indicates whether or not
         FlexE/Calendar information is valid."
    ::= { tMdaFlexMbrInstOperEntry 6 }

tMdaFlexMbrInstOperCalInUse      OBJECT-TYPE
    SYNTAX      INTEGER {
        calendarA (0),
        calendarB (1)
    }
    MAX-ACCESS  read-only
    STATUS      current
    DESCRIPTION
        "The value of tMdaFlexMbrInstOperCalInUse indicates which client
         calendar is being used."
    ::= { tMdaFlexMbrInstOperEntry 7 }

tMdaFlexMbrInstOperFlexEMap      OBJECT-TYPE
    SYNTAX      OCTET STRING (SIZE (32))
    MAX-ACCESS  read-only
    STATUS      current
    DESCRIPTION
        "The value of tMdaFlexMbrInstOperFlexEMap contains a binary
         representation of the FlexE map."
    ::= { tMdaFlexMbrInstOperEntry 8 }

tMdaFlexMbrInstOperCalASlots     OBJECT-TYPE
    SYNTAX      OCTET STRING (SIZE (64))
    MAX-ACCESS  read-only
    STATUS      current
    DESCRIPTION
        "The value of tMdaFlexMbrInstOperCalASlots contains slots configured on
         calendar A. This is represented by an array of 32 entries where each
         entry is a 16-bit unsigned integer. For each pair of bytes, the first
         element represents the least significant bits and the second element
         represents the most significant bits."
    ::= { tMdaFlexMbrInstOperEntry 9 }

tMdaFlexMbrInstOperCalBSlots     OBJECT-TYPE
    SYNTAX      OCTET STRING (SIZE (64))
    MAX-ACCESS  read-only
    STATUS      current
    DESCRIPTION
        "The value of tMdaFlexMbrInstOperCalBSlots contains slots configured on
         calendar B. This is represented by an array of 32 entries where each
         entry is a 16-bit unsigned integer. For each pair of bytes, the first
         element represents the least significant bits and the second element
         represents the most significant bits."
    ::= { tMdaFlexMbrInstOperEntry 10 }

tMdaFlexMbrInstOperRcvdGrpNum    OBJECT-TYPE
    SYNTAX      Unsigned32
    MAX-ACCESS  read-only
    STATUS      current
    DESCRIPTION
        "The value of tMdaFlexMbrInstOperRcvdGrpNum indicates the 20-bit FlexE
         group number received in the FlexE overhead."
    ::= { tMdaFlexMbrInstOperEntry 11 }

tMdaFlexMbrInstOperRcvdInstNum   OBJECT-TYPE
    SYNTAX      Unsigned32
    MAX-ACCESS  read-only
    STATUS      current
    DESCRIPTION
        "The value of tMdaFlexMbrInstOperRcvdInstNum indicates the 100G FlexE
         instance number received in the FlexE overhead."
    ::= { tMdaFlexMbrInstOperEntry 12 }

tmnxVmCardTable                  OBJECT-TYPE
    SYNTAX      SEQUENCE OF TmnxVmCardEntry
    MAX-ACCESS  not-accessible
    STATUS      current
    DESCRIPTION
        ""
    ::= { tmnxCardObjs 63 }

tmnxVmCardEntry                  OBJECT-TYPE
    SYNTAX      TmnxVmCardEntry
    MAX-ACCESS  not-accessible
    STATUS      current
    DESCRIPTION
        "Each row entry represents a virtual IOM card slot in a chassis in the
         system.  Entries cannot be created and deleted via SNMP SET
         operations.  When a tmnxChassisEntry is created, a tmnxVmCardEntry
         is created for each virtual IOM card slot in that chassis. Before a
         tmnxChassisEntry can be deleted, each tmnxVmCardEntry for that
         chassis must be in the proper state for removal."
    AUGMENTS    { tmnxCardEntry }
    ::= { tmnxVmCardTable 1 }

TmnxVmCardEntry                  ::= SEQUENCE
{
    tmnxVmCardHypervisor             TItemDescription,
    tmnxVmCardCpu                    TItemDescription,
    tmnxVmCardNumCores               Unsigned32
}

tmnxVmCardHypervisor             OBJECT-TYPE
    SYNTAX      TItemDescription
    MAX-ACCESS  read-only
    STATUS      current
    DESCRIPTION
        "The value of tmnxVmCardHypervisor indicates the name of the
         hypervisor."
    DEFVAL      { "" }
    ::= { tmnxVmCardEntry 1 }

tmnxVmCardCpu                    OBJECT-TYPE
    SYNTAX      TItemDescription
    MAX-ACCESS  read-only
    STATUS      current
    DESCRIPTION
        "The value of tmnxVmCardCpu indicates the description of the CPU."
    DEFVAL      { "" }
    ::= { tmnxVmCardEntry 2 }

tmnxVmCardNumCores               OBJECT-TYPE
    SYNTAX      Unsigned32
    MAX-ACCESS  read-only
    STATUS      current
    DESCRIPTION
        "The value of tmnxVmCardNumCores indicates the number of processor
         cores available."
    ::= { tmnxVmCardEntry 3 }

tmnxVmCpmCardTable               OBJECT-TYPE
    SYNTAX      SEQUENCE OF TmnxVmCpmCardEntry
    MAX-ACCESS  not-accessible
    STATUS      current
    DESCRIPTION
        ""
    ::= { tmnxCardObjs 64 }

tmnxVmCpmCardEntry               OBJECT-TYPE
    SYNTAX      TmnxVmCpmCardEntry
    MAX-ACCESS  not-accessible
    STATUS      current
    DESCRIPTION
        "Each row entry represents a virtual CPM card or module in a chassis in the
         system. Entries cannot be created and deleted via SNMP SET
         operations. When a tmnxChassisEntry is created, a tmnxVmCpmCardEntry
         is created for each virtual CPM card or module in that chassis.  Before a
         tmnxChassisEntry can be deleted, each tmnxVmCpmCardEntry for that
         chassis must be in the proper state for removal."
    AUGMENTS    { tmnxCpmCardEntry }
    ::= { tmnxVmCpmCardTable 1 }

TmnxVmCpmCardEntry               ::= SEQUENCE
{
    tmnxVmCpmCardHypervisor          TItemDescription,
    tmnxVmCpmCardCpu                 TItemDescription,
    tmnxVmCpmCardNumCores            Unsigned32
}

tmnxVmCpmCardHypervisor          OBJECT-TYPE
    SYNTAX      TItemDescription
    MAX-ACCESS  read-only
    STATUS      current
    DESCRIPTION
        "The value of tmnxVmCpmCardHypervisor indicates the name of the
         hypervisor."
    DEFVAL      { "" }
    ::= { tmnxVmCpmCardEntry 1 }

tmnxVmCpmCardCpu                 OBJECT-TYPE
    SYNTAX      TItemDescription
    MAX-ACCESS  read-only
    STATUS      current
    DESCRIPTION
        "The value of tmnxVmCpmCardCpu indicates the description of the CPU."
    DEFVAL      { "" }
    ::= { tmnxVmCpmCardEntry 2 }

tmnxVmCpmCardNumCores            OBJECT-TYPE
    SYNTAX      Unsigned32
    MAX-ACCESS  read-only
    STATUS      current
    DESCRIPTION
        "The value of tmnxVmCpmCardNumCores indicates the number of processor
         cores available."
    ::= { tmnxVmCpmCardEntry 3 }

tmnxCardLevelUpgradesTable       OBJECT-TYPE
    SYNTAX      SEQUENCE OF TmnxCardLevelUpgradesEntry
    MAX-ACCESS  not-accessible
    STATUS      current
    DESCRIPTION
        "The tmnxCardLevelUpgradesTable has an entry for each possible upgrade
         of an IOM card slot based on it's current tmnxCardLicensedLevel."
    ::= { tmnxCardObjs 65 }

tmnxCardLevelUpgradesEntry       OBJECT-TYPE
    SYNTAX      TmnxCardLevelUpgradesEntry
    MAX-ACCESS  not-accessible
    STATUS      current
    DESCRIPTION
        "Each row entry represents an IOM card slot upgrade in a chassis in the
         system based on tmnxCardLicensedLevel."
    INDEX       {
        tmnxChassisIndex,
        tmnxCardSlotNum,
        tmnxCardLevelUpgradeId
    }
    ::= { tmnxCardLevelUpgradesTable 1 }

TmnxCardLevelUpgradesEntry       ::= SEQUENCE
{
    tmnxCardLevelUpgradeId           TmnxCardFunctionalUpgrade,
    tmnxCardLevelUpgradeName         TNamedItemOrEmpty,
    tmnxCardUpgradeLevelId           TmnxCardFunctionalLevel,
    tmnxCardUpgradeRequiresReboot    TruthValue
}

tmnxCardLevelUpgradeId           OBJECT-TYPE
    SYNTAX      TmnxCardFunctionalUpgrade
    MAX-ACCESS  not-accessible
    STATUS      current
    DESCRIPTION
        "The unique index value which identifies this type of Nokia SROS series
         Card model functional upgrade"
    ::= { tmnxCardLevelUpgradesEntry 1 }

tmnxCardLevelUpgradeName         OBJECT-TYPE
    SYNTAX      TNamedItemOrEmpty
    MAX-ACCESS  read-only
    STATUS      current
    DESCRIPTION
        "The administrative name that identifies this type of Nokia
         SROS series card model functional upgrade.  This name string may be used in
         CLI commands to specify a particular card model upgrade."
    ::= { tmnxCardLevelUpgradesEntry 2 }

tmnxCardUpgradeLevelId           OBJECT-TYPE
    SYNTAX      TmnxCardFunctionalLevel
    MAX-ACCESS  read-only
    STATUS      current
    DESCRIPTION
        "An integer that indicates the card upgraded functional-level with this
         license applied for this slot in this chassis."
    ::= { tmnxCardLevelUpgradesEntry 3 }

tmnxCardUpgradeRequiresReboot    OBJECT-TYPE
    SYNTAX      TruthValue
    MAX-ACCESS  read-only
    STATUS      current
    DESCRIPTION
        "tmnxCardUpgradeRequiresReboot indicates whether this upgrade requires
         a a reboot of the card to be applied for this slot in this chassis."
    ::= { tmnxCardLevelUpgradesEntry 4 }

tmnxCardLevelUpgradeTable        OBJECT-TYPE
    SYNTAX      SEQUENCE OF TmnxCardLevelUpgradeEntry
    MAX-ACCESS  not-accessible
    STATUS      current
    DESCRIPTION
        "The tmnxCardLevelUpgradeTable has an entry for each upgrade that has
         been applied to an IOM card slot."
    ::= { tmnxCardObjs 66 }

tmnxCardLevelUpgradeEntry        OBJECT-TYPE
    SYNTAX      TmnxCardLevelUpgradeEntry
    MAX-ACCESS  not-accessible
    STATUS      current
    DESCRIPTION
        "Each row entry represents an IOM card slot applied upgrade in a
         chassis in the system."
    INDEX       {
        tmnxChassisIndex,
        tmnxCardSlotNum,
        tmnxCardLevelUpgradeIndex
    }
    ::= { tmnxCardLevelUpgradeTable 1 }

TmnxCardLevelUpgradeEntry        ::= SEQUENCE
{
    tmnxCardLevelUpgradeIndex        Unsigned32,
    tmnxCardLevelUpgradeRowStatus    RowStatus,
    tmnxCardAssignedLevelUpgradeId   TmnxCardFunctionalUpgrade
}

tmnxCardLevelUpgradeIndex        OBJECT-TYPE
    SYNTAX      Unsigned32 (1..6)
    MAX-ACCESS  not-accessible
    STATUS      current
    DESCRIPTION
        "The index value which identifies this type of Nokia SROS series Card
         model functional upgrade"
    ::= { tmnxCardLevelUpgradeEntry 1 }

tmnxCardLevelUpgradeRowStatus    OBJECT-TYPE
    SYNTAX      RowStatus
    MAX-ACCESS  read-create
    STATUS      current
    DESCRIPTION
        "The value of tmnxCardLevelUpgradeRowStatus specifies the row status of
         the card level upgrade."
    ::= { tmnxCardLevelUpgradeEntry 2 }

tmnxCardAssignedLevelUpgradeId   OBJECT-TYPE
    SYNTAX      TmnxCardFunctionalUpgrade
    MAX-ACCESS  read-create
    STATUS      current
    DESCRIPTION
        "The unique index value which identifies the Nokia SROS series Card
         model functional upgrade to apply"
    ::= { tmnxCardLevelUpgradeEntry 3 }

tmnxMDALevelUpgradesTable        OBJECT-TYPE
    SYNTAX      SEQUENCE OF TmnxMDALevelUpgradesEntry
    MAX-ACCESS  not-accessible
    STATUS      current
    DESCRIPTION
        "The tmnxMDALevelUpgradesTable has an entry for each possible upgrade
         of an MDA based on it's current tmnxMDALicensedLevel."
    ::= { tmnxCardObjs 67 }

tmnxMDALevelUpgradesEntry        OBJECT-TYPE
    SYNTAX      TmnxMDALevelUpgradesEntry
    MAX-ACCESS  not-accessible
    STATUS      current
    DESCRIPTION
        "Each row entry represents an MDA slot upgrade in a chassis in the
         system based on tmnxMDALicensedLevel."
    INDEX       {
        tmnxChassisIndex,
        tmnxCardSlotNum,
        tmnxMDASlotNum,
        tmnxMDALevelUpgradeId
    }
    ::= { tmnxMDALevelUpgradesTable 1 }

TmnxMDALevelUpgradesEntry        ::= SEQUENCE
{
    tmnxMDALevelUpgradeId            TmnxMDAFunctionalUpgrade,
    tmnxMDALevelUpgradeName          TNamedItemOrEmpty,
    tmnxMDAUpgradeLevelId            TmnxMDAFunctionalLevel,
    tmnxMDAUpgradeRequiresReboot     TruthValue
}

tmnxMDALevelUpgradeId            OBJECT-TYPE
    SYNTAX      TmnxMDAFunctionalUpgrade
    MAX-ACCESS  not-accessible
    STATUS      current
    DESCRIPTION
        "The unique index value which identifies this type of Nokia SROS series
         MDA model functional upgrade"
    ::= { tmnxMDALevelUpgradesEntry 1 }

tmnxMDALevelUpgradeName          OBJECT-TYPE
    SYNTAX      TNamedItemOrEmpty
    MAX-ACCESS  read-only
    STATUS      current
    DESCRIPTION
        "The administrative name that identifies this type of Nokia
         SROS series MDA model functional upgrade.  This name string may be used in
         CLI commands to specify a particular card model upgrade."
    ::= { tmnxMDALevelUpgradesEntry 2 }

tmnxMDAUpgradeLevelId            OBJECT-TYPE
    SYNTAX      TmnxMDAFunctionalLevel
    MAX-ACCESS  read-only
    STATUS      current
    DESCRIPTION
        "An integer that indicates the MDA upgraded functional-level with this
         license applied for this slot in this chassis."
    ::= { tmnxMDALevelUpgradesEntry 3 }

tmnxMDAUpgradeRequiresReboot     OBJECT-TYPE
    SYNTAX      TruthValue
    MAX-ACCESS  read-only
    STATUS      current
    DESCRIPTION
        "tmnxMDAUpgradeRequiresReboot indicates whether this upgrade requires a
         a reboot of the MDA to be applied for this slot in this chassis."
    ::= { tmnxMDALevelUpgradesEntry 4 }

tmnxMDALevelUpgradeTable         OBJECT-TYPE
    SYNTAX      SEQUENCE OF TmnxMDALevelUpgradeEntry
    MAX-ACCESS  not-accessible
    STATUS      current
    DESCRIPTION
        "The tmnxMDALevelUpgradeTable has an entry for each upgrade that has
         been applied to an MDA slot."
    ::= { tmnxCardObjs 68 }

tmnxMDALevelUpgradeEntry         OBJECT-TYPE
    SYNTAX      TmnxMDALevelUpgradeEntry
    MAX-ACCESS  not-accessible
    STATUS      current
    DESCRIPTION
        "Each row entry represents an MDA slot applied upgrade in a chassis in
         the system."
    INDEX       {
        tmnxChassisIndex,
        tmnxCardSlotNum,
        tmnxMDASlotNum,
        tmnxMDALevelUpgradeIndex
    }
    ::= { tmnxMDALevelUpgradeTable 1 }

TmnxMDALevelUpgradeEntry         ::= SEQUENCE
{
    tmnxMDALevelUpgradeIndex         Unsigned32,
    tmnxMDALevelUpgradeRowStatus     RowStatus,
    tmnxMDAAssignedLevelUpgradeId    TmnxMDAFunctionalUpgrade
}

tmnxMDALevelUpgradeIndex         OBJECT-TYPE
    SYNTAX      Unsigned32 (1..6)
    MAX-ACCESS  not-accessible
    STATUS      current
    DESCRIPTION
        "The index value which identifies this type of Nokia SROS series MDA
         model functional upgrade"
    ::= { tmnxMDALevelUpgradeEntry 1 }

tmnxMDALevelUpgradeRowStatus     OBJECT-TYPE
    SYNTAX      RowStatus
    MAX-ACCESS  read-create
    STATUS      current
    DESCRIPTION
        "The value of tmnxMDALevelUpgradeRowStatus specifies the row status of
         the MDA level upgrade."
    ::= { tmnxMDALevelUpgradeEntry 2 }

tmnxMDAAssignedLevelUpgradeId    OBJECT-TYPE
    SYNTAX      TmnxMDAFunctionalUpgrade
    MAX-ACCESS  read-create
    STATUS      current
    DESCRIPTION
        "The unique index value which identifies the Nokia SROS series MDA
         model functional upgrade to apply"
    ::= { tmnxMDALevelUpgradeEntry 3 }

tmnxMDAIsaTnlStatsTable          OBJECT-TYPE
    SYNTAX      SEQUENCE OF TmnxMDAIsaTnlStatsEntry
    MAX-ACCESS  not-accessible
    STATUS      current
    DESCRIPTION
        "The tmnxMDAIsaTnlStatsTable has an entry for each MDA slot in each IOM
         card in this chassis in the TMNX system."
    ::= { tmnxCardObjs 69 }

tmnxMDAIsaTnlStatsEntry          OBJECT-TYPE
    SYNTAX      TmnxMDAIsaTnlStatsEntry
    MAX-ACCESS  not-accessible
    STATUS      current
    DESCRIPTION
        "Each row entry represents a MDA slot in an IOM card in a chassis in
         the system."
    INDEX       {
        tmnxChassisIndex,
        tmnxCardSlotNum,
        tmnxMDASlotNum
    }
    ::= { tmnxMDAIsaTnlStatsTable 1 }

TmnxMDAIsaTnlStatsEntry          ::= SEQUENCE
{ tmnxMDAIsaTnlStatsCryptoAcc      OCTET STRING }

tmnxMDAIsaTnlStatsCryptoAcc      OBJECT-TYPE
    SYNTAX      OCTET STRING (SIZE (0..64))
    MAX-ACCESS  read-only
    STATUS      current
    DESCRIPTION
        "The value of tmnxMDAIsaTnlStatsCryptoAcc indicates the cryptographic
         accelerator information."
    ::= { tmnxMDAIsaTnlStatsEntry 1 }

tmnxEsaTable                     OBJECT-TYPE
    SYNTAX      SEQUENCE OF TmnxEsaEntry
    MAX-ACCESS  not-accessible
    STATUS      current
    DESCRIPTION
        "The tmnxEsaTable contains configuration information for Extended
         Services Appliance (ESA) entries."
    ::= { tmnxCardObjs 70 }

tmnxEsaEntry                     OBJECT-TYPE
    SYNTAX      TmnxEsaEntry
    MAX-ACCESS  not-accessible
    STATUS      current
    DESCRIPTION
        "Each tmnxEsaEntry represents an ESA in the system and contains its
         configuration information.

         Entries in this table are created and destroyed via SNMP set
         operations to tmnxEsaRowStatus."
    INDEX       { tmnxEsaId }
    ::= { tmnxEsaTable 1 }

TmnxEsaEntry                     ::= SEQUENCE
{
    tmnxEsaId                        TmnxEsaId,
    tmnxEsaLastChanged               TimeStamp,
    tmnxEsaRowStatus                 RowStatus,
    tmnxEsaAdminState                TmnxAdminState,
    tmnxEsaDescription               TItemDescription,
    tmnxEsaHwIndex                   TmnxHwIndex,
    tmnxEsaReboot                    TmnxActionType,
    tmnxEsaColdReboot                TmnxActionType
}

tmnxEsaId                        OBJECT-TYPE
    SYNTAX      TmnxEsaId
    MAX-ACCESS  not-accessible
    STATUS      current
    DESCRIPTION
        "The value of tmnxEsaId specifies the ID of the ESA."
    ::= { tmnxEsaEntry 1 }

tmnxEsaLastChanged               OBJECT-TYPE
    SYNTAX      TimeStamp
    MAX-ACCESS  read-only
    STATUS      current
    DESCRIPTION
        "The value of tmnxEsaLastChanged indicates the time, since system
         startup, that the configuration of the row was last modified."
    ::= { tmnxEsaEntry 2 }

tmnxEsaRowStatus                 OBJECT-TYPE
    SYNTAX      RowStatus
    MAX-ACCESS  read-create
    STATUS      current
    DESCRIPTION
        "The value of tmnxEsaRowStatus specifies the status of the row. It also
         controls the creation and deletion of the row."
    ::= { tmnxEsaEntry 3 }

tmnxEsaAdminState                OBJECT-TYPE
    SYNTAX      TmnxAdminState
    MAX-ACCESS  read-create
    STATUS      current
    DESCRIPTION
        "The value of tmnxEsaAdminState specifies the admin state of the ESA."
    DEFVAL      { outOfService }
    ::= { tmnxEsaEntry 4 }

tmnxEsaDescription               OBJECT-TYPE
    SYNTAX      TItemDescription
    MAX-ACCESS  read-create
    STATUS      current
    DESCRIPTION
        "The value of tmnxEsaDescription specifies the description of the ESA."
    DEFVAL      { "" }
    ::= { tmnxEsaEntry 5 }

tmnxEsaHwIndex                   OBJECT-TYPE
    SYNTAX      TmnxHwIndex
    MAX-ACCESS  read-only
    STATUS      current
    DESCRIPTION
        "The value of tmnxEsaHwIndex specifies the tmnxHwIndex  into the
         tmnxHwTable to locate the row entry that represents the hardware
         component information for this ESA."
    ::= { tmnxEsaEntry 6 }

tmnxEsaReboot                    OBJECT-TYPE
    SYNTAX      TmnxActionType
    MAX-ACCESS  read-create
    STATUS      current
    DESCRIPTION
        "Setting the value of tmnxEsaReboot to 'doAction' causes the ESA to
         execute a reboot."
    DEFVAL      { notApplicable }
    ::= { tmnxEsaEntry 7 }

tmnxEsaColdReboot                OBJECT-TYPE
    SYNTAX      TmnxActionType
    MAX-ACCESS  read-create
    STATUS      current
    DESCRIPTION
        "Setting the value of tmnxEsaColdReboot to 'doAction' causes the ESA to
         execute a forced cold reboot."
    DEFVAL      { notApplicable }
    ::= { tmnxEsaEntry 8 }

tmnxEsaHostPortTable             OBJECT-TYPE
    SYNTAX      SEQUENCE OF TmnxEsaHostPortEntry
    MAX-ACCESS  not-accessible
    STATUS      current
    DESCRIPTION
        "The tmnxEsaHostPortTable contains entries for the host ports of each
         ESA."
    ::= { tmnxCardObjs 71 }

tmnxEsaHostPortEntry             OBJECT-TYPE
    SYNTAX      TmnxEsaHostPortEntry
    MAX-ACCESS  not-accessible
    STATUS      current
    DESCRIPTION
        "Each tmnxEsaHostPortEntry represents a host port for an ESA in the
         system and contains its configuration information.

         Entries in this table are created and destroyed via SNMP set
         operations to tmnxEsaHostPortRowStatus."
    INDEX       {
        tmnxEsaId,
        tmnxEsaHostPortId
    }
    ::= { tmnxEsaHostPortTable 1 }

TmnxEsaHostPortEntry             ::= SEQUENCE
{
    tmnxEsaHostPortId                TmnxPortID,
    tmnxEsaHostPortRowStatus         RowStatus,
    tmnxEsaHostPortCrcMonSdThreshold Unsigned32,
    tmnxEsaHostPortCrcMonSdTMltplier Unsigned32,
    tmnxEsaHostPortCrcMonSfThreshold Unsigned32,
    tmnxEsaHostPortCrcMonSfTMltplier Unsigned32,
    tmnxEsaHostPortCrcMonWindowSize  Unsigned32
}

tmnxEsaHostPortId                OBJECT-TYPE
    SYNTAX      TmnxPortID
    MAX-ACCESS  not-accessible
    STATUS      current
    DESCRIPTION
        "The value of tmnxEsaHostPortId specifies the port identifier of the
         ESA host port."
    ::= { tmnxEsaHostPortEntry 1 }

tmnxEsaHostPortRowStatus         OBJECT-TYPE
    SYNTAX      RowStatus
    MAX-ACCESS  read-create
    STATUS      current
    DESCRIPTION
        "The value of tmnxEsaHostPortRowStatus specifies the status of the row.
         It also controls the creation and deletion of the row."
    ::= { tmnxEsaHostPortEntry 2 }

tmnxEsaHostPortCrcMonSdThreshold OBJECT-TYPE
    SYNTAX      Unsigned32 (0..9)
    MAX-ACCESS  read-create
    STATUS      current
    DESCRIPTION
        "The value of tmnxEsaHostPortCrcMonSdThreshold specifies a packet error
         rate threshold used to determine when to send a notification for a CRC
         Signal Degradation (SD) failure and notification for a CRC SD failure
         clear.

         tmnxEsaHostPortCrcMonSdThreshold is the absolute value of the exponent
         of the rate expressed as 10e-n.

         A value of 0 disables CRC SD monitoring."
    DEFVAL      { 0 }
    ::= { tmnxEsaHostPortEntry 3 }

tmnxEsaHostPortCrcMonSdTMltplier OBJECT-TYPE
    SYNTAX      Unsigned32 (1..1)
    MAX-ACCESS  read-create
    STATUS      current
    DESCRIPTION
        "The value of tmnxEsaHostPortCrcMonSdTMltplier specifies the
         tmnxEsaHostPortCrcMonSdTMltplier multiplier value."
    DEFVAL      { 1 }
    ::= { tmnxEsaHostPortEntry 4 }

tmnxEsaHostPortCrcMonSfThreshold OBJECT-TYPE
    SYNTAX      Unsigned32 (0..9)
    MAX-ACCESS  read-create
    STATUS      current
    DESCRIPTION
        "The value of tmnxEsaHostPortCrcMonSfThreshold specifies a packet error
         rate threshold used to determine when to send a notification for a CRC
         Signal Failure (SF) failure.

         Crossing the tmnxEsaHostPortCrcMonSfThreshold will result in the
         tmnxPortOperStatus being set to 'outOfService'.

         A value of 0 disables CRC SF monitoring."
    DEFVAL      { 0 }
    ::= { tmnxEsaHostPortEntry 5 }

tmnxEsaHostPortCrcMonSfTMltplier OBJECT-TYPE
    SYNTAX      Unsigned32 (1..1)
    MAX-ACCESS  read-create
    STATUS      current
    DESCRIPTION
        "The value of tmnxEsaHostPortCrcMonSfTMltplier specifies the
         tmnxEsaHostPortCrcMonSfThreshold multiplier value.

         The CRC SF error rate threshold is calculated as:
         tmnxEsaHostPortCrcMonSfTMltplier *
         10e-tmnxEsaHostPortCrcMonSfThreshold."
    DEFVAL      { 1 }
    ::= { tmnxEsaHostPortEntry 6 }

tmnxEsaHostPortCrcMonWindowSize  OBJECT-TYPE
    SYNTAX      Unsigned32 (10..60)
    UNITS       "seconds"
    MAX-ACCESS  read-create
    STATUS      current
    DESCRIPTION
        "The value of tmnxEsaHostPortCrcMonWindowSize specifies the size of the
         sliding window in increments of 5 seconds over which the
         tmnxEsaHostPortCrcMonSdThreshold and tmnxEsaHostPortCrcMonSfThreshold
         are applied."
    DEFVAL      { 10 }
    ::= { tmnxEsaHostPortEntry 7 }

tmnxEsaVmTable                   OBJECT-TYPE
    SYNTAX      SEQUENCE OF TmnxEsaVmEntry
    MAX-ACCESS  not-accessible
    STATUS      current
    DESCRIPTION
        "The tmnxEsaVmTable contains entries for the VMs of each ESA."
    ::= { tmnxCardObjs 72 }

tmnxEsaVmEntry                   OBJECT-TYPE
    SYNTAX      TmnxEsaVmEntry
    MAX-ACCESS  not-accessible
    STATUS      current
    DESCRIPTION
        "Each tmnxEsaVmEntry represents a VM on an ESA in the system and
         contains its configuration information.

         Entries in this table are created and destroyed via SNMP set
         operations to tmnxEsaVmRowStatus."
    INDEX       {
        tmnxEsaId,
        tmnxEsaVmId
    }
    ::= { tmnxEsaVmTable 1 }

TmnxEsaVmEntry                   ::= SEQUENCE
{
    tmnxEsaVmId                      TmnxEsaVmId,
    tmnxEsaVmLastChanged             TimeStamp,
    tmnxEsaVmRowStatus               RowStatus,
    tmnxEsaVmAdminState              TmnxAdminState,
    tmnxEsaVmDescription             TItemDescription,
    tmnxEsaVmType                    INTEGER,
    tmnxEsaVmHostPortId              TmnxPortID,
    tmnxEsaVmCoreNumber              Unsigned32,
    tmnxEsaVmMemorySize              Unsigned32,
    tmnxEsaVmReboot                  TmnxActionType
}

tmnxEsaVmId                      OBJECT-TYPE
    SYNTAX      TmnxEsaVmId
    MAX-ACCESS  not-accessible
    STATUS      current
    DESCRIPTION
        "The value of tmnxEsaVmId specifies the ID of the VM on this ESA."
    ::= { tmnxEsaVmEntry 1 }

tmnxEsaVmLastChanged             OBJECT-TYPE
    SYNTAX      TimeStamp
    MAX-ACCESS  read-only
    STATUS      current
    DESCRIPTION
        "The value of tmnxEsaVmLastChanged indicates the time, since system
         startup, that the configuration of the row was last modified."
    ::= { tmnxEsaVmEntry 2 }

tmnxEsaVmRowStatus               OBJECT-TYPE
    SYNTAX      RowStatus
    MAX-ACCESS  read-create
    STATUS      current
    DESCRIPTION
        "The value of tmnxEsaVmRowStatus specifies the status of the row. It
         also controls the creation and deletion of the row."
    ::= { tmnxEsaVmEntry 3 }

tmnxEsaVmAdminState              OBJECT-TYPE
    SYNTAX      TmnxAdminState
    MAX-ACCESS  read-create
    STATUS      current
    DESCRIPTION
        "The value of tmnxEsaVmAdminState specifies the admin state of the ESA
         VM."
    DEFVAL      { outOfService }
    ::= { tmnxEsaVmEntry 4 }

tmnxEsaVmDescription             OBJECT-TYPE
    SYNTAX      TItemDescription
    MAX-ACCESS  read-create
    STATUS      current
    DESCRIPTION
        "The value of tmnxEsaVmDescription specifies the description of the ESA
         VM."
    DEFVAL      { "" }
    ::= { tmnxEsaVmEntry 5 }

tmnxEsaVmType                    OBJECT-TYPE
    SYNTAX      INTEGER {
        none   (0),
        aa     (1),
        bb     (2),
        tunnel (3),
        video  (4),
        dms    (5)
    }
    MAX-ACCESS  read-create
    STATUS      current
    DESCRIPTION
        "The value of tmnxEsaVmType specifies to the type of the ESA VM."
    DEFVAL      { none }
    ::= { tmnxEsaVmEntry 6 }

tmnxEsaVmHostPortId              OBJECT-TYPE
    SYNTAX      TmnxPortID
    MAX-ACCESS  read-create
    STATUS      current
    DESCRIPTION
        "The value of tmnxEsaVmHostPortId specifies the port identifier of the
         ESA VM host port. This port must be configured for use on in the
         tmnxEsaHostPortTable."
    DEFVAL      { '1e000000'H }
    ::= { tmnxEsaVmEntry 7 }

tmnxEsaVmCoreNumber              OBJECT-TYPE
    SYNTAX      Unsigned32 (0..128)
    MAX-ACCESS  read-create
    STATUS      current
    DESCRIPTION
        "The value of tmnxEsaVmCoreNumber specifies the number of cores given
         to the ESA VM."
    DEFVAL      { 0 }
    ::= { tmnxEsaVmEntry 8 }

tmnxEsaVmMemorySize              OBJECT-TYPE
    SYNTAX      Unsigned32 (0..256)
    UNITS       "gigabyte"
    MAX-ACCESS  read-create
    STATUS      current
    DESCRIPTION
        "The value of tmnxEsaVmMemorySize specifies the amount of memory, in
         gigabytes, given to the ESA VM."
    DEFVAL      { 0 }
    ::= { tmnxEsaVmEntry 9 }

tmnxEsaVmReboot                  OBJECT-TYPE
    SYNTAX      TmnxActionType
    MAX-ACCESS  read-create
    STATUS      current
    DESCRIPTION
        "Setting the value of tmnxEsaVmReboot to 'doAction' causes the esa-vm
         to execute a reboot."
    DEFVAL      { notApplicable }
    ::= { tmnxEsaVmEntry 10 }

tmnxTunnelGrpEsaVmTable          OBJECT-TYPE
    SYNTAX      SEQUENCE OF TmnxTunnelGrpEsaVmEntry
    MAX-ACCESS  not-accessible
    STATUS      current
    DESCRIPTION
        "The tmnxTunnelGrpEsaVmTable contains configuration information that
         associates tunnel-capable ESA virtual machines to tunnel groups.

         A tunnel group, configured in tmnxIPsecIsaGrpTable, defines a
         collection of tunnel-capable service devices. A tunnel-capable ESA
         virtual machine, configured in tmnxEsaVmTable, is one such service
         device. Examples of services supported by tunnel groups include IPsec
         tunnels, IP-in-IP tunnels, and GRE tunnels."
    ::= { tmnxCardObjs 73 }

tmnxTunnelGrpEsaVmEntry          OBJECT-TYPE
    SYNTAX      TmnxTunnelGrpEsaVmEntry
    MAX-ACCESS  not-accessible
    STATUS      current
    DESCRIPTION
        "Each tmnxTunnelGrpEsaVmEntry represents an ESA virtual machine
         association to a tunnel group.

         Rows are created or destroyed by SNMP Set operations on
         tmnxTunnelGrpEsaVmRowStatus."
    INDEX       {
        tmnxEsaId,
        tmnxEsaVmId
    }
    ::= { tmnxTunnelGrpEsaVmTable 1 }

TmnxTunnelGrpEsaVmEntry          ::= SEQUENCE
{
    tmnxTunnelGrpEsaVmRowStatus      RowStatus,
    tmnxTunnelGrpEsaVmLastChgd       TimeStamp,
    tmnxTunnelGrpEsaVmGroupAssoc     TmnxTunnelGroupIdOrZero,
    tmnxTunnelGrpEsaVmActive         TruthValue,
    tmnxTunnelGrpEsaVmPoolAssoc      TNamedItemOrEmpty,
    tmnxTunnelGrpEsaVmActiveInGrp    TmnxTunnelGroupIdOrZero,
    tmnxTunnelGrpEsaVmWeight         Unsigned32,
    tmnxTunnelGrpEsaVmAllocHashSlots Unsigned32
}

tmnxTunnelGrpEsaVmRowStatus      OBJECT-TYPE
    SYNTAX      RowStatus
    MAX-ACCESS  read-create
    STATUS      current
    DESCRIPTION
        "The value of tmnxTunnelGrpEsaVmRowStatus specifies the status of the
         configuration row for the specified ESA virtual machine tunnel group
         member.

         A row in this table may not be created unless the corresponding ESA
         virtual machine exists in the tmnxEsaVmTable with tmnxEsaVmType of
         'tunnel'. The row in tmnxEsaVmTable may not be destroyed or have its
         tmnxEsaVmType changed from 'tunnel' while a corresponding association
         exists in this table."
    ::= { tmnxTunnelGrpEsaVmEntry 1 }

tmnxTunnelGrpEsaVmLastChgd       OBJECT-TYPE
    SYNTAX      TimeStamp
    MAX-ACCESS  read-only
    STATUS      current
    DESCRIPTION
        "The value of tmnxTunnelGrpEsaVmLastChgd indicates the time, since
         system startup, when the configuration of the tmnxTunnelGrpEsaVmEntry
         was last modified."
    ::= { tmnxTunnelGrpEsaVmEntry 2 }

tmnxTunnelGrpEsaVmGroupAssoc     OBJECT-TYPE
    SYNTAX      TmnxTunnelGroupIdOrZero
    MAX-ACCESS  read-create
    STATUS      current
    DESCRIPTION
        "The value of tmnxTunnelGrpEsaVmGroupAssoc specifies the tunnel group
         to which the ESA virtual machine is associated.

         During row creation, one of tmnxTunnelGrpEsaVmGroupAssoc or
         'tmnxTunnelGrpEsaVmPoolAssoc' must be set to a non-default value.
         These associations can be removed only by destroying the row. When
         this object is set to a non-default value, the value of
         'tmnxTunnelGrpEsaVmPoolAssoc' must be default.

         The tunnel group specified must exist in tmnxIPsecIsaGrpTable. Removal
         of the tunnel group from tmnxIPsecIsaGrpTable will not be allowed
         while this association exists."
    DEFVAL      { 0 }
    ::= { tmnxTunnelGrpEsaVmEntry 3 }

tmnxTunnelGrpEsaVmActive         OBJECT-TYPE
    SYNTAX      TruthValue
    MAX-ACCESS  read-only
    STATUS      current
    DESCRIPTION
        "The value of tmnxTunnelGrpEsaVmActive indicates whether the ESA
         virtual machine is active in the tunnel group indicated by
         tmnxTunnelGrpEsaVmGroupAssoc."
    ::= { tmnxTunnelGrpEsaVmEntry 4 }

tmnxTunnelGrpEsaVmPoolAssoc      OBJECT-TYPE
    SYNTAX      TNamedItemOrEmpty
    MAX-ACCESS  read-create
    STATUS      current
    DESCRIPTION
        "The value of tmnxTunnelGrpEsaVmPoolAssoc specifies the IPsec ISA
         member pool to which the ESA virtual machine is associated.

         During row creation, one of tmnxTunnelGrpEsaVmGroupAssoc or
         tmnxTunnelGrpEsaVmPoolAssoc must be set to a non-default value. These
         associations can be removed only by destroying the row. When this
         object is set to a non-default value, the value of
         tmnxTunnelGrpEsaVmGroupAssoc must be default.

         The member pool specified must exist in tmnxIPsecIsaMemberPoolTable.
         Removal of the member pool from tmnxIPsecIsaMemberPoolTable will not
         be allowed while this associations exists."
    DEFVAL      { "" }
    ::= { tmnxTunnelGrpEsaVmEntry 5 }

tmnxTunnelGrpEsaVmActiveInGrp    OBJECT-TYPE
    SYNTAX      TmnxTunnelGroupIdOrZero
    MAX-ACCESS  read-only
    STATUS      current
    DESCRIPTION
        "The value of tmnxTunnelGrpEsaVmActiveInGrp indicates which
         tunnel-group, if any, the ESA virtual machine is active in. This value
         is only relevant when the ESA virtual machine is associated with a
         member pool."
    ::= { tmnxTunnelGrpEsaVmEntry 6 }

tmnxTunnelGrpEsaVmWeight         OBJECT-TYPE
    SYNTAX      Unsigned32 (0..1000)
    MAX-ACCESS  read-create
    STATUS      current
    DESCRIPTION
        "The value of tmnxTunnelGrpEsaVmWeight specifies the weight to be used
         for this ESA virtual machine in load balancing of this tunnel-group.

         This object can only be set at row creation, and cannot be modified.
         The value 0 means no weight.  The value of tmnxTunnelGrpEsaVmWeight
         must be all 0's or all non-zero's for all ESA virtual machines
         in the same tunnel group or member pool."
    DEFVAL      { 0 }
    ::= { tmnxTunnelGrpEsaVmEntry 7 }

tmnxTunnelGrpEsaVmAllocHashSlots OBJECT-TYPE
    SYNTAX      Unsigned32
    MAX-ACCESS  read-only
    STATUS      current
    DESCRIPTION
        "The value of tmnxTunnelGrpEsaVmAllocHashSlots indicates the number of
         hash slots allocated for this ESA virtual machine."
    ::= { tmnxTunnelGrpEsaVmEntry 8 }

tmnxEsaStatsTable                OBJECT-TYPE
    SYNTAX      SEQUENCE OF TmnxEsaStatsEntry
    MAX-ACCESS  not-accessible
    STATUS      current
    DESCRIPTION
        "The tmnxEsaStatsTable contains statistical information for Extended
         Services Appliance (ESA) entries."
    ::= { tmnxCardObjs 74 }

tmnxEsaStatsEntry                OBJECT-TYPE
    SYNTAX      TmnxEsaStatsEntry
    MAX-ACCESS  not-accessible
    STATUS      current
    DESCRIPTION
        "Each tmnxEsaStatsEntry represents an ESA in the system and contains
         its statistical information.

         Entries in this table are created and destroyed automatically by the
         system."
    INDEX       { tmnxEsaId }
    ::= { tmnxEsaStatsTable 1 }

TmnxEsaStatsEntry                ::= SEQUENCE
{
    tmnxEsaStatsOperState            INTEGER,
    tmnxEsaStatsCoresAvailable       Unsigned32,
    tmnxEsaStatsCoresAllocated       Unsigned32,
    tmnxEsaStatsMemoryAvailable      Unsigned32,
    tmnxEsaStatsMemoryAllocated      Unsigned32,
    tmnxEsaStatsSoftwareVersion      DisplayString,
    tmnxEsaStatsOperFlags            BITS,
    tmnxEsaStatsTimeOfBoot           DateAndTime,
    tmnxEsaStatsSystemManufacturer   DisplayString,
    tmnxEsaStatsSystemProductName    DisplayString,
    tmnxEsaStatsSystemSerialNumber   DisplayString,
    tmnxEsaStatsPerformanceEnabled   TruthValue,
    tmnxEsaStatsExportRestricted     TruthValue,
    tmnxEsaStatsHardwareStatus       INTEGER,
    tmnxEsaStatsPowerSupply1Status   TmnxEsaDeviceState,
    tmnxEsaStatsPowerSupply2Status   TmnxEsaDeviceState,
    tmnxEsaStatsPowerSupply1Temp     Integer32,
    tmnxEsaStatsPowerSupply2Temp     Integer32,
    tmnxEsaStatsFanRedundancy        TmnxEsaDeviceRedundancyState,
    tmnxEsaStatsFanStatus            TmnxEsaDeviceState,
    tmnxEsaStatsPwrSupMismatchStatus TmnxEsaDeviceMismatchState,
    tmnxEsaStatsPwrSupRedundancy     TmnxEsaDeviceRedundancyState,
    tmnxEsaStatsTemperatureStatus    TmnxEsaDeviceState,
    tmnxEsaStatsCpu1Temperature      Integer32,
    tmnxEsaStatsCpu2Temperature      Integer32,
    tmnxEsaStatsSystemPartNumber     DisplayString,
    tmnxEsaStatsPowerSupply1Voltage  Integer32,
    tmnxEsaStatsPowerSupply2Voltage  Integer32,
    tmnxEsaStatsPowerSupply1OutPwr   Integer32,
    tmnxEsaStatsPowerSupply2OutPwr   Integer32,
    tmnxEsaStatsPowerSupply1MaxPwr   Integer32,
    tmnxEsaStatsPowerSupply2MaxPwr   Integer32,
    tmnxEsaStatsCpu1TempThreshold    Integer32,
    tmnxEsaStatsCpu2TempThreshold    Integer32,
    tmnxEsaStatsNic1Temperature      Integer32,
    tmnxEsaStatsNic2Temperature      Integer32,
    tmnxEsaStatsNic1TempThreshold    Integer32,
    tmnxEsaStatsNic2TempThreshold    Integer32
}

tmnxEsaStatsOperState            OBJECT-TYPE
    SYNTAX      INTEGER {
        unknown             (1),
        inService           (2),
        outOfService        (3),
        booting             (4),
        failed              (5),
        provisioned         (6),
        unprovisioned       (7),
        upgrade             (8),
        fwUpgrade           (9),
        fwUpgradeNic        (10),
        fwUpgradeSps        (11),
        fwUpgradeSystemRom  (12),
        fwUpgradeSetting    (13),
        fwUpgradeBmc        (14),
        fwUpgradeBmcSetting (15),
        fwUpgradeIe         (16)
    }
    MAX-ACCESS  read-only
    STATUS      current
    DESCRIPTION
        "The value of tmnxEsaStatsOperState indicates the operational state of
         the ESA."
    ::= { tmnxEsaStatsEntry 1 }

tmnxEsaStatsCoresAvailable       OBJECT-TYPE
    SYNTAX      Unsigned32
    MAX-ACCESS  read-only
    STATUS      current
    DESCRIPTION
        "The value of tmnxEsaStatsCoresAvailable indicates the total number of
         cores on the ESA."
    ::= { tmnxEsaStatsEntry 2 }

tmnxEsaStatsCoresAllocated       OBJECT-TYPE
    SYNTAX      Unsigned32
    MAX-ACCESS  read-only
    STATUS      current
    DESCRIPTION
        "The value of tmnxEsaStatsCoresAllocated indicates the total number of
         allocated cores on the ESA."
    ::= { tmnxEsaStatsEntry 3 }

tmnxEsaStatsMemoryAvailable      OBJECT-TYPE
    SYNTAX      Unsigned32
    UNITS       "gigabyte"
    MAX-ACCESS  read-only
    STATUS      current
    DESCRIPTION
        "The value of tmnxEsaStatsMemoryAvailable indicates the total amount of
         available memory (in GigaBytes) on the ESA."
    ::= { tmnxEsaStatsEntry 4 }

tmnxEsaStatsMemoryAllocated      OBJECT-TYPE
    SYNTAX      Unsigned32
    UNITS       "gigabyte"
    MAX-ACCESS  read-only
    STATUS      current
    DESCRIPTION
        "The value of tmnxEsaStatsMemoryAllocated indicates the total amount of
         allocated memory (in GigaBytes) on the ESA."
    ::= { tmnxEsaStatsEntry 5 }

tmnxEsaStatsSoftwareVersion      OBJECT-TYPE
    SYNTAX      DisplayString
    MAX-ACCESS  read-only
    STATUS      current
    DESCRIPTION
        "The value of tmnxEsaStatsSoftwareVersion indicates the software
         version currently running on the ESA."
    ::= { tmnxEsaStatsEntry 6 }

tmnxEsaStatsOperFlags            OBJECT-TYPE
    SYNTAX      BITS {
        adminDown           (0),
        esaSwMismatch       (1),
        esaMismatch         (2),
        connectFailed       (3),
        fwUpdateFailed      (4),
        bootFailed          (5),
        fwUpdateRequired    (6),
        unexpectedFwVersion (7)
    }
    MAX-ACCESS  read-only
    STATUS      current
    DESCRIPTION
        "The value of tmnxEsaStatsOperFlags indicates the operational flags
         that determine the status of the ESA."
    ::= { tmnxEsaStatsEntry 7 }

tmnxEsaStatsTimeOfBoot           OBJECT-TYPE
    SYNTAX      DateAndTime
    MAX-ACCESS  read-only
    STATUS      current
    DESCRIPTION
        "The value of tmnxEsaStatsTimeOfBoot indicates date and time the
         software running on this ESA was last rebooted."
    ::= { tmnxEsaStatsEntry 8 }

tmnxEsaStatsSystemManufacturer   OBJECT-TYPE
    SYNTAX      DisplayString
    MAX-ACCESS  read-only
    STATUS      current
    DESCRIPTION
        "The value of tmnxEsaStatsSystemManufacturer indicates the system
         manufacturer of the ESA."
    ::= { tmnxEsaStatsEntry 9 }

tmnxEsaStatsSystemProductName    OBJECT-TYPE
    SYNTAX      DisplayString
    MAX-ACCESS  read-only
    STATUS      current
    DESCRIPTION
        "The value of tmnxEsaStatsSystemProductName indicates the system
         product name of the ESA."
    ::= { tmnxEsaStatsEntry 10 }

tmnxEsaStatsSystemSerialNumber   OBJECT-TYPE
    SYNTAX      DisplayString
    MAX-ACCESS  read-only
    STATUS      current
    DESCRIPTION
        "The value of tmnxEsaStatsSystemSerialNumber indicates the system
         serial number of the ESA."
    ::= { tmnxEsaStatsEntry 11 }

tmnxEsaStatsPerformanceEnabled   OBJECT-TYPE
    SYNTAX      TruthValue
    MAX-ACCESS  read-only
    STATUS      current
    DESCRIPTION
        "The value of tmnxEsaStatsPerformanceEnabled indicates whether the ESA
         is in performance (true) or functional (false) mode."
    ::= { tmnxEsaStatsEntry 12 }

tmnxEsaStatsExportRestricted     OBJECT-TYPE
    SYNTAX      TruthValue
    MAX-ACCESS  read-only
    STATUS      current
    DESCRIPTION
        "The value of tmnxEsaStatsExportRestricted indicates whether the ESA is
         in export restricted mode or not. In this mode, some restrictions
         apply to certain vapp types."
    ::= { tmnxEsaStatsEntry 13 }

tmnxEsaStatsHardwareStatus       OBJECT-TYPE
    SYNTAX      INTEGER {
        unknown     (1),
        ok          (2),
        degraded    (3),
        critical    (4),
        unsupported (5)
    }
    MAX-ACCESS  read-only
    STATUS      current
    DESCRIPTION
        "The value of tmnxEsaStatsHardwareStatus indicates
         the overall hardware status reported by the ESA as follows:
         - Unknown    : Esa status not reported. Esa not connected or not booted yet.
         - Ok         : Esa hardware is functioning normally.
         - Degraded   : Esa hardware status is degraded (Health LED flashing amber).
         - Critical   : Esa hardware status is critical (Health LED flashing red).
         - Unsupported: Esa hardware status reporting is unsupported by the ESA."
    ::= { tmnxEsaStatsEntry 14 }

tmnxEsaStatsPowerSupply1Status   OBJECT-TYPE
    SYNTAX      TmnxEsaDeviceState
    MAX-ACCESS  read-only
    STATUS      current
    DESCRIPTION
        "The value of tmnxEsaStatsPowerSupply1Status indicates the status of
         power supply 1 as reported by the ESA."
    ::= { tmnxEsaStatsEntry 15 }

tmnxEsaStatsPowerSupply2Status   OBJECT-TYPE
    SYNTAX      TmnxEsaDeviceState
    MAX-ACCESS  read-only
    STATUS      current
    DESCRIPTION
        "The value of tmnxEsaStatsPowerSupply2Status indicates the status of
         power supply 2 as reported by the ESA."
    ::= { tmnxEsaStatsEntry 16 }

tmnxEsaStatsPowerSupply1Temp     OBJECT-TYPE
    SYNTAX      Integer32
    UNITS       "degrees celsius"
    MAX-ACCESS  read-only
    STATUS      current
    DESCRIPTION
        "The value of tmnxEsaStatsPowerSupply1Temp indicates the temperature of
         power supply 1 as reported by the ESA. This is only supported on
         ESA-100G. A temperature of 0 means that this is not supported and not
         possible to retrieve on the ESA."
    ::= { tmnxEsaStatsEntry 17 }

tmnxEsaStatsPowerSupply2Temp     OBJECT-TYPE
    SYNTAX      Integer32
    UNITS       "degrees celsius"
    MAX-ACCESS  read-only
    STATUS      current
    DESCRIPTION
        "The value of tmnxEsaStatsPowerSupply2Temp indicates the temperature of
         power supply 2 as reported by the ESA. This is only supported on
         ESA-100G. A temperature of 0 means that this is not supported and not
         possible to retrieve on the ESA."
    ::= { tmnxEsaStatsEntry 18 }

tmnxEsaStatsFanRedundancy        OBJECT-TYPE
    SYNTAX      TmnxEsaDeviceRedundancyState
    MAX-ACCESS  read-only
    STATUS      current
    DESCRIPTION
        "The value of tmnxEsaStatsFanRedundancy indicates the fan redundancy
         status as reported by the ESA."
    ::= { tmnxEsaStatsEntry 19 }

tmnxEsaStatsFanStatus            OBJECT-TYPE
    SYNTAX      TmnxEsaDeviceState
    MAX-ACCESS  read-only
    STATUS      current
    DESCRIPTION
        "The value of tmnxEsaStatsFanStatus indicates the fan status as
         reported by the ESA."
    ::= { tmnxEsaStatsEntry 20 }

tmnxEsaStatsPwrSupMismatchStatus OBJECT-TYPE
    SYNTAX      TmnxEsaDeviceMismatchState
    MAX-ACCESS  read-only
    STATUS      current
    DESCRIPTION
        "The value of tmnxEsaStatsPwrSupMismatchStatus indicates the mismatch
         status of power supplies as reported by the ESA."
    ::= { tmnxEsaStatsEntry 21 }

tmnxEsaStatsPwrSupRedundancy     OBJECT-TYPE
    SYNTAX      TmnxEsaDeviceRedundancyState
    MAX-ACCESS  read-only
    STATUS      current
    DESCRIPTION
        "The value of tmnxEsaStatsPwrSupRedundancy indicates the redundancy
         status of power supplies as reported by the ESA."
    ::= { tmnxEsaStatsEntry 22 }

tmnxEsaStatsTemperatureStatus    OBJECT-TYPE
    SYNTAX      TmnxEsaDeviceState
    MAX-ACCESS  read-only
    STATUS      current
    DESCRIPTION
        "The value of tmnxEsaStatsTemperatureStatus indicates
         the temperature status as reported by the ESA, as follows:
             - Ok      : Temperature within normal operating range.
             - Degraded: Temperature is outside the normal operating range.
                         Depending on the system configuration, this system
                         might be shut down.
             - Failed  : Temperature exceeded on the ESA."
    ::= { tmnxEsaStatsEntry 23 }

tmnxEsaStatsCpu1Temperature      OBJECT-TYPE
    SYNTAX      Integer32
    UNITS       "degrees celsius"
    MAX-ACCESS  read-only
    STATUS      current
    DESCRIPTION
        "The value of tmnxEsaStatsCpu1Temperature indicates the CPU temperature
         as reported by the ESA. A temperature of 0 means that this is not
         supported and not possible to retrieve on the ESA. "
    ::= { tmnxEsaStatsEntry 24 }

tmnxEsaStatsCpu2Temperature      OBJECT-TYPE
    SYNTAX      Integer32
    UNITS       "degrees celsius"
    MAX-ACCESS  read-only
    STATUS      current
    DESCRIPTION
        "The value of tmnxEsaStatsCpu2Temperature indicates the CPU temperature
         as reported by the ESA. A temperature of 0 means that this is not
         supported and not possible to retrieve on the ESA. "
    ::= { tmnxEsaStatsEntry 25 }

tmnxEsaStatsSystemPartNumber     OBJECT-TYPE
    SYNTAX      DisplayString
    MAX-ACCESS  read-only
    STATUS      current
    DESCRIPTION
        "The value of tmnxEsaStatsSystemPartNumber indicates the system part
         number of the ESA."
    ::= { tmnxEsaStatsEntry 26 }

tmnxEsaStatsPowerSupply1Voltage  OBJECT-TYPE
    SYNTAX      Integer32
    MAX-ACCESS  read-only
    STATUS      current
    DESCRIPTION
        "The value of tmnxEsaStatsPowerSupply1Voltage indicates the voltage of
         power supply 1 as reported by the ESA. A voltage of 0 means that this
         is not supported and not possible to retrieve on the ESA."
    ::= { tmnxEsaStatsEntry 27 }

tmnxEsaStatsPowerSupply2Voltage  OBJECT-TYPE
    SYNTAX      Integer32
    MAX-ACCESS  read-only
    STATUS      current
    DESCRIPTION
        "The value of tmnxEsaStatsPowerSupply2Voltage indicates the voltage of
         power supply 2 as reported by the ESA. A voltage of 0 means that this
         is not supported and not possible to retrieve on the ESA."
    ::= { tmnxEsaStatsEntry 28 }

tmnxEsaStatsPowerSupply1OutPwr   OBJECT-TYPE
    SYNTAX      Integer32
    MAX-ACCESS  read-only
    STATUS      current
    DESCRIPTION
        "The value of tmnxEsaStatsPowerSupply1OutPwr indicates the output power
         of power supply 1 as reported by the ESA. An output power of 0 means
         that this is not supported and not possible to retrieve on the ESA."
    ::= { tmnxEsaStatsEntry 29 }

tmnxEsaStatsPowerSupply2OutPwr   OBJECT-TYPE
    SYNTAX      Integer32
    MAX-ACCESS  read-only
    STATUS      current
    DESCRIPTION
        "The value of tmnxEsaStatsPowerSupply2OutPwr indicates the output power
         of power supply 2 as reported by the ESA. An output power of 0 means
         that this is not supported and not possible to retrieve on the ESA."
    ::= { tmnxEsaStatsEntry 30 }

tmnxEsaStatsPowerSupply1MaxPwr   OBJECT-TYPE
    SYNTAX      Integer32
    MAX-ACCESS  read-only
    STATUS      current
    DESCRIPTION
        "The value of tmnxEsaStatsPowerSupply1MaxPwr indicates the max power of
         power supply 1 as reported by the ESA. A max power of 0 means that
         this is not supported and not possible to retrieve on the ESA."
    ::= { tmnxEsaStatsEntry 31 }

tmnxEsaStatsPowerSupply2MaxPwr   OBJECT-TYPE
    SYNTAX      Integer32
    MAX-ACCESS  read-only
    STATUS      current
    DESCRIPTION
        "The value of tmnxEsaStatsPowerSupply2MaxPwr indicates the max power of
         power supply 2 as reported by the ESA. A max power of 0 means that
         this is not supported and not possible to retrieve on the ESA."
    ::= { tmnxEsaStatsEntry 32 }

tmnxEsaStatsCpu1TempThreshold    OBJECT-TYPE
    SYNTAX      Integer32
    UNITS       "degrees celsius"
    MAX-ACCESS  read-only
    STATUS      current
    DESCRIPTION
        "The value of tmnxEsaStatsCpu1TempThreshold indicates the CPU
         temperature caution threshold as reported by the ESA. A temperature
         threshold of 0 means that this is not  supported and not possible to
         retrieve on the ESA. "
    ::= { tmnxEsaStatsEntry 33 }

tmnxEsaStatsCpu2TempThreshold    OBJECT-TYPE
    SYNTAX      Integer32
    UNITS       "degrees celsius"
    MAX-ACCESS  read-only
    STATUS      current
    DESCRIPTION
        "The value of tmnxEsaStatsCpu2TempThreshold indicates the CPU
         temperature caution threshold as reported by the ESA. A temperature
         threshold of 0 means that this is not  supported and not possible to
         retrieve on the ESA. "
    ::= { tmnxEsaStatsEntry 34 }

tmnxEsaStatsNic1Temperature      OBJECT-TYPE
    SYNTAX      Integer32
    UNITS       "degrees celsius"
    MAX-ACCESS  read-only
    STATUS      current
    DESCRIPTION
        "The value of tmnxEsaStatsNic1Temperature indicates the NIC temperature
         as reported by the ESA. A temperature of 0 means that this is not
         supported and not possible to retrieve on the ESA. "
    ::= { tmnxEsaStatsEntry 35 }

tmnxEsaStatsNic2Temperature      OBJECT-TYPE
    SYNTAX      Integer32
    UNITS       "degrees celsius"
    MAX-ACCESS  read-only
    STATUS      current
    DESCRIPTION
        "The value of tmnxEsaStatsNic2Temperature indicates the NIC temperature
         as reported by the ESA. A temperature of 0 means that this is not
         supported and not possible to retrieve on the ESA. "
    ::= { tmnxEsaStatsEntry 36 }

tmnxEsaStatsNic1TempThreshold    OBJECT-TYPE
    SYNTAX      Integer32
    UNITS       "degrees celsius"
    MAX-ACCESS  read-only
    STATUS      current
    DESCRIPTION
        "The value of tmnxEsaStatsNic1TempThreshold indicates the NIC
         temperature caution threshold as reported by the ESA. A temperature
         threshold of 0 means that this is not  supported and not possible to
         retrieve on the ESA. "
    ::= { tmnxEsaStatsEntry 37 }

tmnxEsaStatsNic2TempThreshold    OBJECT-TYPE
    SYNTAX      Integer32
    UNITS       "degrees celsius"
    MAX-ACCESS  read-only
    STATUS      current
    DESCRIPTION
        "The value of tmnxEsaStatsNic2TempThreshold indicates the NIC
         temperature caution threshold as reported by the ESA. A temperature
         threshold of 0 means that this is not  supported and not possible to
         retrieve on the ESA. "
    ::= { tmnxEsaStatsEntry 38 }

tmnxEsaVmStatsTable              OBJECT-TYPE
    SYNTAX      SEQUENCE OF TmnxEsaVmStatsEntry
    MAX-ACCESS  not-accessible
    STATUS      current
    DESCRIPTION
        "The tmnxEsaVmStatsTable contains entries for the host ports of each
         ESA."
    ::= { tmnxCardObjs 75 }

tmnxEsaVmStatsEntry              OBJECT-TYPE
    SYNTAX      TmnxEsaVmStatsEntry
    MAX-ACCESS  not-accessible
    STATUS      current
    DESCRIPTION
        "Each tmnxEsaVmStatsEntry represents a VM on an ESA in the system and
         contains its statistical information.

         Entries in this table are created and destroyed automatically by the
         system."
    INDEX       {
        tmnxEsaId,
        tmnxEsaVmId
    }
    ::= { tmnxEsaVmStatsTable 1 }

TmnxEsaVmStatsEntry              ::= SEQUENCE
{
    tmnxEsaVmStatsOperState          INTEGER,
    tmnxEsaVmStatsOperFlags          BITS,
    tmnxEsaVmStatsTimeOfBoot         DateAndTime,
    tmnxEsaVmStatsSoftwareVersion    DisplayString,
    tmnxEsaVmStatsUtilLastChanged    DateAndTime
}

tmnxEsaVmStatsOperState          OBJECT-TYPE
    SYNTAX      INTEGER {
        unknown       (1),
        inService     (2),
        outOfService  (3),
        booting       (4),
        failed        (5),
        provisioned   (6),
        unprovisioned (7),
        upgrade       (8)
    }
    MAX-ACCESS  read-only
    STATUS      current
    DESCRIPTION
        "The value of tmnxEsaVmStatsOperState specifies the  operational state
         of the ESA VM."
    ::= { tmnxEsaVmStatsEntry 1 }

tmnxEsaVmStatsOperFlags          OBJECT-TYPE
    SYNTAX      BITS {
        adminDown                    (0),
        bootFailure                  (1),
        outOfEsaRsrcs                (2),
        connectFailed                (3),
        provisionFail                (4),
        coreFailure                  (5),
        forcedFailure                (6),
        iccFailure                   (7),
        exportRestricted             (8),
        swVerMismatch                (9),
        insufficientCoreAllocation   (10),
        insufficientMemoryAllocation (11),
        hostPortConnFail             (12),
        vmCoresExceedOSLimit         (13)
    }
    MAX-ACCESS  read-only
    STATUS      current
    DESCRIPTION
        "The value of tmnxEsaVmStatsOperFlags indicates the operational flags
         that determine the status of the ESA VM."
    ::= { tmnxEsaVmStatsEntry 2 }

tmnxEsaVmStatsTimeOfBoot         OBJECT-TYPE
    SYNTAX      DateAndTime
    MAX-ACCESS  read-only
    STATUS      current
    DESCRIPTION
        "The value of tmnxEsaVmStatsTimeOfBoot indicates date and time the
         software running on this ESA VM was last rebooted."
    ::= { tmnxEsaVmStatsEntry 3 }

tmnxEsaVmStatsSoftwareVersion    OBJECT-TYPE
    SYNTAX      DisplayString
    MAX-ACCESS  read-only
    STATUS      current
    DESCRIPTION
        "The value of tmnxEsaVmStatsSoftwareVersion indicates the software
         version currently running on the ESA VM."
    ::= { tmnxEsaVmStatsEntry 4 }

tmnxEsaVmStatsUtilLastChanged    OBJECT-TYPE
    SYNTAX      DateAndTime
    MAX-ACCESS  read-only
    STATUS      current
    DESCRIPTION
        "The value of tmnxEsaVmStatsUtilLastChanged indicates  the time since
         system startup, when the core utilization  statistics were last
         collected."
    ::= { tmnxEsaVmStatsEntry 5 }

tCoreResTable                    OBJECT-TYPE
    SYNTAX      SEQUENCE OF TCoreResEntry
    MAX-ACCESS  not-accessible
    STATUS      current
    DESCRIPTION
        "The tCoreResTable contains entries for ingress and egress resources
         supported on this core"
    ::= { tmnxCardObjs 76 }

tCoreResEntry                    OBJECT-TYPE
    SYNTAX      TCoreResEntry
    MAX-ACCESS  not-accessible
    STATUS      current
    DESCRIPTION
        "Each tCoreResEntry represents ingress and egress resources supported.

         Entries in this table are created and destroyed automatically by the
         system."
    INDEX       {
        tmnxChassisIndex,
        tmnxCardSlotNum,
        tmnxFPNum,
        tmnxCoreNum
    }
    ::= { tCoreResTable 1 }

TCoreResEntry                    ::= SEQUENCE
{
    tmnxCoreNum                      INTEGER,
    tCoreResIngFloatPolicerTotal     Unsigned32,
    tCoreResIngFloatPolicerAlloc     Unsigned32,
    tCoreResIngFloatPolicerStatTotal Unsigned32,
    tCoreResIngFloatPolicerStatAlloc Unsigned32,
    tCoreResIngDdctdPolicerTotal     Unsigned32,
    tCoreResIngDdctdPolicerAlloc     Unsigned32,
    tCoreResIngDdctdPolicerStatTotal Unsigned32,
    tCoreResIngDdctdPolicerStatAlloc Unsigned32,
    tCoreResVlanVoqTotal             Unsigned32,
    tCoreResVlanVoqAlloc             Unsigned32,
    tCoreResSapTotal                 Unsigned32,
    tCoreResSapAlloc                 Unsigned32,
    tCoreResIngFloatPlcrStatIUBACL   Unsigned32,
    tCoreResSharedPolicerTotal       Unsigned32,
    tCoreResSharedPolicerAlloc       Unsigned32,
    tCoreResIngFloatPlcrStatIUBSP    Unsigned32,
    tCoreResSharedPolicerStatsTotal  Unsigned32,
    tCoreResSharedPolicerStatsAlloc  Unsigned32,
    tCoreRes4QVlanVoqTotal           Unsigned32,
    tCoreRes4QVlanVoqAlloc           Unsigned32,
    tCoreResFltrSharedPlcrTotal      Unsigned32,
    tCoreResFltrSharedPlcrAlloc      Unsigned32,
    tCoreResFltrSharedPlcrStatsTotal Unsigned32,
    tCoreResFltrSharedPlcrStatsAlloc Unsigned32,
    tCoreResSchedulerFlowTotal       Unsigned32,
    tCoreResSchedulerFlowAlloc       Unsigned32,
    tCoreResSchedulerInterfacesTotal Unsigned32,
    tCoreResSchedulerInterfacesAlloc Unsigned32,
    tCoreRes8QVirtualFlowTotal       Unsigned32,
    tCoreRes8QVirtualFlowAlloc       Unsigned32,
    tCoreRes4QVirtualFlowTotal       Unsigned32,
    tCoreRes4QVirtualFlowAlloc       Unsigned32,
    tCoreRes8QLowRateVlanVoqTotal    Unsigned32,
    tCoreRes8QLowRateVlanVoqAlloc    Unsigned32,
    tCoreRes4QLowRateVlanVoqTotal    Unsigned32,
    tCoreRes4QLowRateVlanVoqAlloc    Unsigned32
}

tmnxCoreNum                      OBJECT-TYPE
    SYNTAX      INTEGER {
        core0 (0),
        core1 (1)
    }
    MAX-ACCESS  not-accessible
    STATUS      current
    DESCRIPTION
        "The value of tmnxCoreNum  identifies the Core"
    DEFVAL      { core0 }
    ::= { tCoreResEntry 1 }

tCoreResIngFloatPolicerTotal     OBJECT-TYPE
    SYNTAX      Unsigned32
    MAX-ACCESS  read-only
    STATUS      current
    DESCRIPTION
        "The value of tCoreResIngFloatPolicerTotal represents the total number
         of ingress floating policers that are supported on this core.

         When the value of tCoreResIngFloatPolicerTotal is zero, it indicates
         that this resource type is not supported on this core."
    ::= { tCoreResEntry 2 }

tCoreResIngFloatPolicerAlloc     OBJECT-TYPE
    SYNTAX      Unsigned32
    MAX-ACCESS  read-only
    STATUS      current
    DESCRIPTION
        "The value of tCoreResIngFloatPolicerAlloc represents the total number
         of ingress floating policers that are currently allocated on this
         core."
    ::= { tCoreResEntry 3 }

tCoreResIngFloatPolicerStatTotal OBJECT-TYPE
    SYNTAX      Unsigned32
    MAX-ACCESS  read-only
    STATUS      current
    DESCRIPTION
        "The value of tCoreResIngFloatPolicerStatTotal represents the total
         number of ingress floating policer stats that are supported on this
         core.

         When the value of tCoreResIngFloatPolicerStatTotal is zero, it
         indicates that this resource type is not supported on this core."
    ::= { tCoreResEntry 4 }

tCoreResIngFloatPolicerStatAlloc OBJECT-TYPE
    SYNTAX      Unsigned32
    MAX-ACCESS  read-only
    STATUS      current
    DESCRIPTION
        "The value of tCoreResIngFloatPolicerStatAlloc represents the total
         number of ingress floating policer stats that are currently allocated
         on this core."
    ::= { tCoreResEntry 5 }

tCoreResIngDdctdPolicerTotal     OBJECT-TYPE
    SYNTAX      Unsigned32
    MAX-ACCESS  read-only
    STATUS      current
    DESCRIPTION
        "The value of tCoreResIngDdctdPolicerTotal represents the total number
         of ingress dedicated policers that are supported on this core.

         When the value of tCoreResIngDdctdPolicerTotal is zero, it indicates
         that this resource type is not supported on this core."
    ::= { tCoreResEntry 6 }

tCoreResIngDdctdPolicerAlloc     OBJECT-TYPE
    SYNTAX      Unsigned32
    MAX-ACCESS  read-only
    STATUS      current
    DESCRIPTION
        "The value of tCoreResIngDdctdPolicerAlloc represents the total number
         of ingress dedicated policers that are currently allocated on this
         core."
    ::= { tCoreResEntry 7 }

tCoreResIngDdctdPolicerStatTotal OBJECT-TYPE
    SYNTAX      Unsigned32
    MAX-ACCESS  read-only
    STATUS      current
    DESCRIPTION
        "The value of tCoreResIngDdctdPolicerStatTotal represents the total
         number of ingress dedicated policer stats that are supported on this
         core.

         When the value of tCoreResIngDdctdPolicerStatTotal is zero, it
         indicates that this resource type is not supported on this core."
    ::= { tCoreResEntry 8 }

tCoreResIngDdctdPolicerStatAlloc OBJECT-TYPE
    SYNTAX      Unsigned32
    MAX-ACCESS  read-only
    STATUS      current
    DESCRIPTION
        "The value of tCoreResIngDdctdPolicerStatAlloc represents the total
         number of ingress dedicated policer stats that are currently allocated
         on this core."
    ::= { tCoreResEntry 9 }

tCoreResVlanVoqTotal             OBJECT-TYPE
    SYNTAX      Unsigned32
    MAX-ACCESS  read-only
    STATUS      current
    DESCRIPTION
        "The value of tCoreResVlanVoqTotal represents the total number of VLAN
         Voqs that are supported on this core.

         When the value of tCoreResVlanVoqTotal is zero, it indicates that this
         resource type is not supported on this core."
    ::= { tCoreResEntry 10 }

tCoreResVlanVoqAlloc             OBJECT-TYPE
    SYNTAX      Unsigned32
    MAX-ACCESS  read-only
    STATUS      current
    DESCRIPTION
        "The value of tCoreResVlanVoqAlloc represents the total number of VLAN
         Voqs that are currently allocated on this core."
    ::= { tCoreResEntry 11 }

tCoreResSapTotal                 OBJECT-TYPE
    SYNTAX      Unsigned32
    MAX-ACCESS  read-only
    STATUS      current
    DESCRIPTION
        "The value of tCoreResSapTotal represents the total number of
         provisioned SAP entries supported on this core."
    ::= { tCoreResEntry 12 }

tCoreResSapAlloc                 OBJECT-TYPE
    SYNTAX      Unsigned32
    MAX-ACCESS  read-only
    STATUS      current
    DESCRIPTION
        "The value of tCoreResSapAlloc represents the total number of
         provisioned SAP entries currently in use on this core."
    ::= { tCoreResEntry 13 }

tCoreResIngFloatPlcrStatIUBACL   OBJECT-TYPE
    SYNTAX      Unsigned32
    MAX-ACCESS  read-only
    STATUS      current
    DESCRIPTION
        "The value of tCoreResIngFloatPlcrStatIUBACL represents the subset of
         floating policer stats which are currently in use by ingress ACLs for
         stats collection."
    ::= { tCoreResEntry 14 }

tCoreResSharedPolicerTotal       OBJECT-TYPE
    SYNTAX      Unsigned32
    MAX-ACCESS  read-only
    STATUS      current
    DESCRIPTION
        "The value of tCoreResSharedPolicerTotal represents the total number of
         shared policers that are supported on this core.

         When the value of tCoreResSharedPolicerTotal is zero, it indicates
         that this resource type is not supported on this core."
    ::= { tCoreResEntry 15 }

tCoreResSharedPolicerAlloc       OBJECT-TYPE
    SYNTAX      Unsigned32
    MAX-ACCESS  read-only
    STATUS      current
    DESCRIPTION
        "The value of tCoreResSharedPolicerAlloc represents the total number of
         shared policers that are currently allocated on this core."
    ::= { tCoreResEntry 16 }

tCoreResIngFloatPlcrStatIUBSP    OBJECT-TYPE
    SYNTAX      Unsigned32
    MAX-ACCESS  read-only
    STATUS      current
    DESCRIPTION
        "The value of tCoreResIngFloatPlcrStatIUBSP represents the subset of
         floating policer stats which are currently in use by shared policers
         for stats collection."
    ::= { tCoreResEntry 17 }

tCoreResSharedPolicerStatsTotal  OBJECT-TYPE
    SYNTAX      Unsigned32
    MAX-ACCESS  read-only
    STATUS      current
    DESCRIPTION
        "The value of tCoreResSharedPolicerStatsTotal represents the total
         number of shared policer stats that are supported on this core"
    ::= { tCoreResEntry 18 }

tCoreResSharedPolicerStatsAlloc  OBJECT-TYPE
    SYNTAX      Unsigned32
    MAX-ACCESS  read-only
    STATUS      current
    DESCRIPTION
        "The value of tCoreResSharedPolicerStatsAlloc represents the total
         number of shared policer stats that are currently allocated on this
         core"
    ::= { tCoreResEntry 19 }

tCoreRes4QVlanVoqTotal           OBJECT-TYPE
    SYNTAX      Unsigned32
    MAX-ACCESS  read-only
    STATUS      current
    DESCRIPTION
        "The value of tCoreRes4QVlanVoqTotal represents the total number of
         4-queue vlan qos resources that are supported on this core"
    ::= { tCoreResEntry 20 }

tCoreRes4QVlanVoqAlloc           OBJECT-TYPE
    SYNTAX      Unsigned32
    MAX-ACCESS  read-only
    STATUS      current
    DESCRIPTION
        "The value of tCoreRes4QVlanVoqAlloc represents the total number of
         4-queue vlan qos resources that are currently allocated on this core"
    ::= { tCoreResEntry 21 }

tCoreResFltrSharedPlcrTotal      OBJECT-TYPE
    SYNTAX      Unsigned32
    MAX-ACCESS  read-only
    STATUS      current
    DESCRIPTION
        "The value of tCoreResFltrSharedPlcrTotal represents the total number
         of filter shared policers that are supported on this core.

         When the value of tCoreResFltrSharedPlcrTotal is zero, it indicates
         that this resource type is not supported on this core."
    ::= { tCoreResEntry 22 }

tCoreResFltrSharedPlcrAlloc      OBJECT-TYPE
    SYNTAX      Unsigned32
    MAX-ACCESS  read-only
    STATUS      current
    DESCRIPTION
        "The value of tCoreResFltrSharedPlcrAlloc represents the total number
         of filter shared policers that are currently allocated on this core."
    ::= { tCoreResEntry 23 }

tCoreResFltrSharedPlcrStatsTotal OBJECT-TYPE
    SYNTAX      Unsigned32
    MAX-ACCESS  read-only
    STATUS      current
    DESCRIPTION
        "The value of tCoreResFltrSharedPlcrStatsTotal represents the total
         number of filter shared policer stats that are supported on this core"
    ::= { tCoreResEntry 24 }

tCoreResFltrSharedPlcrStatsAlloc OBJECT-TYPE
    SYNTAX      Unsigned32
    MAX-ACCESS  read-only
    STATUS      current
    DESCRIPTION
        "The value of tCoreResSharedPolicerStatsAlloc represents the total
         number of filter shared policer stats that are currently allocated on
         this core"
    ::= { tCoreResEntry 25 }

tCoreResSchedulerFlowTotal       OBJECT-TYPE
    SYNTAX      Unsigned32
    MAX-ACCESS  read-only
    STATUS      current
    DESCRIPTION
        "The value of tCoreResSchedulerFlowTotal represents the total number of
         scheduler flows that are supported on this core"
    ::= { tCoreResEntry 26 }

tCoreResSchedulerFlowAlloc       OBJECT-TYPE
    SYNTAX      Unsigned32
    MAX-ACCESS  read-only
    STATUS      current
    DESCRIPTION
        "The value of tCoreResSchedulerFlowAlloc represents the total number of
         scheduler flows that are currently allocated on this core"
    ::= { tCoreResEntry 27 }

tCoreResSchedulerInterfacesTotal OBJECT-TYPE
    SYNTAX      Unsigned32
    MAX-ACCESS  read-only
    STATUS      current
    DESCRIPTION
        "The value of tCoreResSchedulerInterfacesTotal represents the total
         number of scheduler interfaces that are supported on this core"
    ::= { tCoreResEntry 28 }

tCoreResSchedulerInterfacesAlloc OBJECT-TYPE
    SYNTAX      Unsigned32
    MAX-ACCESS  read-only
    STATUS      current
    DESCRIPTION
        "The value of tCoreResSchedulerInterfacesAlloc represents the total
         number of scheduler interfaces that are currently allocated on this
         core"
    ::= { tCoreResEntry 29 }

tCoreRes8QVirtualFlowTotal       OBJECT-TYPE
    SYNTAX      Unsigned32
    MAX-ACCESS  read-only
    STATUS      current
    DESCRIPTION
        "The value of tCoreRes8QVirtualFlowTotal represents the total number of
         eight queue virtual flows that are supported on this core"
    ::= { tCoreResEntry 30 }

tCoreRes8QVirtualFlowAlloc       OBJECT-TYPE
    SYNTAX      Unsigned32
    MAX-ACCESS  read-only
    STATUS      current
    DESCRIPTION
        "The value of tCoreRes8QVirtualFlowAlloc represents the total number of
         eight queue virtual flows that are currently allocated on this core"
    ::= { tCoreResEntry 31 }

tCoreRes4QVirtualFlowTotal       OBJECT-TYPE
    SYNTAX      Unsigned32
    MAX-ACCESS  read-only
    STATUS      current
    DESCRIPTION
        "The value of tCoreRes4QVirtualFlowTotal represents the total number of
         four queue virtual flows that are supported on this core"
    ::= { tCoreResEntry 32 }

tCoreRes4QVirtualFlowAlloc       OBJECT-TYPE
    SYNTAX      Unsigned32
    MAX-ACCESS  read-only
    STATUS      current
    DESCRIPTION
        "The value of tCoreRes4QVirtualFlowAlloc represents the total number of
         four queue virtual flows that are currently allocated on this core"
    ::= { tCoreResEntry 33 }

tCoreRes8QLowRateVlanVoqTotal    OBJECT-TYPE
    SYNTAX      Unsigned32
    MAX-ACCESS  read-only
    STATUS      current
    DESCRIPTION
        "The value of tCoreRes8QLowRateVlanVoqTotal represents the total number
         of 8-queue low rate vlan qos resources that are supported on this core"
    ::= { tCoreResEntry 34 }

tCoreRes8QLowRateVlanVoqAlloc    OBJECT-TYPE
    SYNTAX      Unsigned32
    MAX-ACCESS  read-only
    STATUS      current
    DESCRIPTION
        "The value of tCoreRes8QLowRateVlanVoqAlloc represents the total number
         of 8-queue low rate vlan qos resources that are currently allocated on
         this core"
    ::= { tCoreResEntry 35 }

tCoreRes4QLowRateVlanVoqTotal    OBJECT-TYPE
    SYNTAX      Unsigned32
    MAX-ACCESS  read-only
    STATUS      current
    DESCRIPTION
        "The value of tCoreRes4QLowRateVlanVoqTotal represents the total number
         of 4-queue low rate vlan qos resources that are supported on this core"
    ::= { tCoreResEntry 36 }

tCoreRes4QLowRateVlanVoqAlloc    OBJECT-TYPE
    SYNTAX      Unsigned32
    MAX-ACCESS  read-only
    STATUS      current
    DESCRIPTION
        "The value of tCoreRes4QLowRateVlanVoqAlloc represents the total number
         of 4-queue low rate vlan qos resources that are currently allocated on
         this core"
    ::= { tCoreResEntry 37 }

tmnxXiomConfigTableLastChanged   OBJECT-TYPE
    SYNTAX      TimeStamp
    MAX-ACCESS  read-only
    STATUS      current
    DESCRIPTION
        "The value of tmnxXiomConfigTableLastChanged indicates the time, since
         system startup, when tmnxXiomConfigTable last changed configuration."
    ::= { tmnxCardObjs 77 }

tmnxXiomConfigTable              OBJECT-TYPE
    SYNTAX      SEQUENCE OF TmnxXiomConfigEntry
    MAX-ACCESS  not-accessible
    STATUS      current
    DESCRIPTION
        "The tmnxXiomConfigTable contains configuration information regarding
         the XIOM in the system."
    ::= { tmnxCardObjs 78 }

tmnxXiomConfigEntry              OBJECT-TYPE
    SYNTAX      TmnxXiomConfigEntry
    MAX-ACCESS  not-accessible
    STATUS      current
    DESCRIPTION
        "Each row entry represents XIOM configuration in the system.

         Rows in this table are created by the agent at initialization and
         cannot be created or destroyed by SNMP Set requests."
    INDEX       {
        tmnxCardSlotNum,
        tmnxXiomSlotNum
    }
    ::= { tmnxXiomConfigTable 1 }

TmnxXiomConfigEntry              ::= SEQUENCE
{
    tmnxXiomSlotNum                  Unsigned32,
    tmnxXiomConfigEntryLastChanged   TimeStamp,
    tmnxXiomAssignedType             TmnxXiomType,
    tmnxXiomAssignedLevel            TmnxXiomFunctionalLevel,
    tmnxXiomReboot                   TmnxActionType,
    tmnxXiomFailOnError              TruthValue,
    tmnxXiomResetOnRecoverableError  TruthValue
}

tmnxXiomSlotNum                  OBJECT-TYPE
    SYNTAX      Unsigned32 (1..2)
    MAX-ACCESS  not-accessible
    STATUS      current
    DESCRIPTION
        "The unique value which identifies this XIOM slot within a card in the
         system."
    ::= { tmnxXiomConfigEntry 1 }

tmnxXiomConfigEntryLastChanged   OBJECT-TYPE
    SYNTAX      TimeStamp
    MAX-ACCESS  read-only
    STATUS      current
    DESCRIPTION
        "The value of tmnxXiomConfigEntryLastChanged indicates the time, since
         system startup, that the configuration of the row was last modified."
    ::= { tmnxXiomConfigEntry 2 }

tmnxXiomAssignedType             OBJECT-TYPE
    SYNTAX      TmnxXiomType
    MAX-ACCESS  read-write
    STATUS      current
    DESCRIPTION
        "The value of tmnxXiomAssignedType specifies the XIOM type that was
         administratively assigned to this slot. A value of 1 indicates this
         slot is unassigned."
    DEFVAL      { 1 }
    ::= { tmnxXiomConfigEntry 3 }

tmnxXiomAssignedLevel            OBJECT-TYPE
    SYNTAX      TmnxXiomFunctionalLevel
    MAX-ACCESS  read-write
    STATUS      current
    DESCRIPTION
        "The value of tmnxXiomAssignedLevel specifies the administratively
         assigned (pre-provisioned) XIOM functional level variant that should
         occupy this slot in this chassis."
    DEFVAL      { unrestricted }
    ::= { tmnxXiomConfigEntry 4 }

tmnxXiomReboot                   OBJECT-TYPE
    SYNTAX      TmnxActionType
    MAX-ACCESS  read-write
    STATUS      current
    DESCRIPTION
        "The value of tmnxXiomReboot, when set to 'doAction(1)', causes the
         XIOM to execute a soft-reboot."
    DEFVAL      { notApplicable }
    ::= { tmnxXiomConfigEntry 5 }

tmnxXiomFailOnError              OBJECT-TYPE
    SYNTAX      TruthValue
    MAX-ACCESS  read-write
    STATUS      current
    DESCRIPTION
        "The value of tmnxXiomFailOnError specifies the whether or not the XIOM
         will fail when an error occurs."
    DEFVAL      { false }
    ::= { tmnxXiomConfigEntry 6 }

tmnxXiomResetOnRecoverableError  OBJECT-TYPE
    SYNTAX      TruthValue
    MAX-ACCESS  read-write
    STATUS      current
    DESCRIPTION
        "The value of tmnxXiomResetOnRecoverableError specifies whether or not
         the system resets the XIOM when there are fatal memory parity errors
         on one of the Q-chips on the card with which this XIOM is associated.

         If the value of tmnxXiomResetOnRecoverableError is 'true (1)' and
         there is a fatal memory parity error on a Q-chip, the system will
         reset the XIOM but not fail it, even if tmnxXiomFailOnError is 'true
         (1)'."
    DEFVAL      { false }
    ::= { tmnxXiomConfigEntry 7 }

tmnxXiomStatsTable               OBJECT-TYPE
    SYNTAX      SEQUENCE OF TmnxXiomStatsEntry
    MAX-ACCESS  not-accessible
    STATUS      current
    DESCRIPTION
        "The tmnxXiomStatsTable contains status and statistic information
         regarding the XIOM in the system."
    ::= { tmnxCardObjs 79 }

tmnxXiomStatsEntry               OBJECT-TYPE
    SYNTAX      TmnxXiomStatsEntry
    MAX-ACCESS  not-accessible
    STATUS      current
    DESCRIPTION
        "Each row entry represents XIOM status and statistic information in the
         system.

         Rows in this table are created by the agent at initialization and
         cannot be created or destroyed by SNMP Set requests."
    AUGMENTS    { tmnxXiomConfigEntry }
    ::= { tmnxXiomStatsTable 1 }

TmnxXiomStatsEntry               ::= SEQUENCE
{
    tmnxXiomEquippedType             TmnxXiomType,
    tmnxXiomEquippedLevel            TmnxXiomFunctionalLevel,
    tmnxXiomLicensedLevel            TmnxXiomFunctionalLevel,
    tmnxXiomAvailableMdaSlots        Unsigned32,
    tmnxXiomNumEquippedMdas          Unsigned32,
    tmnxXiomHwIndex                  TmnxHwIndex,
    tmnxXiomSupportedTypes           TmnxXiomSuppType
}

tmnxXiomEquippedType             OBJECT-TYPE
    SYNTAX      TmnxXiomType
    MAX-ACCESS  read-only
    STATUS      current
    DESCRIPTION
        "The value of tmnxXiomEquippedType indicates indicates the XIOM type
         that is physically inserted into this slot. If the slot has been
         pre-provisioned and the value of tmnxXiomEquippedType is not the same
         as tmnxXiomAssignedType, a mismatch alarm will be raised. A value of 0
         indicates the equipped XIOM is not supported by this software release."
    ::= { tmnxXiomStatsEntry 1 }

tmnxXiomEquippedLevel            OBJECT-TYPE
    SYNTAX      TmnxXiomFunctionalLevel
    MAX-ACCESS  read-only
    STATUS      current
    DESCRIPTION
        "The value of tmnxXiomEquippedLevel indicates the XIOM functional-level
         variant that is physically inserted into this slot in this chassis.  If
         the value of tmnxXiomAssignedLevel is not equal to the value of
         tmnxXiomEquippedLevel, a mismatch alarm will be raised."
    ::= { tmnxXiomStatsEntry 2 }

tmnxXiomLicensedLevel            OBJECT-TYPE
    SYNTAX      TmnxXiomFunctionalLevel
    MAX-ACCESS  read-only
    STATUS      current
    DESCRIPTION
        "The value of tmnxXiomLicensedLevel indicates the XIOM functional-level
         that is licensed for this slot in this chassis."
    ::= { tmnxXiomStatsEntry 3 }

tmnxXiomAvailableMdaSlots        OBJECT-TYPE
    SYNTAX      Unsigned32
    MAX-ACCESS  read-only
    STATUS      current
    DESCRIPTION
        "The value of tmnxXiomAvailableMdaSlots indicates the number of
         available MDA slots on this XIOM."
    ::= { tmnxXiomStatsEntry 4 }

tmnxXiomNumEquippedMdas          OBJECT-TYPE
    SYNTAX      Unsigned32
    MAX-ACCESS  read-only
    STATUS      current
    DESCRIPTION
        "The value of tmnxXiomNumEquippedMdas indicates the number of equipped
         MDAs on this XIOM."
    ::= { tmnxXiomStatsEntry 5 }

tmnxXiomHwIndex                  OBJECT-TYPE
    SYNTAX      TmnxHwIndex
    MAX-ACCESS  read-only
    STATUS      current
    DESCRIPTION
        "The value of tmnxXiomHwIndex indicates the hardware index into the
         tmnxHwTable for the row entry that represents the hardware component
         information for this XIOM."
    ::= { tmnxXiomStatsEntry 6 }

tmnxXiomSupportedTypes           OBJECT-TYPE
    SYNTAX      TmnxXiomSuppType
    MAX-ACCESS  read-only
    STATUS      current
    DESCRIPTION
        "The value of tmnxXiomSupportedTypes indicates what XIOM types can be
         configured in this slot in this chassis."
    ::= { tmnxXiomStatsEntry 7 }

tmnxXiomTypeTable                OBJECT-TYPE
    SYNTAX      SEQUENCE OF TmnxXiomTypeEntry
    MAX-ACCESS  not-accessible
    STATUS      current
    DESCRIPTION
        "The tmnxXiomTypeTable contains an entry for every XIOM type supported
         by the system."
    ::= { tmnxCardObjs 80 }

tmnxXiomTypeEntry                OBJECT-TYPE
    SYNTAX      TmnxXiomTypeEntry
    MAX-ACCESS  not-accessible
    STATUS      current
    DESCRIPTION
        "Each row entry represents an Nokia SROS series XIOM.

         Rows in this table are created by the agent at initialization and
         cannot be created or destroyed by SNMP Get or Set requests."
    INDEX       { tmnxXiomTypeIndex }
    ::= { tmnxXiomTypeTable 1 }

TmnxXiomTypeEntry                ::= SEQUENCE
{
    tmnxXiomTypeIndex                TmnxXiomType,
    tmnxXiomTypeName                 TNamedItemOrEmpty,
    tmnxXiomTypeDescription          TItemDescription,
    tmnxXiomTypeStatus               TruthValue
}

tmnxXiomTypeIndex                OBJECT-TYPE
    SYNTAX      TmnxXiomType
    MAX-ACCESS  not-accessible
    STATUS      current
    DESCRIPTION
        "The value of tmnxXiomTypeIndex specifies the unique index value which
         identifies this type of Nokia SROS series XIOM."
    ::= { tmnxXiomTypeEntry 1 }

tmnxXiomTypeName                 OBJECT-TYPE
    SYNTAX      TNamedItemOrEmpty
    MAX-ACCESS  read-only
    STATUS      current
    DESCRIPTION
        "The value of tmnxXiomTypeName indicates the administrative name
         that identifies this type of Nokia SROS series XIOM.  This name
         string may be used in CLI commands to specify a particular XIOM type."
    ::= { tmnxXiomTypeEntry 2 }

tmnxXiomTypeDescription          OBJECT-TYPE
    SYNTAX      TItemDescription
    MAX-ACCESS  read-only
    STATUS      current
    DESCRIPTION
        "The value of tmnxXiomTypeDescription indicates a detailed description
         of this Nokia SROS series XIOM."
    ::= { tmnxXiomTypeEntry 3 }

tmnxXiomTypeStatus               OBJECT-TYPE
    SYNTAX      TruthValue
    MAX-ACCESS  read-only
    STATUS      current
    DESCRIPTION
        "The value of tmnxXiomTypeStatus indicates whether or not this XIOM is
         supported in this revision of the management software."
    ::= { tmnxXiomTypeEntry 4 }

tmnxXiomLevelTable               OBJECT-TYPE
    SYNTAX      SEQUENCE OF TmnxXiomLevelEntry
    MAX-ACCESS  not-accessible
    STATUS      current
    DESCRIPTION
        "The XIOM level table has an entry for each XIOM card model functional
         variant supported by the system."
    ::= { tmnxCardObjs 81 }

tmnxXiomLevelEntry               OBJECT-TYPE
    SYNTAX      TmnxXiomLevelEntry
    MAX-ACCESS  not-accessible
    STATUS      current
    DESCRIPTION
        "Each row entry represents an Nokia SROS series XIOM card
         model.  Rows in this table are created by the agent at initialization
         and cannot be created or destroyed by SNMP Get or Set requests."
    INDEX       {
        tmnxXiomTypeIndex,
        tmnxXiomLevelIndex
    }
    ::= { tmnxXiomLevelTable 1 }

TmnxXiomLevelEntry               ::= SEQUENCE
{
    tmnxXiomLevelIndex               Unsigned32,
    tmnxXiomLevelName                TNamedItemOrEmpty,
    tmnxXiomLevelId                  TmnxXiomFunctionalLevel,
    tmnxXiomLevelDescription         TItemDescription,
    tmnxXiomLevelStatus              TruthValue
}

tmnxXiomLevelIndex               OBJECT-TYPE
    SYNTAX      Unsigned32
    MAX-ACCESS  not-accessible
    STATUS      current
    DESCRIPTION
        "The value of tmnxXiomLevelIndex specifies the unique index value which
         identifies this type of Nokia SROS series XIOM card model functional
         variant."
    ::= { tmnxXiomLevelEntry 1 }

tmnxXiomLevelName                OBJECT-TYPE
    SYNTAX      TNamedItemOrEmpty
    MAX-ACCESS  read-only
    STATUS      current
    DESCRIPTION
        "The value of tmnxXiomLevelName indicates the administrative name that
         identifies this type of Nokia SROS series XIOM card model functional
         variant."
    ::= { tmnxXiomLevelEntry 2 }

tmnxXiomLevelId                  OBJECT-TYPE
    SYNTAX      TmnxXiomFunctionalLevel
    MAX-ACCESS  read-only
    STATUS      current
    DESCRIPTION
        "The value of tmnxXiomLevelId indicates the numeric identifier of this
         type of Nokia SROS series XIOM model functional variant."
    ::= { tmnxXiomLevelEntry 3 }

tmnxXiomLevelDescription         OBJECT-TYPE
    SYNTAX      TItemDescription
    MAX-ACCESS  read-only
    STATUS      current
    DESCRIPTION
        "The value of tmnxXiomLevelDescription indicates a detailed description
         of this Nokia SROS series XIOM card model functional variant."
    ::= { tmnxXiomLevelEntry 4 }

tmnxXiomLevelStatus              OBJECT-TYPE
    SYNTAX      TruthValue
    MAX-ACCESS  read-only
    STATUS      current
    DESCRIPTION
        "The value of tmnxXiomLevelStatus indicates the status.

         A value of 'true' it indicates that this XIOM card level is supported
         in this revision of the management software.  A value of 'false'
         indicates there is no support."
    ::= { tmnxXiomLevelEntry 5 }

tmnxXiomLvlUpgrdTableLastChanged OBJECT-TYPE
    SYNTAX      TimeStamp
    MAX-ACCESS  read-only
    STATUS      current
    DESCRIPTION
        "The value of tmnxXiomLvlUpgrdTableLastChanged indicates the time,
         since system startup, when tmnxXiomLevelUpgradeTable last changed
         configuration."
    ::= { tmnxCardObjs 82 }

tmnxXiomLevelUpgradeTable        OBJECT-TYPE
    SYNTAX      SEQUENCE OF TmnxXiomLevelUpgradeEntry
    MAX-ACCESS  not-accessible
    STATUS      current
    DESCRIPTION
        "The tmnxXiomLevelUpgradeTable has an entry for each upgrade that has
         been applied to an XIOM slot."
    ::= { tmnxCardObjs 83 }

tmnxXiomLevelUpgradeEntry        OBJECT-TYPE
    SYNTAX      TmnxXiomLevelUpgradeEntry
    MAX-ACCESS  not-accessible
    STATUS      current
    DESCRIPTION
        "Each row entry represents an XIOM slot applied upgrade in a chassis in
         the system."
    INDEX       {
        tmnxCardSlotNum,
        tmnxXiomSlotNum,
        tmnxXiomLevelUpgradeIndex
    }
    ::= { tmnxXiomLevelUpgradeTable 1 }

TmnxXiomLevelUpgradeEntry        ::= SEQUENCE
{
    tmnxXiomLevelUpgradeIndex        Unsigned32,
    tmnxXiomLevelUpgradeRowStatus    RowStatus,
    tmnxXiomAssignedLevelUpgradeType TmnxXiomFunctionalUpgrade
}

tmnxXiomLevelUpgradeIndex        OBJECT-TYPE
    SYNTAX      Unsigned32 (1..6)
    MAX-ACCESS  not-accessible
    STATUS      current
    DESCRIPTION
        "The value of tmnxXiomLevelUpgradeIndex specifies the index value which
         identifies this type of Nokia SROS series XIOM model functional
         upgrade."
    ::= { tmnxXiomLevelUpgradeEntry 1 }

tmnxXiomLevelUpgradeRowStatus    OBJECT-TYPE
    SYNTAX      RowStatus
    MAX-ACCESS  read-create
    STATUS      current
    DESCRIPTION
        "The value of tmnxXiomLevelUpgradeRowStatus specifies the row status of
         the XIOM level upgrade."
    ::= { tmnxXiomLevelUpgradeEntry 2 }

tmnxXiomAssignedLevelUpgradeType OBJECT-TYPE
    SYNTAX      TmnxXiomFunctionalUpgrade
    MAX-ACCESS  read-create
    STATUS      current
    DESCRIPTION
        "The value of tmnxXiomAssignedLevelUpgradeType specifies the unique
         index value which identifies the Nokia SROS series XIOM model
         functional upgrade to apply."
    ::= { tmnxXiomLevelUpgradeEntry 3 }

tmnxXiomLevelUpgradeTypeTable    OBJECT-TYPE
    SYNTAX      SEQUENCE OF TmnxXiomLevelUpgradeTypeEntry
    MAX-ACCESS  not-accessible
    STATUS      current
    DESCRIPTION
        "The tmnxXiomLevelUpgradeTypeTable has an entry for each possible
         upgrade of an XIOM based on it's current tmnxXiomLicensedLevel."
    ::= { tmnxCardObjs 84 }

tmnxXiomLevelUpgradeTypeEntry    OBJECT-TYPE
    SYNTAX      TmnxXiomLevelUpgradeTypeEntry
    MAX-ACCESS  not-accessible
    STATUS      current
    DESCRIPTION
        "Each tmnxXiomLevelUpgradeTypeEntry represents an XIOM slot upgrade
         type in the system based on tmnxXiomLicensedLevel."
    INDEX       {
        tmnxCardSlotNum,
        tmnxXiomSlotNum,
        tmnxXiomLevelUpgradeType
    }
    ::= { tmnxXiomLevelUpgradeTypeTable 1 }

TmnxXiomLevelUpgradeTypeEntry    ::= SEQUENCE
{
    tmnxXiomLevelUpgradeType         TmnxXiomFunctionalUpgrade,
    tmnxXiomLevelUpgradeName         TNamedItemOrEmpty,
    tmnxXiomUpgradeLevelId           TmnxXiomFunctionalLevel,
    tmnxXiomUpgradeRequiresReboot    TruthValue
}

tmnxXiomLevelUpgradeType         OBJECT-TYPE
    SYNTAX      TmnxXiomFunctionalUpgrade
    MAX-ACCESS  not-accessible
    STATUS      current
    DESCRIPTION
        "The value of tmnxXiomLevelUpgradeType specifies a unique index value
         which identifies this type of Nokia SROS series XIOM model functional
         upgrade"
    ::= { tmnxXiomLevelUpgradeTypeEntry 1 }

tmnxXiomLevelUpgradeName         OBJECT-TYPE
    SYNTAX      TNamedItemOrEmpty
    MAX-ACCESS  read-only
    STATUS      current
    DESCRIPTION
        "The value of tmnxXiomLevelUpgradeName indicates the administrative
         name that identifies this type of Nokia SROS series XIOM model
         functional upgrade."
    ::= { tmnxXiomLevelUpgradeTypeEntry 2 }

tmnxXiomUpgradeLevelId           OBJECT-TYPE
    SYNTAX      TmnxXiomFunctionalLevel
    MAX-ACCESS  read-only
    STATUS      current
    DESCRIPTION
        "The value of tmnxXiomUpgradeLevelId indicates the XIOM upgraded
         functional-level with this license applied for this slot in this
         chassis."
    ::= { tmnxXiomLevelUpgradeTypeEntry 3 }

tmnxXiomUpgradeRequiresReboot    OBJECT-TYPE
    SYNTAX      TruthValue
    MAX-ACCESS  read-only
    STATUS      current
    DESCRIPTION
        "The value of tmnxXiomUpgradeRequiresReboot indicates whether this
         upgrade requires a reboot of the XIOM to be applied for this slot in
         this chassis."
    ::= { tmnxXiomLevelUpgradeTypeEntry 4 }

tmnxEsaVmCoreUtilStatsTable      OBJECT-TYPE
    SYNTAX      SEQUENCE OF TmnxEsaVmCoreUtilStatsEntry
    MAX-ACCESS  not-accessible
    STATUS      current
    DESCRIPTION
        "The tmnxEsaVmCoreUtilStatsTable contains entries for the core
         utilization  of each esa-vm."
    ::= { tmnxCardObjs 85 }

tmnxEsaVmCoreUtilStatsEntry      OBJECT-TYPE
    SYNTAX      TmnxEsaVmCoreUtilStatsEntry
    MAX-ACCESS  not-accessible
    STATUS      current
    DESCRIPTION
        "Each tmnxEsaVmCoreUtilStatsEntry represents a VM core instance on an
         esa-vm and contains its utilization information.

         Entries in this table are created and destroyed  automatically by the
         system."
    INDEX       {
        tmnxEsaId,
        tmnxEsaVmId,
        tmnxEsaVmVirtualCoreId
    }
    ::= { tmnxEsaVmCoreUtilStatsTable 1 }

TmnxEsaVmCoreUtilStatsEntry      ::= SEQUENCE
{
    tmnxEsaVmVirtualCoreId           Unsigned32,
    tmnxEsaVmVirtualCoreRoleName     TNamedItem,
    tmnxEsaVmVirtCoreCurUtilization  Unsigned32,
    tmnxEsaVmVirtCoreAvgUtilization  Unsigned32,
    tmnxEsaVmVirtCorePeakUtilization Unsigned32
}

tmnxEsaVmVirtualCoreId           OBJECT-TYPE
    SYNTAX      Unsigned32 (1..62)
    MAX-ACCESS  not-accessible
    STATUS      current
    DESCRIPTION
        "The value of tmnxEsaVmVirtualCoreId indicates the virtual core number
         for the given VM."
    ::= { tmnxEsaVmCoreUtilStatsEntry 1 }

tmnxEsaVmVirtualCoreRoleName     OBJECT-TYPE
    SYNTAX      TNamedItem
    MAX-ACCESS  read-only
    STATUS      current
    DESCRIPTION
        "The value of tmnxEsaVmVirtualCoreRoleName specifies the esa-vm virtual
         core role."
    ::= { tmnxEsaVmCoreUtilStatsEntry 2 }

tmnxEsaVmVirtCoreCurUtilization  OBJECT-TYPE
    SYNTAX      Unsigned32
    UNITS       "hundredths of a percent"
    MAX-ACCESS  read-only
    STATUS      current
    DESCRIPTION
        "The value of tmnxEsaVmVirtCoreCurUtilization indicates the current
         utilization of this virtual core on the esa-vm. For management virtual
         cores, the current utilization is the percentage of time spent during
         a 10 second interval running tasks other than the idle task. For
         worker, nic, and scheduler virtual cores, the current utilization is
         the percentage of time spent during a 10 second interval performing
         packet processing tasks and/or housekeeping operations."
    ::= { tmnxEsaVmCoreUtilStatsEntry 3 }

tmnxEsaVmVirtCoreAvgUtilization  OBJECT-TYPE
    SYNTAX      Unsigned32
    UNITS       "hundredths of a percent"
    MAX-ACCESS  read-only
    STATUS      current
    DESCRIPTION
        "The value of tmnxEsaVmVirtCoreAvgUtilization indicates the average
         utilization of this virtual core on the esa-vm. For management virtual
         cores, the average utilization is the percentage of time spent during
         a 15-minute interval running tasks other than the idle task. For
         worker, nic, and scheduler virtual cores, the average utilization is
         the percentage of time spent during a 15-minute interval performing
         packet processing tasks and/or housekeeping operations."
    ::= { tmnxEsaVmCoreUtilStatsEntry 4 }

tmnxEsaVmVirtCorePeakUtilization OBJECT-TYPE
    SYNTAX      Unsigned32
    UNITS       "hundredths of a percent"
    MAX-ACCESS  read-only
    STATUS      current
    DESCRIPTION
        "The value of tmnxEsaVmVirtCorePeakUtilization indicates the  all-time
         peak 10-second utilization of this virtual core on  the esa-vm."
    ::= { tmnxEsaVmCoreUtilStatsEntry 5 }

tmnxIPsecIsaMemberPoolTable      OBJECT-TYPE
    SYNTAX      SEQUENCE OF TmnxIPsecIsaMemberPoolEntry
    MAX-ACCESS  not-accessible
    STATUS      current
    DESCRIPTION
        "Table to store entries for pools of IPSec Integrated Service
         Adaptor (ISA) tunnel-group members.  Pooling tunnel-group members
         allows a common set of members to be associated with multiple
         tunnel-groups."
    ::= { tmnxCardObjs 86 }

tmnxIPsecIsaMemberPoolEntry      OBJECT-TYPE
    SYNTAX      TmnxIPsecIsaMemberPoolEntry
    MAX-ACCESS  not-accessible
    STATUS      current
    DESCRIPTION
        "Information about a single IPsec ISA member pool entry."
    INDEX       { tmnxIPsecIsaMemberPoolName }
    ::= { tmnxIPsecIsaMemberPoolTable 1 }

TmnxIPsecIsaMemberPoolEntry      ::= SEQUENCE
{
    tmnxIPsecIsaMemberPoolName       TNamedItem,
    tmnxIPsecIsaMemberPoolRowStatus  RowStatus,
    tmnxIPsecIsaMemberPoolLastChgd   TimeStamp,
    tmnxIPsecIsaMemberPoolDesc       TItemDescription,
    tmnxIPsecIsaMemberPoolHighAvail  INTEGER
}

tmnxIPsecIsaMemberPoolName       OBJECT-TYPE
    SYNTAX      TNamedItem
    MAX-ACCESS  read-create
    STATUS      current
    DESCRIPTION
        "The value of tmnxIPsecIsaMemberPoolName specifies the name of a
          TmnxIPsecIsaMemberPoolEntry and is the primary index for the table."
    ::= { tmnxIPsecIsaMemberPoolEntry 1 }

tmnxIPsecIsaMemberPoolRowStatus  OBJECT-TYPE
    SYNTAX      RowStatus
    MAX-ACCESS  read-create
    STATUS      current
    DESCRIPTION
        "The tmnxIPsecIsaMemberPoolRowStatus object is used to create and
         delete rows in the tmnxIPsecIsaMemberPoolTable."
    ::= { tmnxIPsecIsaMemberPoolEntry 2 }

tmnxIPsecIsaMemberPoolLastChgd   OBJECT-TYPE
    SYNTAX      TimeStamp
    MAX-ACCESS  read-only
    STATUS      current
    DESCRIPTION
        "The value of tmnxIPsecIsaMemberPoolLastChgd indicates the sysUpTime at
         the time of the last modification of this entry.

         If no changes were made to the entry since the last re-initialization
         of the local network management subsystem, then this object contains a
         zero value."
    ::= { tmnxIPsecIsaMemberPoolEntry 3 }

tmnxIPsecIsaMemberPoolDesc       OBJECT-TYPE
    SYNTAX      TItemDescription
    MAX-ACCESS  read-create
    STATUS      current
    DESCRIPTION
        "The value of tmnxIPsecIsaMemberPoolDesc specifies the user-provided
         description for each tmnxIPsecIsaMemberPoolEntry in the table
         tmnxIPsecIsaMemberPoolTable."
    DEFVAL      { "" }
    ::= { tmnxIPsecIsaMemberPoolEntry 4 }

tmnxIPsecIsaMemberPoolHighAvail  OBJECT-TYPE
    SYNTAX      INTEGER {
        none              (0),
        tunnelLimitSystem (1),
        tunnelLimit32k    (2),
        tunnelLimit64k    (3),
        tunnelLimit128k   (4),
        tunnelLimit256k   (5)
    }
    MAX-ACCESS  read-create
    STATUS      current
    DESCRIPTION
        "The value of tmnxIPsecIsaMemberPoolHighAvail specifies the maximum
         tunnel scale each pool member can support in high availability mode. A
         value of 'none' disables high availability mode.

         When this object has a value other than 'none' each pool member
         unselected by a tunnel group is maintained in a state of high
         availability for all tunnel groups associated with the pool. In this
         high availability state, each unselected pool member is provisioned
         with the configuration and state information of all associated tunnel
         groups, and the combined tunnel scale of those groups will not be
         permitted to exceed the tunnel limit specified by this object.

         When this object has a value of 'none' high availability is disabled,
         each pool member is only provisioned with the configuration and state
         information of one tunnel group upon selection by that group, and no
         combined tunnel scale is enforced across all associated groups.

         The pool must contain no MDAs or ESA-VMs for this object to be
         configurable to a value other than the default of 'none'."
    DEFVAL      { none }
    ::= { tmnxIPsecIsaMemberPoolEntry 5 }

tmnxIPsecIsaMemberPoolTblLstChgd OBJECT-TYPE
    SYNTAX      TimeStamp
    MAX-ACCESS  read-only
    STATUS      current
    DESCRIPTION
        "The value of tmnxIPsecIsaMemberPoolTblLstChgd indicates the sysUpTime
         at the time of the last modification to tmnxIPsecIsaMemberPoolTable by
         adding, deleting an entry or change to a writable object in the table.

         If no changes were made to the table since the last re-initialization
         of the local network management subsystem, then this object contains a
         zero value."
    ::= { tmnxCardObjs 87 }

tmnxMdaXConMacTableLastChanged   OBJECT-TYPE
    SYNTAX      TimeStamp
    MAX-ACCESS  read-only
    STATUS      current
    DESCRIPTION
        "The value of tmnxMdaXConMacTableLastChanged indicates the time, since
         system startup, when tmnxMdaXConMacTable last changed configuration."
    ::= { tmnxCardObjs 88 }

tmnxMdaXConMacTable              OBJECT-TYPE
    SYNTAX      SEQUENCE OF TmnxMdaXConMacEntry
    MAX-ACCESS  not-accessible
    STATUS      current
    DESCRIPTION
        "The tmnxMdaXConMacTable contains the MDA Cross-Connect  information
         for the Media Access Control (MAC) instances."
    ::= { tmnxCardObjs 89 }

tmnxMdaXConMacEntry              OBJECT-TYPE
    SYNTAX      TmnxMdaXConMacEntry
    MAX-ACCESS  not-accessible
    STATUS      current
    DESCRIPTION
        "The tmnxMdaXConMacEntry consists of the MDA Cross-Connect information
         for a specific MAC."
    INDEX       {
        tmnxCardSlotNum,
        tmnxMDASlotNum,
        tmnxMdaXConMacId
    }
    ::= { tmnxMdaXConMacTable 1 }

TmnxMdaXConMacEntry              ::= SEQUENCE
{
    tmnxMdaXConMacId                 Unsigned32,
    tmnxMdaXConMacRowStatus          RowStatus,
    tmnxMdaXConMacLastChanged        TimeStamp,
    tmnxMdaXConMacDescription        TItemVeryLongDescription
}

tmnxMdaXConMacId                 OBJECT-TYPE
    SYNTAX      Unsigned32 (1..12)
    MAX-ACCESS  not-accessible
    STATUS      current
    DESCRIPTION
        "The value of tmnxMdaXConMacId specifies the MAC identifier for the MDA
         Cross-Connect.

         This value is the chip number which is the physical location of the
         loopback on a forwarding complex."
    ::= { tmnxMdaXConMacEntry 1 }

tmnxMdaXConMacRowStatus          OBJECT-TYPE
    SYNTAX      RowStatus
    MAX-ACCESS  read-create
    STATUS      current
    DESCRIPTION
        "The value of tmnxMdaXConMacRowStatus specifies the row status. It
         allows the creation and deletion of MDA Cross-Connect entries per MAC."
    ::= { tmnxMdaXConMacEntry 2 }

tmnxMdaXConMacLastChanged        OBJECT-TYPE
    SYNTAX      TimeStamp
    MAX-ACCESS  read-only
    STATUS      current
    DESCRIPTION
        "The value of tmnxMdaXConMacLastChanged indicates the time, since
         system startup, that the configuration of this MDA Cross-Connect MAC
         entry was created or modified."
    ::= { tmnxMdaXConMacEntry 3 }

tmnxMdaXConMacDescription        OBJECT-TYPE
    SYNTAX      TItemVeryLongDescription
    MAX-ACCESS  read-create
    STATUS      current
    DESCRIPTION
        "The value of tmnxMdaXConMacDescription specifies the description of
         the MDA Cross-Connect for the specific MAC."
    DEFVAL      { "" }
    ::= { tmnxMdaXConMacEntry 4 }

tmnxMdaXConLpbkTableLastChanged  OBJECT-TYPE
    SYNTAX      TimeStamp
    MAX-ACCESS  read-only
    STATUS      current
    DESCRIPTION
        "The value of tmnxMdaXConLpbkTableLastChanged indicates the time, since
         system startup, when tmnxMdaXConLpbkTable last changed configuration."
    ::= { tmnxCardObjs 90 }

tmnxMdaXConLpbkTable             OBJECT-TYPE
    SYNTAX      SEQUENCE OF TmnxMdaXConLpbkEntry
    MAX-ACCESS  not-accessible
    STATUS      current
    DESCRIPTION
        "The tmnxMdaXConLpbkTable contains the MDA Cross-Connect  information
         for the loopback instances."
    ::= { tmnxCardObjs 91 }

tmnxMdaXConLpbkEntry             OBJECT-TYPE
    SYNTAX      TmnxMdaXConLpbkEntry
    MAX-ACCESS  not-accessible
    STATUS      current
    DESCRIPTION
        "The tmnxMdaXConLpbkEntry consists of the MDA Cross-Connect information
         for a specific loopback instance."
    INDEX       {
        tmnxCardSlotNum,
        tmnxMDASlotNum,
        tmnxMdaXConMacId,
        tmnxMdaXConLoopbackId
    }
    ::= { tmnxMdaXConLpbkTable 1 }

TmnxMdaXConLpbkEntry             ::= SEQUENCE
{
    tmnxMdaXConLoopbackId            Unsigned32,
    tmnxMdaXConLpbkRowStatus         RowStatus,
    tmnxMdaXConLpbkLastChanged       TimeStamp,
    tmnxMdaXConLpbkDescription       TItemVeryLongDescription,
    tmnxMdaXConLpbkBandwidth         Unsigned32
}

tmnxMdaXConLoopbackId            OBJECT-TYPE
    SYNTAX      Unsigned32 (1..2)
    MAX-ACCESS  not-accessible
    STATUS      current
    DESCRIPTION
        "The value of tmnxMdaXConLoopbackId specifies the loopback identifier
         for the MDA Cross-Connect."
    ::= { tmnxMdaXConLpbkEntry 1 }

tmnxMdaXConLpbkRowStatus         OBJECT-TYPE
    SYNTAX      RowStatus
    MAX-ACCESS  read-create
    STATUS      current
    DESCRIPTION
        "The value of tmnxMdaXConLpbkRowStatus specifies the row status. It
         allows the creation and deletion of MDA Cross-Connect entries per
         loopback."
    ::= { tmnxMdaXConLpbkEntry 2 }

tmnxMdaXConLpbkLastChanged       OBJECT-TYPE
    SYNTAX      TimeStamp
    MAX-ACCESS  read-only
    STATUS      current
    DESCRIPTION
        "The value of tmnxMdaXConLpbkLastChanged indicates the time, since
         system startup, that the configuration of this MDA Cross-Connect
         loopback entry was created or modified."
    ::= { tmnxMdaXConLpbkEntry 3 }

tmnxMdaXConLpbkDescription       OBJECT-TYPE
    SYNTAX      TItemVeryLongDescription
    MAX-ACCESS  read-create
    STATUS      current
    DESCRIPTION
        "The value of tmnxMdaXConLpbkDescription specifies the description of
         the MDA Cross-Connect for the specific loopback."
    DEFVAL      { "" }
    ::= { tmnxMdaXConLpbkEntry 4 }

tmnxMdaXConLpbkBandwidth         OBJECT-TYPE
    SYNTAX      Unsigned32 (10 | 25 | 40 | 100 | 400 | 800)
    UNITS       "gigabps"
    MAX-ACCESS  read-create
    STATUS      current
    DESCRIPTION
        "The value of tmnxMdaXConLpbkBandwidth specifies the bandwidth of the
         MDA Cross-Connect for the specific loopback."
    DEFVAL      { 100 }
    ::= { tmnxMdaXConLpbkEntry 5 }

tCoreDdctdPolicerResTable        OBJECT-TYPE
    SYNTAX      SEQUENCE OF TCoreDdctdPolicerResEntry
    MAX-ACCESS  not-accessible
    STATUS      current
    DESCRIPTION
        "tCoreDdctdPolicerResTable contains entries for direct-mapped policer
         resource information on a core"
    ::= { tmnxCardObjs 92 }

tCoreDdctdPolicerResEntry        OBJECT-TYPE
    SYNTAX      TCoreDdctdPolicerResEntry
    MAX-ACCESS  not-accessible
    STATUS      current
    DESCRIPTION
        "Each entry represents core specific direct-mapped policer resource
         information.

         Entries in this table are created and destroyed automatically by the
         system."
    INDEX       {
        tmnxChassisIndex,
        tmnxCardSlotNum,
        tmnxFPNum,
        tmnxCoreNum,
        tCoreDdctdPolicerPartition
    }
    ::= { tCoreDdctdPolicerResTable 1 }

TCoreDdctdPolicerResEntry        ::= SEQUENCE
{
    tCoreDdctdPolicerPartition       INTEGER,
    tCoreDdctdPolicersTotal          Unsigned32,
    tCoreDdctdPolicersAlloc          Unsigned32,
    tCoreDdctdPolicerStatsTotal      Unsigned32,
    tCoreDdctdPolicerStatsAlloc      Unsigned32
}

tCoreDdctdPolicerPartition       OBJECT-TYPE
    SYNTAX      INTEGER {
        per-fc                                     (1),
        per-fc-unicast-multicast-or-multipoint     (2),
        per-fc-unicast-broadcast-unknown-multicast (3),
        per-2-fc-unicast-multicast-or-multipoint   (4),
        per-4-fc-unicast-multicast-or-multipoint   (5),
        per-2-fc                                   (6),
        per-4-fc                                   (7)
    }
    MAX-ACCESS  not-accessible
    STATUS      current
    DESCRIPTION
        "The value of tCoreDdctdPolicerPartition identifies the policer pool.
         - per-fc
         - per-fc-unicast-multicast-or-multipoint - used for both
           per-fc-unicast-multicast and per-fc-unicast-multipoint
           policer allocations
         - per-fc-unicast-broadcast-unknown-multicast.
         - per-2-fc-unicast-multicast-or-multipoint used for both
           per-2-fc-unicast-multicast and per-2-fc-unicast-multipoint
           policer allocations
         - per-4-fc-unicast-multicast-or-multipoint  used for both
           per-4-fc-unicast-multicast and per-4-fc-unicast-multipoint
           policer allocations
         - per-4-fc"
    ::= { tCoreDdctdPolicerResEntry 1 }

tCoreDdctdPolicersTotal          OBJECT-TYPE
    SYNTAX      Unsigned32
    MAX-ACCESS  read-only
    STATUS      current
    DESCRIPTION
        "The value of tCoreDdctdPolicersTotal represents the total number of
         policers in the partition

         When the value of tCoreResIngFloatPolicerTotal is zero, it indicates
         that this resource type is not supported on this core."
    ::= { tCoreDdctdPolicerResEntry 2 }

tCoreDdctdPolicersAlloc          OBJECT-TYPE
    SYNTAX      Unsigned32
    MAX-ACCESS  read-only
    STATUS      current
    DESCRIPTION
        "The value of tCoreDdctdPolicersAlloc represents the total number of
         policers allocated from the partition."
    ::= { tCoreDdctdPolicerResEntry 3 }

tCoreDdctdPolicerStatsTotal      OBJECT-TYPE
    SYNTAX      Unsigned32
    MAX-ACCESS  read-only
    STATUS      current
    DESCRIPTION
        "The value of tCoreDdctdPolicerStatsTotal represents the total number
         of policer stats in the partition

         When the value of tCoreDdctdPolicerStatsTotal is zero, it indicates
         that this resource type is not supported on this core."
    ::= { tCoreDdctdPolicerResEntry 4 }

tCoreDdctdPolicerStatsAlloc      OBJECT-TYPE
    SYNTAX      Unsigned32
    MAX-ACCESS  read-only
    STATUS      current
    DESCRIPTION
        "The value of tCoreDdctdPolicerStatsAlloc represents the total number
         of policer stats allocated from the partition."
    ::= { tCoreDdctdPolicerResEntry 5 }

tmnxFPtoFPStatTable              OBJECT-TYPE
    SYNTAX      SEQUENCE OF TmnxFPtoFPStatEntry
    MAX-ACCESS  not-accessible
    STATUS      current
    DESCRIPTION
        "tmnxFPtoFPStatTable contains statistics entries for the unicast
         traffic sent from the specified FP to each destination FP."
    ::= { tmnxCardObjs 93 }

tmnxFPtoFPStatEntry              OBJECT-TYPE
    SYNTAX      TmnxFPtoFPStatEntry
    MAX-ACCESS  not-accessible
    STATUS      current
    DESCRIPTION
        "Each entry represents the packet and octet statistics for the unicast
         traffic sent from the specified FP to each destination FP.

         Entries in this table are created and destroyed automatically by the
         system."
    INDEX       {
        tmnxSrcChassisIndex,
        tmnxSrcCardSlotNum,
        tmnxSrcFPNum,
        tmnxSrcTap,
        tmnxDstChassisIndex,
        tmnxDstCardSlotNum,
        tmnxDstFPNum,
        tmnxDstTap
    }
    ::= { tmnxFPtoFPStatTable 1 }

TmnxFPtoFPStatEntry              ::= SEQUENCE
{
    tmnxSrcChassisIndex              TmnxChassisIndex,
    tmnxSrcCardSlotNum               TmnxSlotNum,
    tmnxSrcFPNum                     TmnxFPNumber,
    tmnxSrcTap                       Integer32,
    tmnxDstChassisIndex              TmnxChassisIndex,
    tmnxDstCardSlotNum               TmnxSlotNum,
    tmnxDstFPNum                     TmnxFPNumber,
    tmnxDstTap                       Integer32,
    tmnxBestEffortFptoFpPkts         Counter64,
    tmnxBestEffortFptoFpOcts         Counter64,
    tmnxExpeditedFptoFpPkts          Counter64,
    tmnxExpeditedFptoFpOcts          Counter64
}

tmnxSrcChassisIndex              OBJECT-TYPE
    SYNTAX      TmnxChassisIndex
    MAX-ACCESS  not-accessible
    STATUS      current
    DESCRIPTION
        "The value of tmnxSrcChassisIndex specifies source FP chassis index.
         The value of this object cannot be changed. The only supported value
         is '1'.

         Different values of TmnxPhysChassisIndex are used to identify
         different physical chassis (e.g. in an XRS-40 system) in
         tmnxPhysChassisTable."
    ::= { tmnxFPtoFPStatEntry 1 }

tmnxSrcCardSlotNum               OBJECT-TYPE
    SYNTAX      TmnxSlotNum
    MAX-ACCESS  not-accessible
    STATUS      current
    DESCRIPTION
        "The value of tmnxSrcCardSlotNum identifies the source IOM slot within
         a chassis in the system."
    ::= { tmnxFPtoFPStatEntry 2 }

tmnxSrcFPNum                     OBJECT-TYPE
    SYNTAX      TmnxFPNumber
    MAX-ACCESS  not-accessible
    STATUS      current
    DESCRIPTION
        "The value of tmnxSrcFPNum identifies the source Forwarding Plane."
    ::= { tmnxFPtoFPStatEntry 3 }

tmnxSrcTap                       OBJECT-TYPE
    SYNTAX      Integer32 (1..128)
    MAX-ACCESS  not-accessible
    STATUS      current
    DESCRIPTION
        "The tmnxSrcTap is the source one based tap offset of a FP in an Nokia
         SROS series chassis."
    ::= { tmnxFPtoFPStatEntry 4 }

tmnxDstChassisIndex              OBJECT-TYPE
    SYNTAX      TmnxChassisIndex
    MAX-ACCESS  not-accessible
    STATUS      current
    DESCRIPTION
        "The value of tmnxDstChassisIndex specifies destination FP chassis
         index. The value of this object cannot be changed. The only supported
         value is '1'.

         Different values of TmnxPhysChassisIndex are used to identify
         different physical chassis (e.g. in an XRS-40 system) in
         tmnxPhysChassisTable."
    ::= { tmnxFPtoFPStatEntry 5 }

tmnxDstCardSlotNum               OBJECT-TYPE
    SYNTAX      TmnxSlotNum
    MAX-ACCESS  not-accessible
    STATUS      current
    DESCRIPTION
        "The value of tmnxDstCardSlotNum identifies the destination IOM slot
         within a chassis in the system."
    ::= { tmnxFPtoFPStatEntry 6 }

tmnxDstFPNum                     OBJECT-TYPE
    SYNTAX      TmnxFPNumber
    MAX-ACCESS  not-accessible
    STATUS      current
    DESCRIPTION
        "The value of tmnxDstFPNum identifies the destination Forwarding Plane."
    ::= { tmnxFPtoFPStatEntry 7 }

tmnxDstTap                       OBJECT-TYPE
    SYNTAX      Integer32 (1..128)
    MAX-ACCESS  not-accessible
    STATUS      current
    DESCRIPTION
        "The tmnxDstTap is the destination one based tap offset of a FP in an
         Nokia SROS series chassis."
    ::= { tmnxFPtoFPStatEntry 8 }

tmnxBestEffortFptoFpPkts         OBJECT-TYPE
    SYNTAX      Counter64
    MAX-ACCESS  read-only
    STATUS      current
    DESCRIPTION
        "The value of tmnxBestEffortFptoFpPkts indicates the total number of
         best effort packets forwarded by the specified forwarding engine  to
         destination forwarding engine."
    ::= { tmnxFPtoFPStatEntry 9 }

tmnxBestEffortFptoFpOcts         OBJECT-TYPE
    SYNTAX      Counter64
    MAX-ACCESS  read-only
    STATUS      current
    DESCRIPTION
        "The value of tmnxBestEffortFptoFpOcts indicates the total number of
         best effort octets forwarded by the specified forwarding engine  to
         destination forwarding engine."
    ::= { tmnxFPtoFPStatEntry 10 }

tmnxExpeditedFptoFpPkts          OBJECT-TYPE
    SYNTAX      Counter64
    MAX-ACCESS  read-only
    STATUS      current
    DESCRIPTION
        "The value of tmnxExpeditedFptoFpPkts indicates the total number of
         expedited packets forwarded by the specified forwarding engine  to
         destination forwarding engine."
    ::= { tmnxFPtoFPStatEntry 11 }

tmnxExpeditedFptoFpOcts          OBJECT-TYPE
    SYNTAX      Counter64
    MAX-ACCESS  read-only
    STATUS      current
    DESCRIPTION
        "The value of tmnxExpeditedFptoFpOcts indicates the total number of
         expedited octets forwarded by the specified forwarding engine  to
         destination forwarding engine."
    ::= { tmnxFPtoFPStatEntry 12 }

tmnxEsaCellTopoTable             OBJECT-TYPE
    SYNTAX      SEQUENCE OF TmnxEsaCellTopoEntry
    MAX-ACCESS  not-accessible
    STATUS      current
    DESCRIPTION
        "The tmnxEsaCellTopoTable contains information for Extended Services
         Appliance (ESA) NUMA cell topology."
    ::= { tmnxCardObjs 94 }

tmnxEsaCellTopoEntry             OBJECT-TYPE
    SYNTAX      TmnxEsaCellTopoEntry
    MAX-ACCESS  not-accessible
    STATUS      current
    DESCRIPTION
        "Each tmnxEsaCellTopoEntry represents an ESA in the system and contains
         its NUMA cell information.

         Entries in this table are created and destroyed automatically by the
         system."
    INDEX       {
        tmnxEsaId,
        tmnxEsaCellId
    }
    ::= { tmnxEsaCellTopoTable 1 }

TmnxEsaCellTopoEntry             ::= SEQUENCE
{
    tmnxEsaCellId                    Unsigned32,
    tmnxEsaCellTopoSocket            Unsigned32,
    tmnxEsaCellTopoCoresAvailable    Unsigned32,
    tmnxEsaCellTopoCoresAllocated    Unsigned32,
    tmnxEsaCellTopoMemoryAvailable   Unsigned32,
    tmnxEsaCellTopoMemoryAllocated   Unsigned32
}

tmnxEsaCellId                    OBJECT-TYPE
    SYNTAX      Unsigned32 (0..7)
    MAX-ACCESS  not-accessible
    STATUS      current
    DESCRIPTION
        "The value of tmnxEsaCellId indicates the ESA cell Id of this entry."
    ::= { tmnxEsaCellTopoEntry 1 }

tmnxEsaCellTopoSocket            OBJECT-TYPE
    SYNTAX      Unsigned32
    MAX-ACCESS  read-only
    STATUS      current
    DESCRIPTION
        "The value of tmnxEsaCellTopoSocket indicates the socket number that
         the ESA NUMA cell resides on."
    ::= { tmnxEsaCellTopoEntry 2 }

tmnxEsaCellTopoCoresAvailable    OBJECT-TYPE
    SYNTAX      Unsigned32
    MAX-ACCESS  read-only
    STATUS      current
    DESCRIPTION
        "The value of tmnxEsaCellTopoCoresAvailable indicates the number of
         cores available on the ESA NUMA cell."
    ::= { tmnxEsaCellTopoEntry 3 }

tmnxEsaCellTopoCoresAllocated    OBJECT-TYPE
    SYNTAX      Unsigned32
    MAX-ACCESS  read-only
    STATUS      current
    DESCRIPTION
        "The value of tmnxEsaCellTopoCoresAllocated indicates the number of
         cores allocated on the ESA NUMA cell."
    ::= { tmnxEsaCellTopoEntry 4 }

tmnxEsaCellTopoMemoryAvailable   OBJECT-TYPE
    SYNTAX      Unsigned32
    UNITS       "gigabyte"
    MAX-ACCESS  read-only
    STATUS      current
    DESCRIPTION
        "The value of tmnxEsaCellTopoMemoryAvailable indicates the amount of
         memory (in GigaBytes) available on the ESA NUMA cell."
    ::= { tmnxEsaCellTopoEntry 5 }

tmnxEsaCellTopoMemoryAllocated   OBJECT-TYPE
    SYNTAX      Unsigned32
    UNITS       "gigabyte"
    MAX-ACCESS  read-only
    STATUS      current
    DESCRIPTION
        "The value of tmnxEsaCellTopoMemoryAllocated indicates the amount of
         memory (in GigaBytes) allocated on the ESA NUMA cell."
    ::= { tmnxEsaCellTopoEntry 6 }

tmnxEsaHostPortStatsTable        OBJECT-TYPE
    SYNTAX      SEQUENCE OF TmnxEsaHostPortStatsEntry
    MAX-ACCESS  not-accessible
    STATUS      current
    DESCRIPTION
        "The tmnxEsaHostPortStatsTable contains information for Extended
         Services Appliance (ESA) host-port socket and and NIC information."
    ::= { tmnxCardObjs 95 }

tmnxEsaHostPortStatsEntry        OBJECT-TYPE
    SYNTAX      TmnxEsaHostPortStatsEntry
    MAX-ACCESS  not-accessible
    STATUS      current
    DESCRIPTION
        "Each tmnxEsaHostPortStatsEntry represents an ESA host port in the
         system containing its socket and NIC information.

         Entries in this table are created and destroyed automatically by the
         system."
    INDEX       {
        tmnxEsaId,
        tmnxEsaHostPortId
    }
    ::= { tmnxEsaHostPortStatsTable 1 }

TmnxEsaHostPortStatsEntry        ::= SEQUENCE
{
    tmnxEsaHostPortSocketId          Unsigned32,
    tmnxEsaHostPortNicIfName         DisplayString,
    tmnxEsaHostPortNicXceiverType    INTEGER,
    tmnxEsaHostPortNicXceiverMN      TNamedItemOrEmpty,
    tmnxEsaHostPortNicXceiverLWL     Unsigned32,
    tmnxEsaHostPortNicSFPNumLanes    Unsigned32,
    tmnxEsaHostPortNictSFPConCode    INTEGER,
    tmnxEsaHostPortNicSFPVendorOUI   Unsigned32,
    tmnxEsaHostPortNicSFPVendorMfg   DateAndTime,
    tmnxEsaHostPortNicSFPMedia       INTEGER,
    tmnxEsaHostPortNicSFPVendorSN    TNamedItemOrEmpty,
    tmnxEsaHostPortNicSFPVendorPN    TNamedItemOrEmpty,
    tmnxEsaHostPortNicOptCompliance  OCTET STRING,
    tmnxEsaHostPortNicOptCCExtension TmnxPortOptComplianceExtType,
    tmnxEsaHostPortNicLinkLenInfo    OCTET STRING,
    tmnxEsaHostPortNicDDMTemp        Integer32,
    tmnxEsaHostPortNicDDMTempLowWarn Integer32,
    tmnxEsaHostPortNicDDMTempLwAlarm Integer32,
    tmnxEsaHostPortNicDDMTempHiWarn  Integer32,
    tmnxEsaHostPortNicDDMTempHiAlarm Integer32,
    tmnxEsaHostPortNicDDMSupVoltage  Integer32,
    tmnxEsaHostPortNicDDMSVLowWarn   Integer32,
    tmnxEsaHostPortNicDDMSVLowAlarm  Integer32,
    tmnxEsaHostPortNicDDMSVHiWarn    Integer32,
    tmnxEsaHostPortNicDDMSVHiAlarm   Integer32,
    tmnxEsaHostPortNicDDMTxBCLwWarn  Integer32,
    tmnxEsaHostPortNicDDMTxBCLwAlarm Integer32,
    tmnxEsaHostPortNicDDMTxBCHiWarn  Integer32,
    tmnxEsaHostPortNicDDMTxBCHiAlarm Integer32,
    tmnxEsaHostPortNicDDMTxOPLwWarn  Integer32,
    tmnxEsaHostPortNicDDMTxOPLwAlarm Integer32,
    tmnxEsaHostPortNicDDMTxOPHiWarn  Integer32,
    tmnxEsaHostPortNicDDMTxOPHiAlarm Integer32,
    tmnxEsaHostPortNicDDMRxOpPLwWarn Integer32,
    tmnxEsaHostPortNicDDMRxOpPLwAlrm Integer32,
    tmnxEsaHostPortNicDDMRxOpPHiWarn Integer32,
    tmnxEsaHostPortNicDDMRxOpPHiAlrm Integer32,
    tmnxEsaHostPortOperStatus        INTEGER,
    tmnxEsaHostPortFwdStatus         TruthValue,
    tmnxEsaHostPortRxTotalPkts       Counter64,
    tmnxEsaHostPortTxTotalPkts       Counter64,
    tmnxEsaHostPortRxDiscards        Counter64,
    tmnxEsaHostPortRxCrcErrors       Counter64,
    tmnxEsaHostPortRxSymErrors       Counter64
}

tmnxEsaHostPortSocketId          OBJECT-TYPE
    SYNTAX      Unsigned32
    MAX-ACCESS  read-only
    STATUS      current
    DESCRIPTION
        "The value of tmnxEsaHostPortSocketId indicates the socket number that
         the ESA host port resides on."
    ::= { tmnxEsaHostPortStatsEntry 1 }

tmnxEsaHostPortNicIfName         OBJECT-TYPE
    SYNTAX      DisplayString
    MAX-ACCESS  read-only
    STATUS      current
    DESCRIPTION
        "The value of tmnxEsaHostPortNicIfName indicates the nic interface name
         that the ESA host port is connected to."
    ::= { tmnxEsaHostPortStatsEntry 2 }

tmnxEsaHostPortNicXceiverType    OBJECT-TYPE
    SYNTAX      INTEGER {
        unknown                              (0),
        gbic                                 (1),
        moduleConnectorSolderedToMotherboard (2),
        sfpTransceiver                       (3),
        xbiTransceiver                       (4),
        xenpakTransceiver                    (5),
        xfpTransceiver                       (6),
        xffTransceiver                       (7),
        xfpeTransceiver                      (8),
        xpakTransceiver                      (9),
        x2Transceiver                        (10),
        dwdmSfpTransceiver                   (11),
        qsfpTransceiver                      (12),
        qsfpPlusTransceiver                  (13),
        cfpTransceiver                       (14),
        cxpTransceiver                       (15),
        oifMsa100gLh                         (16),
        cfp2OrQsfp28Transceiver              (17),
        cfp4Transceiver                      (18),
        cdfpTransceiver                      (19),
        cfp2AcoTransceiver                   (20),
        cfp8Transceiver                      (21),
        cdfp3Transceiver                     (22),
        microQsfpTransceiver                 (23),
        qsfpDdTransceiver                    (24),
        cfp2DcoTransceiver                   (25),
        sfpDdTransceiver                     (26),
        dsfpTransceiver                      (27),
        x4MiniLinkTransceiver                (28),
        x8MiniLinkTransceiver                (29),
        qsfpPlusOrLaterWithCmisTransceiver   (30),
        sfpDdWithCmisTransceiver             (31),
        sfpPlusOrLaterWithCmisTransceiver    (32)
    }
    MAX-ACCESS  read-only
    STATUS      current
    DESCRIPTION
        "Type of the transceiver."
    ::= { tmnxEsaHostPortStatsEntry 3 }

tmnxEsaHostPortNicXceiverMN      OBJECT-TYPE
    SYNTAX      TNamedItemOrEmpty
    MAX-ACCESS  read-only
    STATUS      current
    DESCRIPTION
        "The value of tmnxEsaHostPortNicXceiverMN indicates the model
         information for the transceiver, as read from the transceiver EEPROM.

         The string is expected to contain printable ASCII characters, but
         unprintable ASCII characters read from the EEPROM are not filtered
         out."
    ::= { tmnxEsaHostPortStatsEntry 4 }

tmnxEsaHostPortNicXceiverLWL     OBJECT-TYPE
    SYNTAX      Unsigned32
    MAX-ACCESS  read-only
    STATUS      current
    DESCRIPTION
        "The light wavelength transmitted by the transceiver's laser. A value
         of zero indicates that the port is not equipped with the transceiver.

         A value in the range of 1 to 2000 indicates that the units are in
         nanometers (nm). A value in the range of 850000 to 2000000 indicates
         that the units are in picometers (pm)."
    ::= { tmnxEsaHostPortStatsEntry 5 }

tmnxEsaHostPortNicSFPNumLanes    OBJECT-TYPE
    SYNTAX      Unsigned32
    MAX-ACCESS  read-only
    STATUS      current
    DESCRIPTION
        "The value of tmnxEsaHostPortNicSFPNumLanes indicates the total number
         of lanes supported by the CSFP/QSFP."
    ::= { tmnxEsaHostPortStatsEntry 6 }

tmnxEsaHostPortNictSFPConCode    OBJECT-TYPE
    SYNTAX      INTEGER {
        unknown                             (0),
        sc                                  (1),
        fiberChannel-Style1-CopperConnector (2),
        fiberChannel-Style2-CopperConnector (3),
        bncortnc                            (4),
        fiberChannelCoaxialHeaders          (5),
        fiberJack                           (6),
        lc                                  (7),
        mt-rj                               (8),
        mu                                  (9),
        sg                                  (10),
        opticalPigtail                      (11),
        mpo1x12                             (12),
        mpo2x16                             (13),
        hssdcII                             (32),
        copperPigtail                       (33),
        rj45                                (34),
        noSepConn                           (35),
        mxc2x16                             (36),
        cs                                  (37),
        snOptConn                           (38),
        mpo2x12                             (39),
        mpo1x16                             (40),
        opticalTransceiver                  (51),
        copperGigE                          (128),
        rjp5                                (129)
    }
    MAX-ACCESS  read-only
    STATUS      current
    DESCRIPTION
        "The external connector provided on the interface."
    ::= { tmnxEsaHostPortStatsEntry 7 }

tmnxEsaHostPortNicSFPVendorOUI   OBJECT-TYPE
    SYNTAX      Unsigned32
    MAX-ACCESS  read-only
    STATUS      current
    DESCRIPTION
        "The vendor organizationally unique identifier field (OUI) contains the
         IEEE company identifier for the vendor. A value of all zero indicates
         that the vendor OUI is unspecified."
    ::= { tmnxEsaHostPortStatsEntry 8 }

tmnxEsaHostPortNicSFPVendorMfg   OBJECT-TYPE
    SYNTAX      DateAndTime
    MAX-ACCESS  read-only
    STATUS      current
    DESCRIPTION
        "The vendor's date code."
    ::= { tmnxEsaHostPortStatsEntry 9 }

tmnxEsaHostPortNicSFPMedia       OBJECT-TYPE
    SYNTAX      INTEGER {
        notApplicable (0),
        ethernet      (1),
        sonetsdh      (2)
    }
    MAX-ACCESS  read-only
    STATUS      current
    DESCRIPTION
        "The value of tmnxEsaHostPortNicSFPMedia indicates the media supported
         for the SFF (Small Form Factor)."
    ::= { tmnxEsaHostPortStatsEntry 10 }

tmnxEsaHostPortNicSFPVendorSN    OBJECT-TYPE
    SYNTAX      TNamedItemOrEmpty
    MAX-ACCESS  read-only
    STATUS      current
    DESCRIPTION
        "The value of tmnxEsaHostPortNicSFPVendorSN indicates the transceiver's
         vendor serial number in ASCII characters, as read from the transceiver
         EEPROM.

         An empty string indicates the vendor serial number is unspecified.

         The string is expected to contain printable ASCII characters, but
         unprintable ASCII characters read from the EEPROM are not filtered
         out."
    ::= { tmnxEsaHostPortStatsEntry 11 }

tmnxEsaHostPortNicSFPVendorPN    OBJECT-TYPE
    SYNTAX      TNamedItemOrEmpty
    MAX-ACCESS  read-only
    STATUS      current
    DESCRIPTION
        "The value of tmnxEsaHostPortNicSFPVendorPN indicates the transceiver's
         vendor part number (or product name) in ASCII characters, as read from
         the transceiver EEPROM.

         An empty string indicates the vendor part number is unspecified.

         The string is expected to contain printable ASCII characters, but
         unprintable ASCII characters read from the EEPROM are not filtered
         out."
    ::= { tmnxEsaHostPortStatsEntry 12 }

tmnxEsaHostPortNicOptCompliance  OBJECT-TYPE
    SYNTAX      OCTET STRING (SIZE (64))
    MAX-ACCESS  read-only
    STATUS      current
    DESCRIPTION
        "The value of tmnxEsaHostPortNicOptCompliance indicates the 64 bytes of
         optical compliance bits stored in SFF EEPROMs."
    REFERENCE
        "CFP MSA Management Interface Specification V2.6 R06a, March 24 2017
         Section 5, CFP NVR 1 Table: Base ID Registers, Table 23 CFP NVR 1.

         SFF Committee document SFF-8024, February 14 2019
         Revision 4.6 Section 4.4.

         SFF Committee document SFF-8472, July 29 2018
         Revision 12.3 Section 5.4 Table 5-3 Transceiver Compliance Codes.

         SFF Committee document SFF-8436, August 31 2018
         Revision 4.9 Section 7.6.2.4 Table 33 Specification Compliance.

         SFF Committee document SFF-8636, February 14 2019
         Revision 2.10a Section 6.3.4 Table 6-16 Specification Compliance Codes.

         SFP-DD MIS document, Revision 2.0, September 25, 2020
         Section 7.2.1 Table 7-2 Identifier and Status Summary.

         QSFP-DD CMIS document, Revision 5.0, May 8 2021."
    ::= { tmnxEsaHostPortStatsEntry 13 }

tmnxEsaHostPortNicOptCCExtension OBJECT-TYPE
    SYNTAX      TmnxPortOptComplianceExtType
    MAX-ACCESS  read-only
    STATUS      current
    DESCRIPTION
        "The value of tmnxEsaHostPortNicOptCCExtension indicates the optical
         compliance extension stored in SFF EEPROMs.

         tmnxEsaHostPortNicOptCCExtension extends the
         tmnxEsaHostPortNicOptCompliance field of the SFF."
    ::= { tmnxEsaHostPortStatsEntry 14 }

tmnxEsaHostPortNicLinkLenInfo    OBJECT-TYPE
    SYNTAX      OCTET STRING (SIZE (6))
    MAX-ACCESS  read-only
    STATUS      current
    DESCRIPTION
        "The value of tmnxEsaHostPortNicLinkLenInfo indicates the link length
         info stored in SFF EEPROMs.


         See SFF Committee documents for details on the representation of the
         values in each byte. For SFP EEPROMs, the 6 bytes are bytes 14 to 19
         of the A0 bank inclusive, described in SFF Committee document
         SFF-8472. For XFP EEPROMs, the first 5 bytes are bytes 142 to 146 of
         the 01 bank inclusive, described in SFF Committee document INF-8077i.
         For XFP EEPROMs, byte 6 will have a value of '0'."
    REFERENCE
        "SFF Committee, SFF-8472 Specification for Diagnostic Monitoring
         Interface for Optical Transceivers, Rev 11.0, September 14, 2010

         SFF Committee, INF-8077i 10 Gigabit Small Form Factor Pluggable
         Module, Rev 4.5, August 31, 2005"
    ::= { tmnxEsaHostPortStatsEntry 15 }

tmnxEsaHostPortNicDDMTemp        OBJECT-TYPE
    SYNTAX      Integer32
    MAX-ACCESS  read-only
    STATUS      current
    DESCRIPTION
        "The value of tmnxEsaHostPortNicDDMTemp indicates the current
         temperature of the SFF in 1/256th degrees Celsius.

         The formula for translating between the value of tmnxEsaHostPortNicDDMTemp and
         degrees Celsius is:
            Internally Calibrated only:
                tmnxEsaHostPortNicDDMTemp / 256

         For example (internally calibrated SFF): The SNMP value 5734 is 22.4
         degrees Celsius."
    REFERENCE
        "SFF Committee, SFF-8472 Specification for Diagnostic Monitoring
         Interface for Optical Transceivers, Rev 11.3, June 11, 2013"
    ::= { tmnxEsaHostPortStatsEntry 16 }

tmnxEsaHostPortNicDDMTempLowWarn OBJECT-TYPE
    SYNTAX      Integer32
    MAX-ACCESS  read-only
    STATUS      current
    DESCRIPTION
        "The value of tmnxEsaHostPortNicDDMTempLowWarn indicates the
         temperature of the SFF that triggers a low-warning.

         See description of tmnxEsaHostPortNicDDMTemp for translating to
         degrees Celsius."
    ::= { tmnxEsaHostPortStatsEntry 17 }

tmnxEsaHostPortNicDDMTempLwAlarm OBJECT-TYPE
    SYNTAX      Integer32
    MAX-ACCESS  read-only
    STATUS      current
    DESCRIPTION
        "The value of tmnxEsaHostPortNicDDMTempLwAlarm indicates the
         temperature of the SFF that triggers a low-alarm.

         See description of tmnxEsaHostPortNicDDMTemp for translating to
         degrees Celsius."
    ::= { tmnxEsaHostPortStatsEntry 18 }

tmnxEsaHostPortNicDDMTempHiWarn  OBJECT-TYPE
    SYNTAX      Integer32
    MAX-ACCESS  read-only
    STATUS      current
    DESCRIPTION
        "The value of tmnxEsaHostPortNicDDMTempHiWarn indicates the temperature
         of the SFF that triggers a hi-warning.

         See description of tmnxEsaHostPortNicDDMTemp for translating to
         degrees Celsius."
    ::= { tmnxEsaHostPortStatsEntry 19 }

tmnxEsaHostPortNicDDMTempHiAlarm OBJECT-TYPE
    SYNTAX      Integer32
    MAX-ACCESS  read-only
    STATUS      current
    DESCRIPTION
        "The value of tmnxEsaHostPortNicDDMTempHiAlarm indicates the
         temperature of the SFF that triggers a hi-alarm.

         See description of tmnxEsaHostPortNicDDMTemp for translating to
         degrees Celsius."
    ::= { tmnxEsaHostPortStatsEntry 20 }

tmnxEsaHostPortNicDDMSupVoltage  OBJECT-TYPE
    SYNTAX      Integer32
    MAX-ACCESS  read-only
    STATUS      current
    DESCRIPTION
        "The value of tmnxEsaHostPortNicDDMSupVoltage indicates the current
         supply voltage of the SFF. For 100G MSA Transponder, the supply
         voltage is in millivolts (mV). For all other types the voltage is in
         deci-millivolts (1/10th of a millivolt or 100 microvolt units).

         The formula for translating between the value of tmnxEsaHostPortNicDDMSupVoltage
         and Voltage is:
            Internally Calibrated only:
                tmnxEsaHostPortNicDDMSupVoltage * conversion_factor

         For example (internally calibrated SFF): 1. For 100G MSA transponders,
         the SNMP value 32851 is 32.851 Volts (V). 2. For all others, the SNMP
         value 32851 is 3.2851 Volts (V)."
    REFERENCE
        "SFF Committee, SFF-8472 Specification for Diagnostic Monitoring
         Interface for Optical Transceivers, Rev 11.3, June 11, 2013"
    ::= { tmnxEsaHostPortStatsEntry 21 }

tmnxEsaHostPortNicDDMSVLowWarn   OBJECT-TYPE
    SYNTAX      Integer32
    MAX-ACCESS  read-only
    STATUS      current
    DESCRIPTION
        "The value of tmnxEsaHostPortNicDDMSVLowWarn indicates the supply
         voltage of the SFF that trigger a low-warning.

         See description of tmnxEsaHostPortNicDDMSupVoltage for translating to
         Volts (V)."
    ::= { tmnxEsaHostPortStatsEntry 22 }

tmnxEsaHostPortNicDDMSVLowAlarm  OBJECT-TYPE
    SYNTAX      Integer32
    MAX-ACCESS  read-only
    STATUS      current
    DESCRIPTION
        "The value of tmnxEsaHostPortNicDDMSVLowAlarm indicates the supply
         voltage of the SFF that triggers a low-alarm.

         See description of tmnxEsaHostPortNicDDMSupVoltage for translating to
         Volts (V)."
    ::= { tmnxEsaHostPortStatsEntry 23 }

tmnxEsaHostPortNicDDMSVHiWarn    OBJECT-TYPE
    SYNTAX      Integer32
    MAX-ACCESS  read-only
    STATUS      current
    DESCRIPTION
        "The value of tmnxEsaHostPortNicDDMSVHiWarn indicates the supply
         voltage of the SFF that triggers a hi-warning.

         See description of tmnxDDMSupplyVoltage for translating to Volts (V)."
    ::= { tmnxEsaHostPortStatsEntry 24 }

tmnxEsaHostPortNicDDMSVHiAlarm   OBJECT-TYPE
    SYNTAX      Integer32
    MAX-ACCESS  read-only
    STATUS      current
    DESCRIPTION
        "The value of tmnxEsaHostPortNicDDMSVHiAlarm indicates the supply
         voltage of the SFF that triggers a hi-alarm.

         See description of tmnxEsaHostPortNicDDMSupVoltage for translating to
         Volts (V)."
    ::= { tmnxEsaHostPortStatsEntry 25 }

tmnxEsaHostPortNicDDMTxBCLwWarn  OBJECT-TYPE
    SYNTAX      Integer32
    MAX-ACCESS  read-only
    STATUS      current
    DESCRIPTION
        "The value of tmnxEsaHostPortNicDDMTxBCLwWarn indicates the Transmit
         Bias Current of the SFF that triggers a low-warning.

         See description of tmnxEsaHostPortNicDDMTxBiasCurr for translating to
         milliamperes (mA)."
    ::= { tmnxEsaHostPortStatsEntry 26 }

tmnxEsaHostPortNicDDMTxBCLwAlarm OBJECT-TYPE
    SYNTAX      Integer32
    MAX-ACCESS  read-only
    STATUS      current
    DESCRIPTION
        "The value of tmnxEsaHostPortNicDDMTxBCLwAlarm indicates the Transmit
         Bias Current of the SFF that triggers a low-alarm.

         See description of tmnxEsaHostPortNicDDMTxBiasCurr for translating to
         milliamperes (mA)."
    ::= { tmnxEsaHostPortStatsEntry 27 }

tmnxEsaHostPortNicDDMTxBCHiWarn  OBJECT-TYPE
    SYNTAX      Integer32
    MAX-ACCESS  read-only
    STATUS      current
    DESCRIPTION
        "The value of tmnxEsaHostPortNicDDMTxBCHiWarn indicates the Transmit
         Bias Current of the SFF that triggers a hi-warning.

         See description of tmnxEsaHostPortNicDDMTxBiasCurr for translating to
         milliamperes (mA)."
    ::= { tmnxEsaHostPortStatsEntry 28 }

tmnxEsaHostPortNicDDMTxBCHiAlarm OBJECT-TYPE
    SYNTAX      Integer32
    MAX-ACCESS  read-only
    STATUS      current
    DESCRIPTION
        "The value of tmnxEsaHostPortNicDDMTxBCHiAlarm indicates the Transmit
         Bias Current of the SFF that triggers a hi-alarm.

         See description of tmnxEsaHostPortNicDDMTxBiasCurr for translating to
         milliamperes (mA)."
    ::= { tmnxEsaHostPortStatsEntry 29 }

tmnxEsaHostPortNicDDMTxOPLwWarn  OBJECT-TYPE
    SYNTAX      Integer32
    MAX-ACCESS  read-only
    STATUS      current
    DESCRIPTION
        "The value of tmnxEsaHostPortNicDDMTxOPLwWarn indicates the Output
         Power of the SFF in one tenths of a microwatt (uW) that triggers a
         low-warning."
    ::= { tmnxEsaHostPortStatsEntry 30 }

tmnxEsaHostPortNicDDMTxOPLwAlarm OBJECT-TYPE
    SYNTAX      Integer32
    MAX-ACCESS  read-only
    STATUS      current
    DESCRIPTION
        "The value of tmnxEsaHostPortNicDDMTxOPLwAlarm indicates the Output
         Power of the SFF in one tenths of a microwatt (uW) that triggers a
         low-alarm."
    ::= { tmnxEsaHostPortStatsEntry 31 }

tmnxEsaHostPortNicDDMTxOPHiWarn  OBJECT-TYPE
    SYNTAX      Integer32
    MAX-ACCESS  read-only
    STATUS      current
    DESCRIPTION
        "The value of tmnxEsaHostPortNicDDMTxOPHiWarn indicates the Output
         Power of the SFF in one tenths of a microwatt (uW) that triggers a
         hi-warning."
    ::= { tmnxEsaHostPortStatsEntry 32 }

tmnxEsaHostPortNicDDMTxOPHiAlarm OBJECT-TYPE
    SYNTAX      Integer32
    MAX-ACCESS  read-only
    STATUS      current
    DESCRIPTION
        "The value of tmnxEsaHostPortNicDDMTxOPHiAlarm indicates the Output
         Power of the SFF in one tenths of a microwatt (uW) that triggers a
         hi-alarm."
    ::= { tmnxEsaHostPortStatsEntry 33 }

tmnxEsaHostPortNicDDMRxOpPLwWarn OBJECT-TYPE
    SYNTAX      Integer32
    MAX-ACCESS  read-only
    STATUS      current
    DESCRIPTION
        "The value of tmnxEsaHostPortNicDDMRxOpPLwWarn indicates the Received
         Optical Power of the SFF in one tenths of a microwatt (uW) that
         triggers a low-warning."
    ::= { tmnxEsaHostPortStatsEntry 34 }

tmnxEsaHostPortNicDDMRxOpPLwAlrm OBJECT-TYPE
    SYNTAX      Integer32
    MAX-ACCESS  read-only
    STATUS      current
    DESCRIPTION
        "The value of tmnxEsaHostPortNicDDMRxOpPLwAlrm indicates the Received
         Optical Power of the SFF in one tenths of a microwatt (uW) that
         triggers a low-alarm."
    ::= { tmnxEsaHostPortStatsEntry 35 }

tmnxEsaHostPortNicDDMRxOpPHiWarn OBJECT-TYPE
    SYNTAX      Integer32
    MAX-ACCESS  read-only
    STATUS      current
    DESCRIPTION
        "The value of tmnxEsaHostPortNicDDMRxOpPHiWarn indicates the Received
         Optical Power of the SFF in one tenths of a microwatt (uW) that
         triggers a hi-warning."
    ::= { tmnxEsaHostPortStatsEntry 36 }

tmnxEsaHostPortNicDDMRxOpPHiAlrm OBJECT-TYPE
    SYNTAX      Integer32
    MAX-ACCESS  read-only
    STATUS      current
    DESCRIPTION
        "The value of tmnxEsaHostPortNicDDMRxOpPHiAlrm indicates the Received
         Optical Power of the SFF in one tenths of a microwatt (uW) that
         triggers a hi-alarm."
    ::= { tmnxEsaHostPortStatsEntry 37 }

tmnxEsaHostPortOperStatus        OBJECT-TYPE
    SYNTAX      INTEGER {
        unknown      (1),
        inService    (2),
        outOfService (3)
    }
    MAX-ACCESS  read-only
    STATUS      current
    DESCRIPTION
        "The value of tmnxEsaHostPortOperStatus indicates the operational
         status of the ESA interface connected to this port."
    ::= { tmnxEsaHostPortStatsEntry 38 }

tmnxEsaHostPortFwdStatus         OBJECT-TYPE
    SYNTAX      TruthValue
    MAX-ACCESS  read-only
    STATUS      current
    DESCRIPTION
        "The value of tmnxEsaHostPortFwdStatus indicates the control traffic
         forwarding status of the ESA interface connected to this port."
    ::= { tmnxEsaHostPortStatsEntry 39 }

tmnxEsaHostPortRxTotalPkts       OBJECT-TYPE
    SYNTAX      Counter64
    MAX-ACCESS  read-only
    STATUS      current
    DESCRIPTION
        "The value of tmnxEsaHostPortRxTotalPkts indicates the total packets
         received on the ESA interface connected to this port."
    ::= { tmnxEsaHostPortStatsEntry 40 }

tmnxEsaHostPortTxTotalPkts       OBJECT-TYPE
    SYNTAX      Counter64
    MAX-ACCESS  read-only
    STATUS      current
    DESCRIPTION
        "The value of tmnxEsaHostPortTxTotalPkts indicates the total packets
         transmitted on the ESA interface connected to this port."
    ::= { tmnxEsaHostPortStatsEntry 41 }

tmnxEsaHostPortRxDiscards        OBJECT-TYPE
    SYNTAX      Counter64
    MAX-ACCESS  read-only
    STATUS      current
    DESCRIPTION
        "The value of tmnxEsaHostPortRxDiscards indicates the total received
         packets discarded on the ESA interface connected to this port."
    ::= { tmnxEsaHostPortStatsEntry 42 }

tmnxEsaHostPortRxCrcErrors       OBJECT-TYPE
    SYNTAX      Counter64
    MAX-ACCESS  read-only
    STATUS      current
    DESCRIPTION
        "The value of tmnxEsaHostPortRxCrcErrors indicates the number of crc
         errors on packets received on the ESA interface connected to this
         port."
    ::= { tmnxEsaHostPortStatsEntry 43 }

tmnxEsaHostPortRxSymErrors       OBJECT-TYPE
    SYNTAX      Counter64
    MAX-ACCESS  read-only
    STATUS      current
    DESCRIPTION
        "The value of tmnxEsaHostPortRxSymErrors indicates the number of symbol
         errors on packets received on the ESA interface connected to this
         port."
    ::= { tmnxEsaHostPortStatsEntry 44 }

tmnxFPCoreResUsgStatsTable       OBJECT-TYPE
    SYNTAX      SEQUENCE OF TmnxFPCoreResUsgStatsEntry
    MAX-ACCESS  not-accessible
    STATUS      current
    DESCRIPTION
        "The tmnxFPCoreResUsgStatsTable contains the FP core resource usage
         state information."
    ::= { tmnxCardObjs 96 }

tmnxFPCoreResUsgStatsEntry       OBJECT-TYPE
    SYNTAX      TmnxFPCoreResUsgStatsEntry
    MAX-ACCESS  not-accessible
    STATUS      current
    DESCRIPTION
        "The tmnxFPCoreResUsgStatsEntry consists of the resource usage state
         information for a specific FP core."
    INDEX       {
        tmnxCardSlotNum,
        tmnxFPNum,
        tmnxCoreNum
    }
    ::= { tmnxFPCoreResUsgStatsTable 1 }

TmnxFPCoreResUsgStatsEntry       ::= SEQUENCE
{
    tmnxFPCoreFreeDramBdb            Counter64,
    tmnxFPCoreMinFreeDramBdb         Counter64,
    tmnxFPCoreLowFreeDramBdb         Counter64,
    tmnxFPCoreTotalDramBdb           Counter64,
    tmnxFPCoreFreeSramBuf            Counter64,
    tmnxFPCoreMinFreeSramBuf         Counter64,
    tmnxFPCoreLowFreeSramBuf         Counter64,
    tmnxFPCoreTotalSramBuf           Counter64,
    tmnxFPCoreFreeSramPdb            Counter64,
    tmnxFPCoreMinFreeSramPdb         Counter64,
    tmnxFPCoreLowFreeSramPdb         Counter64,
    tmnxFPCoreTotalSramPdb           Counter64,
    tmnxFPCoreDramBwMaxCnscPollBlk   Counter64,
    tmnxFPCoreDramBwPktRejLastPoll   Counter64,
    tmnxFPCoreDramBwTotalPktRejects  Counter64,
    tmnxFPCorePcsPipeNifPrdDrpLstPol Counter64,
    tmnxFPCorePcsPipeTotNifPrdDrops  Counter64,
    tmnxFPCorePcsPipeMxCnvPlNifPrdDp Counter64,
    tmnxFPCoreMeshFabBwAsrtCngstFP1  Counter64,
    tmnxFPCoreMeshFabBwAsrtCngstFP2  Counter64,
    tmnxFPCoreMeshFabBwAsrtCngstFP3  Counter64,
    tmnxFPCoreL0PolicerProfilesInUse Unsigned32,
    tmnxFPCoreL1PolicerProfilesInUse Unsigned32
}

tmnxFPCoreFreeDramBdb            OBJECT-TYPE
    SYNTAX      Counter64
    MAX-ACCESS  read-only
    STATUS      current
    DESCRIPTION
        "The value of tmnxFPCoreFreeDramBdb indicates the number of free DRAM
         bundle descriptor buffers (BDB) on the core."
    ::= { tmnxFPCoreResUsgStatsEntry 1 }

tmnxFPCoreMinFreeDramBdb         OBJECT-TYPE
    SYNTAX      Counter64
    MAX-ACCESS  read-only
    STATUS      current
    DESCRIPTION
        "The value of tmnxFPCoreMinFreeDramBdb indicates the minimum number of
         free DRAM BDBs on the core since the last read from the device."
    ::= { tmnxFPCoreResUsgStatsEntry 2 }

tmnxFPCoreLowFreeDramBdb         OBJECT-TYPE
    SYNTAX      Counter64
    MAX-ACCESS  read-only
    STATUS      current
    DESCRIPTION
        "The value of tmnxFPCoreLowFreeDramBdb indicates the lowest number of
         free DRAM BDBs on the core since it was last polled."
    ::= { tmnxFPCoreResUsgStatsEntry 3 }

tmnxFPCoreTotalDramBdb           OBJECT-TYPE
    SYNTAX      Counter64
    MAX-ACCESS  read-only
    STATUS      current
    DESCRIPTION
        "The value of tmnxFPCoreTotalDramBdb indicates the total number of DRAM
         BDBs on the core."
    ::= { tmnxFPCoreResUsgStatsEntry 4 }

tmnxFPCoreFreeSramBuf            OBJECT-TYPE
    SYNTAX      Counter64
    MAX-ACCESS  read-only
    STATUS      current
    DESCRIPTION
        "The value of tmnxFPCoreFreeSramBuf indicates the number of free SRAM
         buffers on the core."
    ::= { tmnxFPCoreResUsgStatsEntry 5 }

tmnxFPCoreMinFreeSramBuf         OBJECT-TYPE
    SYNTAX      Counter64
    MAX-ACCESS  read-only
    STATUS      current
    DESCRIPTION
        "The value of tmnxFPCoreMinFreeSramBuf indicates the minimum number of
         free SRAM buffers on the core since the last read from the device."
    ::= { tmnxFPCoreResUsgStatsEntry 6 }

tmnxFPCoreLowFreeSramBuf         OBJECT-TYPE
    SYNTAX      Counter64
    MAX-ACCESS  read-only
    STATUS      current
    DESCRIPTION
        "The value of tmnxFPCoreLowFreeSramBuf indicates the lowest number of
         free SRAM buffers on the core since it was last polled."
    ::= { tmnxFPCoreResUsgStatsEntry 7 }

tmnxFPCoreTotalSramBuf           OBJECT-TYPE
    SYNTAX      Counter64
    MAX-ACCESS  read-only
    STATUS      current
    DESCRIPTION
        "The value of tmnxFPCoreTotalSramBuf indicates the total number of SRAM
         buffers on the core."
    ::= { tmnxFPCoreResUsgStatsEntry 8 }

tmnxFPCoreFreeSramPdb            OBJECT-TYPE
    SYNTAX      Counter64
    MAX-ACCESS  read-only
    STATUS      current
    DESCRIPTION
        "The value of tmnxFPCoreFreeSramPdb indicates the number of free SRAM
         packet descriptor buffers (PDB) on the core."
    ::= { tmnxFPCoreResUsgStatsEntry 9 }

tmnxFPCoreMinFreeSramPdb         OBJECT-TYPE
    SYNTAX      Counter64
    MAX-ACCESS  read-only
    STATUS      current
    DESCRIPTION
        "The value of tmnxFPCoreMinFreeSramPdb indicates the minimum number of
         free SRAM PDBs on the core since the last read from the device."
    ::= { tmnxFPCoreResUsgStatsEntry 10 }

tmnxFPCoreLowFreeSramPdb         OBJECT-TYPE
    SYNTAX      Counter64
    MAX-ACCESS  read-only
    STATUS      current
    DESCRIPTION
        "The value of tmnxFPCoreLowFreeSramPdb indicates the lowest number of
         free SRAM PDBs on the core since it was last polled."
    ::= { tmnxFPCoreResUsgStatsEntry 11 }

tmnxFPCoreTotalSramPdb           OBJECT-TYPE
    SYNTAX      Counter64
    MAX-ACCESS  read-only
    STATUS      current
    DESCRIPTION
        "The value of tmnxFPCoreTotalSramPdb indicates the total number of SRAM
         PDBs on the core."
    ::= { tmnxFPCoreResUsgStatsEntry 12 }

tmnxFPCoreDramBwMaxCnscPollBlk   OBJECT-TYPE
    SYNTAX      Counter64
    MAX-ACCESS  read-only
    STATUS      current
    DESCRIPTION
        "The value of tmnxFPCoreDramBwMaxCnscPollBlk indicates the number of
         DRAM bandwidth max consecutive polls blocked on the core."
    ::= { tmnxFPCoreResUsgStatsEntry 13 }

tmnxFPCoreDramBwPktRejLastPoll   OBJECT-TYPE
    SYNTAX      Counter64
    MAX-ACCESS  read-only
    STATUS      current
    DESCRIPTION
        "The value of tmnxFPCoreDramBwPktRejLastPoll indicates the number of
         DRAM bandwidth packets that were rejected due to resource exhaustion
         since last poll on the core."
    ::= { tmnxFPCoreResUsgStatsEntry 14 }

tmnxFPCoreDramBwTotalPktRejects  OBJECT-TYPE
    SYNTAX      Counter64
    MAX-ACCESS  read-only
    STATUS      current
    DESCRIPTION
        "The value of tmnxFPCoreDramBwTotalPktRejects indicates the cumulative
         total number of DRAM bandwidth packet rejects on the core."
    ::= { tmnxFPCoreResUsgStatsEntry 15 }

tmnxFPCorePcsPipeNifPrdDrpLstPol OBJECT-TYPE
    SYNTAX      Counter64
    MAX-ACCESS  read-only
    STATUS      current
    DESCRIPTION
        "The value of tmnxFPCorePcsPipeNifPrdDrpLstPol indicates the number of
         core processing pipeline NIF PRD drops since the last poll on the
         core."
    ::= { tmnxFPCoreResUsgStatsEntry 16 }

tmnxFPCorePcsPipeTotNifPrdDrops  OBJECT-TYPE
    SYNTAX      Counter64
    MAX-ACCESS  read-only
    STATUS      current
    DESCRIPTION
        "The value of tmnxFPCorePcsPipeTotNifPrdDrops indicates the cumulative
         total number of all core processing pipeline NIF PRD drops on the
         core."
    ::= { tmnxFPCoreResUsgStatsEntry 17 }

tmnxFPCorePcsPipeMxCnvPlNifPrdDp OBJECT-TYPE
    SYNTAX      Counter64
    MAX-ACCESS  read-only
    STATUS      current
    DESCRIPTION
        "The value of tmnxFPCorePcsPipeMxCnvPlNifPrdDp indicates the maximum
         number of core processing pipeline consecutive polls during NIF PRD
         drops on the core."
    ::= { tmnxFPCoreResUsgStatsEntry 18 }

tmnxFPCoreMeshFabBwAsrtCngstFP1  OBJECT-TYPE
    SYNTAX      Counter64
    MAX-ACCESS  read-only
    STATUS      current
    DESCRIPTION
        "The value of tmnxFPCoreMeshFabBwAsrtCngstFP1 indicates the mesh fabric
         bandwidth congestion asserted count between this FP and FP1 on the
         core.

         This object is not applicable when the value of tmnxFPNum is 1, and
         will return 0."
    ::= { tmnxFPCoreResUsgStatsEntry 19 }

tmnxFPCoreMeshFabBwAsrtCngstFP2  OBJECT-TYPE
    SYNTAX      Counter64
    MAX-ACCESS  read-only
    STATUS      current
    DESCRIPTION
        "The value of tmnxFPCoreMeshFabBwAsrtCngstFP2 indicates the mesh fabric
         bandwidth congestion asserted count between this FP and FP2 on the
         core.

         This object is not applicable when the value of tmnxFPNum is 2, and
         will return 0."
    ::= { tmnxFPCoreResUsgStatsEntry 20 }

tmnxFPCoreMeshFabBwAsrtCngstFP3  OBJECT-TYPE
    SYNTAX      Counter64
    MAX-ACCESS  read-only
    STATUS      current
    DESCRIPTION
        "The value of tmnxFPCoreMeshFabBwAsrtCngstFP3 indicates the mesh fabric
         bandwidth congestion asserted count between this FP and FP2 on the
         core.

         This object is not applicable when the value of tmnxFPNum is 3, and
         will return 0."
    ::= { tmnxFPCoreResUsgStatsEntry 21 }

tmnxFPCoreL0PolicerProfilesInUse OBJECT-TYPE
    SYNTAX      Unsigned32
    MAX-ACCESS  read-only
    STATUS      current
    DESCRIPTION
        "The value of tmnxFPCoreL0PolicerProfilesInUse indicates the total
         number of Level-0 policer profiles currently in use."
    ::= { tmnxFPCoreResUsgStatsEntry 22 }

tmnxFPCoreL1PolicerProfilesInUse OBJECT-TYPE
    SYNTAX      Unsigned32
    MAX-ACCESS  read-only
    STATUS      current
    DESCRIPTION
        "The value of tmnxFPCoreL1PolicerProfilesInUse indicates the total
         number of Level-1 policer profiles currently in use."
    ::= { tmnxFPCoreResUsgStatsEntry 23 }

tmnxCpmSecureBootStatsTable      OBJECT-TYPE
    SYNTAX      SEQUENCE OF TmnxCpmSecureBootStatsEntry
    MAX-ACCESS  not-accessible
    STATUS      current
    DESCRIPTION
        "The tmnxCpmSecureBootStatsTable contains information for secure-boot
         status information relevant to CPMs in use by the system."
    ::= { tmnxCardObjs 97 }

tmnxCpmSecureBootStatsEntry      OBJECT-TYPE
    SYNTAX      TmnxCpmSecureBootStatsEntry
    MAX-ACCESS  not-accessible
    STATUS      current
    DESCRIPTION
        "Each tmnxCpmSecureBootStatsEntry represents secure-boot state
         information specific to a CPM card.

         Entries cannot be created or deleted by SNMP SET operations. Where
         supported, entries are created automatically by the system."
    AUGMENTS    { tmnxCpmCardEntry }
    ::= { tmnxCpmSecureBootStatsTable 1 }

TmnxCpmSecureBootStatsEntry      ::= SEQUENCE
{
    tmnxCpmSecureBootEnabled         TmnxEnabledDisabledOrNA,
    tmnxCpmSBUefiVarsStatus          TmnxSBUefiVarsState
}

tmnxCpmSecureBootEnabled         OBJECT-TYPE
    SYNTAX      TmnxEnabledDisabledOrNA
    MAX-ACCESS  read-only
    STATUS      current
    DESCRIPTION
        "The value of tmnxCpmSecureBootEnabled indicates whether the CPM has
         enabled the use of the signed software feature.

         This feature, once enabled, cannot be disabled. If in use, the CPM
         will boot only into signed software images."
    ::= { tmnxCpmSecureBootStatsEntry 1 }

tmnxCpmSBUefiVarsStatus          OBJECT-TYPE
    SYNTAX      TmnxSBUefiVarsState
    MAX-ACCESS  read-only
    STATUS      current
    DESCRIPTION
        "The value of tmnxCpmSBUefiVarsStatus indicates whether or not the UEFI
         variables of the CPM are the latest included with the software image
         in use."
    ::= { tmnxCpmSecureBootStatsEntry 2 }

tmnxFPResOversubStatsTable       OBJECT-TYPE
    SYNTAX      SEQUENCE OF TmnxFPResOversubStatsEntry
    MAX-ACCESS  not-accessible
    STATUS      current
    DESCRIPTION
        "The tmnxFPResOversubStatsTable contains statistics information for
         oversubscription of FP resources."
    ::= { tmnxCardObjs 98 }

tmnxFPResOversubStatsEntry       OBJECT-TYPE
    SYNTAX      TmnxFPResOversubStatsEntry
    MAX-ACCESS  not-accessible
    STATUS      current
    DESCRIPTION
        "Each tmnxFPResOversubStatsEntry represents oversubscription
         information for each FP resource which may be oversubscribed.

         Entries cannot be created or deleted by SNMP SET operations. Where
         supported, entries are created automatically by the system."
    INDEX       {
        tmnxCardSlotNum,
        tmnxFPNum,
        tmnxFPOversubResource
    }
    ::= { tmnxFPResOversubStatsTable 1 }

TmnxFPResOversubStatsEntry       ::= SEQUENCE
{
    tmnxFPOversubResource            INTEGER,
    tmnxFPResOversubDetected         Unsigned32
}

tmnxFPOversubResource            OBJECT-TYPE
    SYNTAX      INTEGER {
        sramBuf             (1),
        sramPdb             (2),
        dramBdb             (3),
        dramBandwidth       (4),
        coreProcessPipeline (5),
        meshFabricBandwidth (6)
    }
    MAX-ACCESS  not-accessible
    STATUS      current
    DESCRIPTION
        "The value of tmnxFPOversubResource specifies the FP resource which may
         be oversubscribed."
    ::= { tmnxFPResOversubStatsEntry 1 }

tmnxFPResOversubDetected         OBJECT-TYPE
    SYNTAX      Unsigned32
    MAX-ACCESS  read-only
    STATUS      current
    DESCRIPTION
        "The value of tmnxFPResOversubDetected indicates the number of seconds
         it has been detected that the FP resource has been oversubscribed."
    ::= { tmnxFPResOversubStatsEntry 2 }

tCardIxrResourceTable            OBJECT-TYPE
    SYNTAX      SEQUENCE OF TCardIxrResourceEntry
    MAX-ACCESS  not-accessible
    STATUS      current
    DESCRIPTION
        "The tCardIxrResourceTable contains information about card resource
         utilization for resources specific to the Nokia IXR systems."
    ::= { tmnxCardObjs 99 }

tCardIxrResourceEntry            OBJECT-TYPE
    SYNTAX      TCardIxrResourceEntry
    MAX-ACCESS  not-accessible
    STATUS      current
    DESCRIPTION
        "Each row in the tCardIxrResourceEntry contains information about
         resource utilization on the card specified by the indices.

         Entries cannot be created or deleted by SNMP SET operations. Where
         supported, entries are created automatically by the system."
    INDEX       {
        tmnxChassisIndex,
        tmnxCardSlotNum
    }
    ::= { tCardIxrResourceTable 1 }

TCardIxrResourceEntry            ::= SEQUENCE
{
    tCardIxrResMplsEcmpGroupsTotal   Unsigned32,
    tCardIxrResMplsEcmpGroupsAlloc   Unsigned32,
    tCardIxrResMplsEcmpGroupsFree    Unsigned32,
    tCardIxrResIpEcmpGroupsTotal     Unsigned32,
    tCardIxrResIpEcmpGroupsAlloc     Unsigned32,
    tCardIxrResIpEcmpGroupsFree      Unsigned32,
    tCardIxrResFecBanksTotal         Unsigned32,
    tCardIxrResFecBanksAlloc         Unsigned32,
    tCardIxrResFecBanksFree          Unsigned32,
    tCardIxrResFecLevel1BanksAlloc   Unsigned32,
    tCardIxrResFecLevel2BanksAlloc   Unsigned32,
    tCardIxrResFecsTotal             Unsigned32,
    tCardIxrResFecsAlloc             Unsigned32,
    tCardIxrResFecsFree              Unsigned32,
    tCardIxrResFecLevel1Total        Unsigned32,
    tCardIxrResFecLevel1Alloc        Unsigned32,
    tCardIxrResFecLevel1Free         Unsigned32,
    tCardIxrResFecLevel2Total        Unsigned32,
    tCardIxrResFecLevel2Alloc        Unsigned32,
    tCardIxrResFecLevel2Free         Unsigned32,
    tCardIxrResGrpFecsTotal          Unsigned32,
    tCardIxrResGrpFecsAlloc          Unsigned32,
    tCardIxrResGrpFecsFree           Unsigned32,
    tCardIxrResGrpFecBanksTotal      Unsigned32,
    tCardIxrResGrpFecBanksAlloc      Unsigned32,
    tCardIxrResGrpFecBanksFree       Unsigned32,
    tCardIxrResGrpFecLvl1BanksAlloc  Unsigned32,
    tCardIxrResGrpFecLvl2BanksAlloc  Unsigned32,
    tCardIxrResGrpFecLevel1Total     Unsigned32,
    tCardIxrResGrpFecLevel1Alloc     Unsigned32,
    tCardIxrResGrpFecLevel1Free      Unsigned32,
    tCardIxrResGrpFecLevel2Total     Unsigned32,
    tCardIxrResGrpFecLevel2Alloc     Unsigned32,
    tCardIxrResGrpFecLevel2Free      Unsigned32,
    tCardIxrResIlmSwapTotal          Unsigned32,
    tCardIxrResIlmSwapAlloc          Unsigned32,
    tCardIxrResIlmSwapFree           Unsigned32,
    tCardIxrResFecLevel3Total        Unsigned32,
    tCardIxrResFecLevel3Alloc        Unsigned32,
    tCardIxrResFecLevel3Free         Unsigned32,
    tCardIxrResGrpFecLvl3BanksAlloc  Unsigned32,
    tCardIxrResGrpFecLevel3Total     Unsigned32,
    tCardIxrResGrpFecLevel3Alloc     Unsigned32,
    tCardIxrResGrpFecLevel3Free      Unsigned32,
    tCardIxrResPpmcBestCaseEstTotal  Unsigned32,
    tCardIxrResPpmcWrstCaseEstTotal  Unsigned32,
    tCardIxrResPpmcSingleLevelAlloc  Unsigned32,
    tCardIxrResPpmcMultiLevelAlloc   Unsigned32,
    tCardIxrResPpmcExhausted         TruthValue
}

tCardIxrResMplsEcmpGroupsTotal   OBJECT-TYPE
    SYNTAX      Unsigned32
    MAX-ACCESS  read-only
    STATUS      obsolete
    DESCRIPTION
        "The value of the object tCardIxrResMplsEcmpGroupsTotal indicates the
         maximum number of MPLS ECMP Group entries that are allowed on this
         card.

         MPLS applications like LDP or Segment Routing requires an entry to
         program (MPLS layer) ECMP when available and ECMP is enabled.

         This object is deprecated in release 23.10"
    ::= { tCardIxrResourceEntry 1 }

tCardIxrResMplsEcmpGroupsAlloc   OBJECT-TYPE
    SYNTAX      Unsigned32
    MAX-ACCESS  read-only
    STATUS      obsolete
    DESCRIPTION
        "The value of the object tCardIxrResMplsEcmpGroupsAlloc indicates the
         number of MPLS ECMP Group entries that are currently in use on this
         card.

         MPLS applications like LDP or Segment Routing requires an entry to
         program (MPLS layer) ECMP when available and ECMP is enabled.

         This object is deprecated in release 23.10"
    ::= { tCardIxrResourceEntry 2 }

tCardIxrResMplsEcmpGroupsFree    OBJECT-TYPE
    SYNTAX      Unsigned32
    MAX-ACCESS  read-only
    STATUS      obsolete
    DESCRIPTION
        "The value of the object tCardIxrResMplsEcmpGroupsFree indicates the
         number of free MPLS ECMP Group entries that are currently available on
         this card.

         MPLS applications like LDP or Segment Routing requires an entry to
         program (MPLS layer) ECMP when available and ECMP is enabled.

         This object is deprecated in release 23.10"
    ::= { tCardIxrResourceEntry 3 }

tCardIxrResIpEcmpGroupsTotal     OBJECT-TYPE
    SYNTAX      Unsigned32
    MAX-ACCESS  read-only
    STATUS      obsolete
    DESCRIPTION
        "The value of the object tCardIxrResIpEcmpGroupsTotal indicates the
         maximum number of IP ECMP Group entries that are allowed on this card.

         IP layer ECMP requires an entry per routing destination when ECMP is
         available and enabled.

         This object is deprecated in release 23.10"
    ::= { tCardIxrResourceEntry 4 }

tCardIxrResIpEcmpGroupsAlloc     OBJECT-TYPE
    SYNTAX      Unsigned32
    MAX-ACCESS  read-only
    STATUS      obsolete
    DESCRIPTION
        "The value of the object tCardIxrResIpEcmpGroupsAlloc indicates the
         number of IP ECMP Group entries that are currently in use on this
         card.

         IP layer ECMP requires an entry per routing destination when ECMP is
         available and enabled.

         This object is deprecated in release 23.10"
    ::= { tCardIxrResourceEntry 5 }

tCardIxrResIpEcmpGroupsFree      OBJECT-TYPE
    SYNTAX      Unsigned32
    MAX-ACCESS  read-only
    STATUS      obsolete
    DESCRIPTION
        "The value of the object tCardIxrResIpEcmpGroupsFree indicates the
         number of free IP ECMP Group entries that are currently available on
         this card.

         IP layer ECMP requires an entry per routing destination when ECMP is
         available and enabled.

         This object is deprecated in release 23.10"
    ::= { tCardIxrResourceEntry 6 }

tCardIxrResFecBanksTotal         OBJECT-TYPE
    SYNTAX      Unsigned32
    MAX-ACCESS  read-only
    STATUS      current
    DESCRIPTION
        "The value of the object tCardIxrResFecBanksTotal indicates the maximum
         number of FEC resources on the bank level that are allowed on this
         card.

         FEC entries are required when programming a wide variety of different
         applications, from LSPs to Filters"
    ::= { tCardIxrResourceEntry 7 }

tCardIxrResFecBanksAlloc         OBJECT-TYPE
    SYNTAX      Unsigned32
    MAX-ACCESS  read-only
    STATUS      current
    DESCRIPTION
        "The value of the object tCardIxrResFecBanksAlloc indicates the number
         of FEC resources on the bank level that are currently in use on this
         card.

         FEC entries are required when programming a wide variety of different
         applications, from LSPs to Filters"
    ::= { tCardIxrResourceEntry 8 }

tCardIxrResFecBanksFree          OBJECT-TYPE
    SYNTAX      Unsigned32
    MAX-ACCESS  read-only
    STATUS      current
    DESCRIPTION
        "The value of the object tCardIxrResFecBanksFree indicates the number
         of free FEC resources on the bank level that are currently available
         on this card.

         FEC entries are required when programming a wide variety of different
         applications, from LSPs to Filters"
    ::= { tCardIxrResourceEntry 9 }

tCardIxrResFecLevel1BanksAlloc   OBJECT-TYPE
    SYNTAX      Unsigned32
    MAX-ACCESS  read-only
    STATUS      current
    DESCRIPTION
        "The value of the object tCardIxrResFecLevel1BanksAlloc indicates the
         number of FEC Level-1 banks that are currently in use by different
         applications on this card.

         Application list includes Filters, IP Multicast, IP routing, ARP/ND,
         IP interfaces and FECs allocated for System use."
    ::= { tCardIxrResourceEntry 10 }

tCardIxrResFecLevel2BanksAlloc   OBJECT-TYPE
    SYNTAX      Unsigned32
    MAX-ACCESS  read-only
    STATUS      current
    DESCRIPTION
        "The value of the object tCardIxrResFecLevel2BanksAlloc indicates the
         number of FEC Level-2 banks that are currently in use by different
         applications on this card.

         Application list includes MPLS LSPs and NHLFEs together with FECs
         allocated for System use."
    ::= { tCardIxrResourceEntry 11 }

tCardIxrResFecsTotal             OBJECT-TYPE
    SYNTAX      Unsigned32
    MAX-ACCESS  read-only
    STATUS      current
    DESCRIPTION
        "The value of the object tCardIxrResFecsTotal indicates the maximum
         number of FEC entries that are allowed on this card.

         FEC entries are required when programming a wide variety of different
         applications, from LSPs to Filters"
    ::= { tCardIxrResourceEntry 12 }

tCardIxrResFecsAlloc             OBJECT-TYPE
    SYNTAX      Unsigned32
    MAX-ACCESS  read-only
    STATUS      current
    DESCRIPTION
        "The value of the object tCardIxrResFecsAlloc indicates the number of
         FEC entries that are currently in use on this card.

         FEC entries are required when programming a wide variety of different
         applications, from LSPs to Filters"
    ::= { tCardIxrResourceEntry 13 }

tCardIxrResFecsFree              OBJECT-TYPE
    SYNTAX      Unsigned32
    MAX-ACCESS  read-only
    STATUS      current
    DESCRIPTION
        "The value of the object tCardIxrResFecsFree indicates the number of
         free FEC entries that are currently available on this card.

         FEC entries are required when programming a wide variety of different
         applications, from LSPs to Filters"
    ::= { tCardIxrResourceEntry 14 }

tCardIxrResFecLevel1Total        OBJECT-TYPE
    SYNTAX      Unsigned32
    MAX-ACCESS  read-only
    STATUS      current
    DESCRIPTION
        "The value of the object tCardIxrResFecLevel1Total indicates the
         maximum number of FEC Level-1 entries that are allowed on this card to
         be used by different applications on this card.

         Application list includes Filters, IP Multicast, IP routing, ARP/ND,
         IP interfaces and FECs allocated for System use."
    ::= { tCardIxrResourceEntry 15 }

tCardIxrResFecLevel1Alloc        OBJECT-TYPE
    SYNTAX      Unsigned32
    MAX-ACCESS  read-only
    STATUS      current
    DESCRIPTION
        "The value of the object tCardIxrResFecLevel1Alloc indicates the number
         of FEC Level-1 entries that are currently in use by different
         applications on this card.

         Application list includes Filters, IP Multicast, IP routing, ARP/ND,
         IP interfaces and FECs allocated for System use."
    ::= { tCardIxrResourceEntry 16 }

tCardIxrResFecLevel1Free         OBJECT-TYPE
    SYNTAX      Unsigned32
    MAX-ACCESS  read-only
    STATUS      current
    DESCRIPTION
        "The value of the object tCardIxrResFecLevel1Free indicates the number
         of free FEC Level-1 entries that are currently available for different
         applications on this card.

         Application list includes Filters, IP Multicast, IP routing, ARP/ND,
         IP interfaces and FECs allocated for System use."
    ::= { tCardIxrResourceEntry 17 }

tCardIxrResFecLevel2Total        OBJECT-TYPE
    SYNTAX      Unsigned32
    MAX-ACCESS  read-only
    STATUS      current
    DESCRIPTION
        "The value of the object tCardIxrResFecLevel2Total indicates the
         maximum number of FEC Level-2 entries that are allowed on this card to
         be used by different applications on this card.

         Application list includes MPLS LSPs and NHLFEs together with FECs
         allocated for System use"
    ::= { tCardIxrResourceEntry 18 }

tCardIxrResFecLevel2Alloc        OBJECT-TYPE
    SYNTAX      Unsigned32
    MAX-ACCESS  read-only
    STATUS      current
    DESCRIPTION
        "The value of the object tCardIxrResFecLevel2Alloc indicates the number
         of FEC Level-2 entries that are currently in use by different
         applications on this card.

         Application list includes MPLS LSPs and NHLFEs together with FECs
         allocated for System use"
    ::= { tCardIxrResourceEntry 19 }

tCardIxrResFecLevel2Free         OBJECT-TYPE
    SYNTAX      Unsigned32
    MAX-ACCESS  read-only
    STATUS      current
    DESCRIPTION
        "The value of the object tCardIxrResFecLevel2Free indicates the number
         of free FEC Level-2 entries that are currently available for different
         applications on this card.

         Application list includes MPLS LSPs and NHLFEs together with FECs
         allocated for System use"
    ::= { tCardIxrResourceEntry 20 }

tCardIxrResGrpFecsTotal          OBJECT-TYPE
    SYNTAX      Unsigned32
    MAX-ACCESS  read-only
    STATUS      current
    DESCRIPTION
        "The value of the object tCardIxrResGrpFecsTotal indicates the maximum
         number of FEC Group entries that are allowed on this card to be used
         by different applications on this card.

         Group FECs are required on per ECMP group, also known as ECMP
         destination basis.

         Level-1 is used by IP ECMP applications while Level-2 FEC may be used
         by labeled or IP ECMP applications."
    ::= { tCardIxrResourceEntry 21 }

tCardIxrResGrpFecsAlloc          OBJECT-TYPE
    SYNTAX      Unsigned32
    MAX-ACCESS  read-only
    STATUS      current
    DESCRIPTION
        "The value of the object tCardIxrResGrpFecsAlloc indicates the number
         of FEC Group entries that are currently in use by different
         application on this card.

         Group FECs are required on per ECMP group, also known as ECMP
         destination basis.

         Level-1 is used by IP ECMP applications while Level-2 FEC may be used
         by labeled or IP ECMP applications."
    ::= { tCardIxrResourceEntry 22 }

tCardIxrResGrpFecsFree           OBJECT-TYPE
    SYNTAX      Unsigned32
    MAX-ACCESS  read-only
    STATUS      current
    DESCRIPTION
        "The value of the object tCardIxrResGrpFecsFree indicates the number of
         free FEC Group entries that are currently available for different
         applications on this card.

         Group FECs are required on per ECMP group, also known as ECMP
         destination basis.

         Level-1 is used by IP ECMP applications while Level-2 FEC may be used
         by labeled or IP ECMP applications."
    ::= { tCardIxrResourceEntry 23 }

tCardIxrResGrpFecBanksTotal      OBJECT-TYPE
    SYNTAX      Unsigned32
    MAX-ACCESS  read-only
    STATUS      current
    DESCRIPTION
        "The value of the object tCardIxrResGrpFecBanksTotal indicates the
         maximum number of FEC Group banks that are allowed on this card to be
         used by different applications on this card.

         Group FECs are required on per ECMP group, also known as ECMP
         destination basis.

         Level-1 is used by IP ECMP applications while Level-2 FEC may be used
         by labeled or IP ECMP applications."
    ::= { tCardIxrResourceEntry 24 }

tCardIxrResGrpFecBanksAlloc      OBJECT-TYPE
    SYNTAX      Unsigned32
    MAX-ACCESS  read-only
    STATUS      current
    DESCRIPTION
        "The value of the object tCardIxrResGrpFecBanksAlloc indicates the
         number of FEC Group banks that are currently in use by different
         applications on this card.

         Group FECs are required on per ECMP group, also known as ECMP
         destination basis.

         Level-1 is used by IP ECMP applications while Level-2 FEC may be used
         by labeled or IP ECMP applications."
    ::= { tCardIxrResourceEntry 25 }

tCardIxrResGrpFecBanksFree       OBJECT-TYPE
    SYNTAX      Unsigned32
    MAX-ACCESS  read-only
    STATUS      current
    DESCRIPTION
        "The value of the object tCardIxrResGrpFecBanksFree indicates the
         number of free FEC Group banks that are currently available for
         different applications on this card.

         Group FECs are required on per ECMP group, also known as ECMP
         destination basis.

         Level-1 is used by IP ECMP applications while Level-2 FEC may be used
         by labeled or IP ECMP applications."
    ::= { tCardIxrResourceEntry 26 }

tCardIxrResGrpFecLvl1BanksAlloc  OBJECT-TYPE
    SYNTAX      Unsigned32
    MAX-ACCESS  read-only
    STATUS      current
    DESCRIPTION
        "The value of the object tCardIxrResGrpFecLvl1BanksAlloc indicates the
         number of FEC Group Level-1 banks that are currently in use by
         different applications on this card.

         Level-1 is used by IP ECMP applications."
    ::= { tCardIxrResourceEntry 27 }

tCardIxrResGrpFecLvl2BanksAlloc  OBJECT-TYPE
    SYNTAX      Unsigned32
    MAX-ACCESS  read-only
    STATUS      current
    DESCRIPTION
        "The value of the object tCardIxrResGrpFecLvl2BanksAlloc indicates the
         number of FEC Group Level-2 banks that are currently in use by
         different applications on this card.

         Level-2 may be used by labeled or IP ECMP applications."
    ::= { tCardIxrResourceEntry 28 }

tCardIxrResGrpFecLevel1Total     OBJECT-TYPE
    SYNTAX      Unsigned32
    MAX-ACCESS  read-only
    STATUS      current
    DESCRIPTION
        "The value of the object tCardIxrResGrpFecLevel1Total indicates the
         maximum number of FEC Group Level-1 entries that are allowed on this
         card to be used by different applications on this card.

         Level-1 is used by IP ECMP applications."
    ::= { tCardIxrResourceEntry 29 }

tCardIxrResGrpFecLevel1Alloc     OBJECT-TYPE
    SYNTAX      Unsigned32
    MAX-ACCESS  read-only
    STATUS      current
    DESCRIPTION
        "The value of the object tCardIxrResGrpFecLevel1Alloc indicates the
         number of FEC Group Level-1 entries that are currently in use by
         different applications on this card.

         Level-1 is used by IP ECMP applications."
    ::= { tCardIxrResourceEntry 30 }

tCardIxrResGrpFecLevel1Free      OBJECT-TYPE
    SYNTAX      Unsigned32
    MAX-ACCESS  read-only
    STATUS      current
    DESCRIPTION
        "The value of the object tCardIxrResGrpFecLevel1Free indicates the
         number of free FEC Group Level-1 entries that are currently available
         for different applications on this card.

         Level-1 is used by IP ECMP applications."
    ::= { tCardIxrResourceEntry 31 }

tCardIxrResGrpFecLevel2Total     OBJECT-TYPE
    SYNTAX      Unsigned32
    MAX-ACCESS  read-only
    STATUS      current
    DESCRIPTION
        "The value of the object tCardIxrResGrpFecLevel2Total indicates the
         maximum number of FEC Group Level-2 entries that are allowed on this
         card to be used by different applications on this card.

         Level-2 may be used by labeled or IP ECMP applications."
    ::= { tCardIxrResourceEntry 32 }

tCardIxrResGrpFecLevel2Alloc     OBJECT-TYPE
    SYNTAX      Unsigned32
    MAX-ACCESS  read-only
    STATUS      current
    DESCRIPTION
        "The value of the object tCardIxrResGrpFecLevel2Alloc indicates the
         number of FEC Group Level 2 entries that are currently in use by
         different applications on this card.

         Level-2 may be used by labeled or IP ECMP applications."
    ::= { tCardIxrResourceEntry 33 }

tCardIxrResGrpFecLevel2Free      OBJECT-TYPE
    SYNTAX      Unsigned32
    MAX-ACCESS  read-only
    STATUS      current
    DESCRIPTION
        "The value of the object tCardIxrResGrpFecLevel2Free indicates the
         number of free FEC Group Level 2 entries that are currently available
         for different applications on this card.

         Level-2 may be used by labeled or IP ECMP applications."
    ::= { tCardIxrResourceEntry 34 }

tCardIxrResIlmSwapTotal          OBJECT-TYPE
    SYNTAX      Unsigned32
    MAX-ACCESS  read-only
    STATUS      current
    DESCRIPTION
        "The value of the object tCardIxrResIlmSwapTotal indicates the maximum
         number of ILM Swap entries that are allowed on this card to be used by
         different applications on this card."
    ::= { tCardIxrResourceEntry 35 }

tCardIxrResIlmSwapAlloc          OBJECT-TYPE
    SYNTAX      Unsigned32
    MAX-ACCESS  read-only
    STATUS      current
    DESCRIPTION
        "The value of the object tCardIxrResIlmSwapAlloc indicates the number
         of ILM Swap entries that are currently in use by different
         applications on this card."
    ::= { tCardIxrResourceEntry 36 }

tCardIxrResIlmSwapFree           OBJECT-TYPE
    SYNTAX      Unsigned32
    MAX-ACCESS  read-only
    STATUS      current
    DESCRIPTION
        "The value of the object tCardIxrResIlmSwapFree indicates the number of
         free ILM Swap entries that are currently available for different
         applications on this card."
    ::= { tCardIxrResourceEntry 37 }

tCardIxrResFecLevel3Total        OBJECT-TYPE
    SYNTAX      Unsigned32
    MAX-ACCESS  read-only
    STATUS      current
    DESCRIPTION
        "The value of the object tCardIxrResFecLevel3Total indicates the
         maximum number of FEC Level-3 entries that are allowed to be used by
         different applications on this card.

         FEC Level-3 may be used by labeled applications."
    ::= { tCardIxrResourceEntry 38 }

tCardIxrResFecLevel3Alloc        OBJECT-TYPE
    SYNTAX      Unsigned32
    MAX-ACCESS  read-only
    STATUS      current
    DESCRIPTION
        "The value of the object tCardIxrResFecLevel3Alloc indicates the number
         of FEC Level-3 entries that are currently in use by different
         applications on this card.

         FEC Level-3 may be used by labeled applications."
    ::= { tCardIxrResourceEntry 39 }

tCardIxrResFecLevel3Free         OBJECT-TYPE
    SYNTAX      Unsigned32
    MAX-ACCESS  read-only
    STATUS      current
    DESCRIPTION
        "The value of the object tCardIxrResFecLevel3Free indicates the number
         of free FEC Level-3 entries that are currently available for different
         applications on this card.

         FEC Level-3 may be used by labeled applications."
    ::= { tCardIxrResourceEntry 40 }

tCardIxrResGrpFecLvl3BanksAlloc  OBJECT-TYPE
    SYNTAX      Unsigned32
    MAX-ACCESS  read-only
    STATUS      current
    DESCRIPTION
        "The value of the object tCardIxrResGrpFecLvl3BanksAlloc indicates the
         number of FEC Group Level-3 banks that are currently in use by
         different applications on this card.

         FEC Level-3 may be used by labeled applications."
    ::= { tCardIxrResourceEntry 41 }

tCardIxrResGrpFecLevel3Total     OBJECT-TYPE
    SYNTAX      Unsigned32
    MAX-ACCESS  read-only
    STATUS      current
    DESCRIPTION
        "The value of the object tCardIxrResGrpFecLevel3Total indicates the
         maximum number of FEC Group Level-3 entries that are allowed to be
         used by different applications on this card.

         FEC Level-3 may be used by labeled applications."
    ::= { tCardIxrResourceEntry 42 }

tCardIxrResGrpFecLevel3Alloc     OBJECT-TYPE
    SYNTAX      Unsigned32
    MAX-ACCESS  read-only
    STATUS      current
    DESCRIPTION
        "The value of the object tCardIxrResGrpFecLevel3Alloc indicates the
         number of FEC Group Level-3 entries that are currently in use by
         different applications on this card.

         FEC Level-3 may be used by labeled applications."
    ::= { tCardIxrResourceEntry 43 }

tCardIxrResGrpFecLevel3Free      OBJECT-TYPE
    SYNTAX      Unsigned32
    MAX-ACCESS  read-only
    STATUS      current
    DESCRIPTION
        "The value of the object tCardIxrResGrpFecLevel3Free indicates the
         number of free FEC Group Level-3 entries that are currently available
         for different applications on this card.

         FEC Level-3 may be used by labeled applications."
    ::= { tCardIxrResourceEntry 44 }

tCardIxrResPpmcBestCaseEstTotal  OBJECT-TYPE
    SYNTAX      Unsigned32
    MAX-ACCESS  read-only
    STATUS      current
    DESCRIPTION
        "The value of the object tCardIxrResPpmcBestCaseEstTotal indicates the
         best-case estimate for the maximum number of PPMC resources that can
         be used by different applications on this card."
    ::= { tCardIxrResourceEntry 45 }

tCardIxrResPpmcWrstCaseEstTotal  OBJECT-TYPE
    SYNTAX      Unsigned32
    MAX-ACCESS  read-only
    STATUS      current
    DESCRIPTION
        "The value of the object tCardIxrResPpmcWrstCaseEstTotal indicates the
         worst-case estimate for the maximum number of PPMC resources that can
         be used by different applications on this card."
    ::= { tCardIxrResourceEntry 46 }

tCardIxrResPpmcSingleLevelAlloc  OBJECT-TYPE
    SYNTAX      Unsigned32
    MAX-ACCESS  read-only
    STATUS      current
    DESCRIPTION
        "The value of the object tCardIxrResPpmcSingleLevelAlloc indicates the
         number of PPMC entries that are currently in use for single-level
         hierarchies.

         The value 4294967295 indicates that the value is not applicable."
    ::= { tCardIxrResourceEntry 47 }

tCardIxrResPpmcMultiLevelAlloc   OBJECT-TYPE
    SYNTAX      Unsigned32
    MAX-ACCESS  read-only
    STATUS      current
    DESCRIPTION
        "The value of the object tCardIxrResPpmcMultiLevelAlloc indicates the
         number of PPMC entries that are currently in use for multi-level
         hierarchies.

         The value 4294967295 indicates that the value is not applicable."
    ::= { tCardIxrResourceEntry 48 }

tCardIxrResPpmcExhausted         OBJECT-TYPE
    SYNTAX      TruthValue
    MAX-ACCESS  read-only
    STATUS      current
    DESCRIPTION
        "The value of the object tCardIxrResPpmcExhausted indicates if the PPMC
         entries have been exhausted."
    ::= { tCardIxrResourceEntry 49 }

tCardIxrResourceOwnerTable       OBJECT-TYPE
    SYNTAX      SEQUENCE OF TCardIxrResourceOwnerEntry
    MAX-ACCESS  not-accessible
    STATUS      current
    DESCRIPTION
        "The tCardIxrResourceOwnerTable contains information about a card
         resource utilization by resource owners for resources specific to the
         Nokia IXR systems."
    ::= { tmnxCardObjs 100 }

tCardIxrResourceOwnerEntry       OBJECT-TYPE
    SYNTAX      TCardIxrResourceOwnerEntry
    MAX-ACCESS  not-accessible
    STATUS      current
    DESCRIPTION
        "Each row in the tCardIxrResourceOwnerEntry contains information about
         resource utilization for the chassis, card and resource owner
         specified by the indexes.

         Entries cannot be created or deleted by SNMP SET operations. Where
         supported, entries are created automatically by the system."
    INDEX       {
        tmnxChassisIndex,
        tmnxCardSlotNum,
        tCardIxrResourceOwner
    }
    ::= { tCardIxrResourceOwnerTable 1 }

TCardIxrResourceOwnerEntry       ::= SEQUENCE
{
    tCardIxrResourceOwner            TmnxCardIxrResourceOwner,
    tCardIxrResOwnFecLevel1Alloc     Unsigned32,
    tCardIxrResOwnFecLevel2Alloc     Unsigned32,
    tCardIxrResOwnGrpFecAlloc        Unsigned32,
    tCardIxrResOwnGrpFecLevel1Alloc  Unsigned32,
    tCardIxrResOwnGrpFecLevel2Alloc  Unsigned32,
    tCardIxrResOwnFecLevel3Alloc     Unsigned32,
    tCardIxrResOwnGrpFecLevel3Alloc  Unsigned32,
    tCardIxrResOwnPpmcSingleLvlAlloc Unsigned32,
    tCardIxrResOwnPpmcMultiLvlAlloc  Unsigned32
}

tCardIxrResourceOwner            OBJECT-TYPE
    SYNTAX      TmnxCardIxrResourceOwner
    MAX-ACCESS  not-accessible
    STATUS      current
    DESCRIPTION
        "The value of the object tCardIxrResourceOwner specifies the
         application that uses the resources."
    ::= { tCardIxrResourceOwnerEntry 1 }

tCardIxrResOwnFecLevel1Alloc     OBJECT-TYPE
    SYNTAX      Unsigned32
    MAX-ACCESS  read-only
    STATUS      current
    DESCRIPTION
        "The value of the object tCardIxrResOwnFecLevel1Alloc indicates the
         number of FEC Level-1 entries that are currently in use by the owner.

         The value 4294967295 indicates that the value is not applicable."
    ::= { tCardIxrResourceOwnerEntry 2 }

tCardIxrResOwnFecLevel2Alloc     OBJECT-TYPE
    SYNTAX      Unsigned32
    MAX-ACCESS  read-only
    STATUS      current
    DESCRIPTION
        "The value of the object tCardIxrResOwnFecLevel2Alloc indicates the
         number of FEC Level-2 entries that are currently in use by the owner.

         The value 4294967295 indicates that the value is not applicable."
    ::= { tCardIxrResourceOwnerEntry 3 }

tCardIxrResOwnGrpFecAlloc        OBJECT-TYPE
    SYNTAX      Unsigned32
    MAX-ACCESS  read-only
    STATUS      current
    DESCRIPTION
        "The value of the object tCardIxrResOwnGrpFecAlloc indicates the number
         of FEC Group entries that are currently in use by the owner.

         The value 4294967295 indicates that the value is not applicable."
    ::= { tCardIxrResourceOwnerEntry 4 }

tCardIxrResOwnGrpFecLevel1Alloc  OBJECT-TYPE
    SYNTAX      Unsigned32
    MAX-ACCESS  read-only
    STATUS      current
    DESCRIPTION
        "The value of the object tCardIxrResOwnGrpFecLevel1Alloc indicates the
         number of FEC Group Level 1 entries that are currently in use by the
         owner.

         The value 4294967295 indicates that the value is not applicable."
    ::= { tCardIxrResourceOwnerEntry 5 }

tCardIxrResOwnGrpFecLevel2Alloc  OBJECT-TYPE
    SYNTAX      Unsigned32
    MAX-ACCESS  read-only
    STATUS      current
    DESCRIPTION
        "The value of the object tCardIxrResOwnGrpFecLevel2Alloc indicates the
         number of FEC Group Level 2 entries that are currently in use by the
         owner.

         The value 4294967295 indicates that the value is not applicable."
    ::= { tCardIxrResourceOwnerEntry 6 }

tCardIxrResOwnFecLevel3Alloc     OBJECT-TYPE
    SYNTAX      Unsigned32
    MAX-ACCESS  read-only
    STATUS      current
    DESCRIPTION
        "The value of the object tCardIxrResOwnFecLevel3Alloc indicates the
         number of FEC Level-3 entries that are currently in use by the owner.

         The value 4294967295 indicates that the value is not applicable."
    ::= { tCardIxrResourceOwnerEntry 7 }

tCardIxrResOwnGrpFecLevel3Alloc  OBJECT-TYPE
    SYNTAX      Unsigned32
    MAX-ACCESS  read-only
    STATUS      current
    DESCRIPTION
        "The value of the object tCardIxrResOwnGrpFecLevel3Alloc indicates the
         number of FEC Group Level 3 entries that are currently in use by the
         owner.

         The value 4294967295 indicates that the value is not applicable."
    ::= { tCardIxrResourceOwnerEntry 8 }

tCardIxrResOwnPpmcSingleLvlAlloc OBJECT-TYPE
    SYNTAX      Unsigned32
    MAX-ACCESS  read-only
    STATUS      current
    DESCRIPTION
        "The value of the object tCardIxrResOwnPpmcSingleLvlAlloc indicates the
         number of PPMC entries that are currently in use by the owner for
         single-level hierarchies.

         The value 4294967295 indicates that the value is not applicable."
    ::= { tCardIxrResourceOwnerEntry 9 }

tCardIxrResOwnPpmcMultiLvlAlloc  OBJECT-TYPE
    SYNTAX      Unsigned32
    MAX-ACCESS  read-only
    STATUS      current
    DESCRIPTION
        "The value of the object tCardIxrResOwnPpmcMultiLvlAlloc indicates the
         number of PPMC entries that are currently in use by the owner for
         multi-level hierarchies.

         The value 4294967295 indicates that the value is not applicable."
    ::= { tCardIxrResourceOwnerEntry 10 }

tFpIxrResourceTable              OBJECT-TYPE
    SYNTAX      SEQUENCE OF TFpIxrResourceEntry
    MAX-ACCESS  not-accessible
    STATUS      current
    DESCRIPTION
        "The tFpIxrResourceTable contains information about FP resource
         utilization for resources specific to the Nokia IXR systems."
    ::= { tmnxCardObjs 102 }

tFpIxrResourceEntry              OBJECT-TYPE
    SYNTAX      TFpIxrResourceEntry
    MAX-ACCESS  not-accessible
    STATUS      current
    DESCRIPTION
        "Each row in the tFpIxrResourceEntry contains information about
         resource utilization on the FP specified by the indices.

         Entries cannot be created or deleted by SNMP SET operations. Where
         supported, entries are created automatically by the system."
    INDEX       {
        tmnxChassisIndex,
        tmnxCardSlotNum,
        tFPIxrResFPNum
    }
    ::= { tFpIxrResourceTable 1 }

TFpIxrResourceEntry              ::= SEQUENCE
{
    tFPIxrResFPNum                   TmnxFPNumber,
    tFpIxrResEgrGlobalLifMapTotal    Unsigned32,
    tFpIxrResEgrGlobalLifMapAlloc    Unsigned32,
    tFpIxrResEgrGlobalLifMapFree     Unsigned32,
    tFpIxrResIngTerminationATotal    Unsigned32,
    tFpIxrResIngTerminationAAlloc    Unsigned32,
    tFpIxrResIngTerminationAFree     Unsigned32,
    tFpIxrResIngTerminationBTotal    Unsigned32,
    tFpIxrResIngTerminationBAlloc    Unsigned32,
    tFpIxrResIngTerminationBFree     Unsigned32,
    tFpIxrResIngEndpoint1Total       Unsigned32,
    tFpIxrResIngEndpoint1Alloc       Unsigned32,
    tFpIxrResIngEndpoint1Free        Unsigned32,
    tFpIxrResIngEndpoint2Total       Unsigned32,
    tFpIxrResIngEndpoint2Alloc       Unsigned32,
    tFpIxrResIngEndpoint2Free        Unsigned32,
    tFpIxrResIngEndpoint3Total       Unsigned32,
    tFpIxrResIngEndpoint3Alloc       Unsigned32,
    tFpIxrResIngEndpoint3Free        Unsigned32,
    tFpIxrResEgrEncapBanksTotal      Unsigned32,
    tFpIxrResEgrEncapBanksAlloc      Unsigned32,
    tFpIxrResEgrEncapBanksFree       Unsigned32,
    tFpIxrResEgrEncapEntriesTotal    Unsigned32,
    tFpIxrResEgrEncapEntriesAlloc    Unsigned32,
    tFpIxrResEgrEncapEntriesFree     Unsigned32,
    tFpIxrResEgrRoutedBanks          Unsigned32,
    tFpIxrResEgrRoutedTotal          Unsigned32,
    tFpIxrResEgrRoutedAlloc          Unsigned32,
    tFpIxrResEgrRoutedFree           Unsigned32,
    tFpIxrResEgrTdmBanks             Unsigned32,
    tFpIxrResEgrTdmTotal             Unsigned32,
    tFpIxrResEgrTdmAlloc             Unsigned32,
    tFpIxrResEgrTdmFree              Unsigned32,
    tFpIxrResEgrPortVlanXlatBanks    Unsigned32,
    tFpIxrResEgrPortVlanXlatTotal    Unsigned32,
    tFpIxrResEgrPortVlanXlatAlloc    Unsigned32,
    tFpIxrResEgrPortVlanXlatFree     Unsigned32,
    tFpIxrResEgrArpBanks             Unsigned32,
    tFpIxrResEgrArpTotal             Unsigned32,
    tFpIxrResEgrArpAlloc             Unsigned32,
    tFpIxrResEgrArpFree              Unsigned32,
    tFpIxrResEgrLabelPushBanks       Unsigned32,
    tFpIxrResEgrLabelPushTotal       Unsigned32,
    tFpIxrResEgrLabelPushAlloc       Unsigned32,
    tFpIxrResEgrLabelPushFree        Unsigned32,
    tFpIxrResEgrLabelSwapPushBanks   Unsigned32,
    tFpIxrResEgrLabelSwapPushTotal   Unsigned32,
    tFpIxrResEgrLabelSwapPushAlloc   Unsigned32,
    tFpIxrResEgrLabelSwapPushFree    Unsigned32,
    tFpIxrResEgrPortVlanXltExtBanks  Unsigned32,
    tFpIxrResEgrPortVlanXltExtTotal  Unsigned32,
    tFpIxrResEgrPortVlanXltExtAlloc  Unsigned32,
    tFpIxrResEgrPortVlanXltExtFree   Unsigned32,
    tFpIxrResEgrArpExtBanks          Unsigned32,
    tFpIxrResEgrArpExtTotal          Unsigned32,
    tFpIxrResEgrArpExtAlloc          Unsigned32,
    tFpIxrResEgrArpExtFree           Unsigned32,
    tFpIxrResEgrLabelPushExtBanks    Unsigned32,
    tFpIxrResEgrLabelPushExtTotal    Unsigned32,
    tFpIxrResEgrLabelPushExtAlloc    Unsigned32,
    tFpIxrResEgrLabelPushExtFree     Unsigned32,
    tFpIxrResEgrLabelSwapPshExBanks  Unsigned32,
    tFpIxrResEgrLabelSwapPshExTotal  Unsigned32,
    tFpIxrResEgrLabelSwapPshExAlloc  Unsigned32,
    tFpIxrResEgrLabelSwapPshExFree   Unsigned32,
    tFpIxrResEgrEncapExtBanksTotal   Unsigned32,
    tFpIxrResEgrEncapExtBanksAlloc   Unsigned32,
    tFpIxrResEgrEncapExtBanksFree    Unsigned32,
    tFpIxrResEgrEncapExtEntriesTotal Unsigned32,
    tFpIxrResEgrEncapExtEntriesAlloc Unsigned32,
    tFpIxrResEgrEncapExtEntriesFree  Unsigned32,
    tFpIxrResEgrExPortVlanXlatBanks  Unsigned32,
    tFpIxrResEgrExPortVlanXlatTotal  Unsigned32,
    tFpIxrResEgrExPortVlanXlatAlloc  Unsigned32,
    tFpIxrResEgrExPortVlanXlatFree   Unsigned32,
    tFpIxrResEgrExArpBanks           Unsigned32,
    tFpIxrResEgrExArpTotal           Unsigned32,
    tFpIxrResEgrExArpAlloc           Unsigned32,
    tFpIxrResEgrExArpFree            Unsigned32,
    tFpIxrResEgrExLabelPushBanks     Unsigned32,
    tFpIxrResEgrExLabelPushTotal     Unsigned32,
    tFpIxrResEgrExLabelPushAlloc     Unsigned32,
    tFpIxrResEgrExLabelPushFree      Unsigned32,
    tFpIxrResEgrExLabelSwapPshBanks  Unsigned32,
    tFpIxrResEgrExLabelSwapPshTotal  Unsigned32,
    tFpIxrResEgrExLabelSwapPshAlloc  Unsigned32,
    tFpIxrResEgrExLabelSwapPshFree   Unsigned32,
    tFpIxrResLargeExactMatchTotal    Unsigned32,
    tFpIxrResLargeExactMatchAlloc    Unsigned32,
    tFpIxrResLargeExactMatchFree     Unsigned32,
    tFpIxrResLargeExactMatch1Total   Unsigned32,
    tFpIxrResLargeExactMatch1Alloc   Unsigned32,
    tFpIxrResLargeExactMatch1Free    Unsigned32,
    tFpIxrResLargeExactMatch2Total   Unsigned32,
    tFpIxrResLargeExactMatch2Alloc   Unsigned32,
    tFpIxrResLargeExactMatch2Free    Unsigned32
}

tFPIxrResFPNum                   OBJECT-TYPE
    SYNTAX      TmnxFPNumber
    MAX-ACCESS  not-accessible
    STATUS      current
    DESCRIPTION
        "The value of tmnxFPNum identifies the Forwarding Plane."
    ::= { tFpIxrResourceEntry 1 }

tFpIxrResEgrGlobalLifMapTotal    OBJECT-TYPE
    SYNTAX      Unsigned32
    MAX-ACCESS  read-only
    STATUS      current
    DESCRIPTION
        "The value of the object tFpIxrResEgrGlobalLifMapTotal indicates the
         maximum number of Global LIF entries at Egress datapath that are
         allowed on this FP."
    ::= { tFpIxrResourceEntry 2 }

tFpIxrResEgrGlobalLifMapAlloc    OBJECT-TYPE
    SYNTAX      Unsigned32
    MAX-ACCESS  read-only
    STATUS      current
    DESCRIPTION
        "The value of the object tFpIxrResEgrGlobalLifMapAlloc indicates the
         number of Global LIF entries that are currently in use on this FP"
    ::= { tFpIxrResourceEntry 3 }

tFpIxrResEgrGlobalLifMapFree     OBJECT-TYPE
    SYNTAX      Unsigned32
    MAX-ACCESS  read-only
    STATUS      current
    DESCRIPTION
        "The value of the object tFpIxrResEgrGlobalLifMapFree indicates the
         number of free Global LIF entries that are currently available on this
         FP.

         Free entries can be claimed by various applications for further
         growth."
    ::= { tFpIxrResourceEntry 4 }

tFpIxrResIngTerminationATotal    OBJECT-TYPE
    SYNTAX      Unsigned32
    MAX-ACCESS  read-only
    STATUS      current
    DESCRIPTION
        "The value of the object tFpIxrResIngTerminationATotal indicates the
         maximum number of Ingress Decapsulation entries on termination stage-A
         that are allowed on this FP.

         Ingress termination is used by various applications including Service
         termination."
    ::= { tFpIxrResourceEntry 5 }

tFpIxrResIngTerminationAAlloc    OBJECT-TYPE
    SYNTAX      Unsigned32
    MAX-ACCESS  read-only
    STATUS      current
    DESCRIPTION
        "The value of the object tFpIxrResIngTerminationAAlloc indicates the
         number of Ingress Decapsulation entries on termination stage-A that
         are currently in use on this FP.

         Ingress termination is used by various applications including Service
         termination."
    ::= { tFpIxrResourceEntry 6 }

tFpIxrResIngTerminationAFree     OBJECT-TYPE
    SYNTAX      Unsigned32
    MAX-ACCESS  read-only
    STATUS      current
    DESCRIPTION
        "The value of the object tFpIxrResIngTerminationAFree indicates the
         number of free Ingress Decapsulation entries on termination stage-A
         that are currently available on this FP.

         Ingress termination is used by various applications including Service
         termination."
    ::= { tFpIxrResourceEntry 7 }

tFpIxrResIngTerminationBTotal    OBJECT-TYPE
    SYNTAX      Unsigned32
    MAX-ACCESS  read-only
    STATUS      current
    DESCRIPTION
        "The value of the object tFpIxrResIngTerminationBTotal indicates the
         maximum number of Ingress Decapsulation entries on termination stage-B
         that are allowed on this FP.

         Ingress termination is used by various applications including Service
         termination."
    ::= { tFpIxrResourceEntry 8 }

tFpIxrResIngTerminationBAlloc    OBJECT-TYPE
    SYNTAX      Unsigned32
    MAX-ACCESS  read-only
    STATUS      current
    DESCRIPTION
        "The value of the object tFpIxrResIngTerminationBAlloc indicates the
         number of Ingress Decapsulation entries on termination stage-B that
         are currently in use on this FP.

         Ingress termination is used by various applications including Service
         termination."
    ::= { tFpIxrResourceEntry 9 }

tFpIxrResIngTerminationBFree     OBJECT-TYPE
    SYNTAX      Unsigned32
    MAX-ACCESS  read-only
    STATUS      current
    DESCRIPTION
        "The value of the object tFpIxrResIngTerminationBFree indicates the
         number of free Ingress Decapsulation entries on termination stage-B
         that are currently available on this FP.

         Ingress termination is used by various applications including Service
         termination."
    ::= { tFpIxrResourceEntry 10 }

tFpIxrResIngEndpoint1Total       OBJECT-TYPE
    SYNTAX      Unsigned32
    MAX-ACCESS  read-only
    STATUS      current
    DESCRIPTION
        "The value of the object tFpIxrResIngEndpoint1Total indicates the
         maximum number of Ingress Decapsulation entries on Endpoint stage-1
         that are allowed on this FP.

         Ingress termination is used by various applications including MPLS."
    ::= { tFpIxrResourceEntry 11 }

tFpIxrResIngEndpoint1Alloc       OBJECT-TYPE
    SYNTAX      Unsigned32
    MAX-ACCESS  read-only
    STATUS      current
    DESCRIPTION
        "The value of the object tFpIxrResIngEndpoint1Alloc indicates the
         number of Ingress Decapsulation entries on Endpoint stage-1 that are
         currently in use on this FP.

         Ingress termination is used by various applications including MPLS."
    ::= { tFpIxrResourceEntry 12 }

tFpIxrResIngEndpoint1Free        OBJECT-TYPE
    SYNTAX      Unsigned32
    MAX-ACCESS  read-only
    STATUS      current
    DESCRIPTION
        "The value of the object tFpIxrResIngEndpoint1Free indicates the number
         of free Ingress Decapsulation entries on Endpoint stage-1 that are
         currently available on this FP.

         Ingress termination is used by various applications including MPLS."
    ::= { tFpIxrResourceEntry 13 }

tFpIxrResIngEndpoint2Total       OBJECT-TYPE
    SYNTAX      Unsigned32
    MAX-ACCESS  read-only
    STATUS      current
    DESCRIPTION
        "The value of the object tFpIxrResIngEndpoint2Total indicates the
         maximum number of Ingress Decapsulation entries on Endpoint stage-2
         that are allowed on this FP.

         Ingress termination is used by various applications including MPLS."
    ::= { tFpIxrResourceEntry 14 }

tFpIxrResIngEndpoint2Alloc       OBJECT-TYPE
    SYNTAX      Unsigned32
    MAX-ACCESS  read-only
    STATUS      current
    DESCRIPTION
        "The value of the object tFpIxrResIngEndpoint2Alloc indicates the
         number of Ingress Decapsulation entries on Endpoint stage-2 that are
         currently in use on this FP.

         Ingress termination is used by various applications including MPLS."
    ::= { tFpIxrResourceEntry 15 }

tFpIxrResIngEndpoint2Free        OBJECT-TYPE
    SYNTAX      Unsigned32
    MAX-ACCESS  read-only
    STATUS      current
    DESCRIPTION
        "The value of the object tFpIxrResIngEndpoint2Free indicates the number
         of free Ingress Decapsulation entries on Endpoint stage-2 that are
         currently available on this FP.

         Ingress termination is used by various applications including MPLS."
    ::= { tFpIxrResourceEntry 16 }

tFpIxrResIngEndpoint3Total       OBJECT-TYPE
    SYNTAX      Unsigned32
    MAX-ACCESS  read-only
    STATUS      current
    DESCRIPTION
        "The value of the object tFpIxrResIngEndpoint3Total indicates the
         maximum number of Ingress Decapsulation entries on Endpoint stage-3
         that are allowed on this FP.

         Ingress termination is used by various applications."
    ::= { tFpIxrResourceEntry 17 }

tFpIxrResIngEndpoint3Alloc       OBJECT-TYPE
    SYNTAX      Unsigned32
    MAX-ACCESS  read-only
    STATUS      current
    DESCRIPTION
        "The value of the object tFpIxrResIngEndpoint3Alloc indicates the
         number of Ingress Decapsulation entries on Endpoint stage-3 that are
         currently in use on this FP.

         Ingress termination is used by various applications."
    ::= { tFpIxrResourceEntry 18 }

tFpIxrResIngEndpoint3Free        OBJECT-TYPE
    SYNTAX      Unsigned32
    MAX-ACCESS  read-only
    STATUS      current
    DESCRIPTION
        "The value of the object tFpIxrResIngEndpoint3Free indicates the number
         of free Ingress Decapsulation entries on Endpoint stage-3 that are
         currently available on this FP.

         Ingress termination is used by various applications."
    ::= { tFpIxrResourceEntry 19 }

tFpIxrResEgrEncapBanksTotal      OBJECT-TYPE
    SYNTAX      Unsigned32
    MAX-ACCESS  read-only
    STATUS      current
    DESCRIPTION
        "The value of the object tFpIxrResEgrEncapBanksTotal indicates the
         maximum number of Egress Encapsulation entries at an aggregate level
         on per bank basis that are allowed on this FP."
    ::= { tFpIxrResourceEntry 20 }

tFpIxrResEgrEncapBanksAlloc      OBJECT-TYPE
    SYNTAX      Unsigned32
    MAX-ACCESS  read-only
    STATUS      current
    DESCRIPTION
        "The value of the object tFpIxrResEgrEncapBanksAlloc indicates the
         number of Egress Encapsulation entries at an aggregate level on per
         bank basis that are currently in use on this FP."
    ::= { tFpIxrResourceEntry 21 }

tFpIxrResEgrEncapBanksFree       OBJECT-TYPE
    SYNTAX      Unsigned32
    MAX-ACCESS  read-only
    STATUS      current
    DESCRIPTION
        "The value of the object tFpIxrResEgrEncapBanksFree indicates the
         number of free Egress Encapsulation entries at an aggregate level on
         per bank basis that are currently available on this FP."
    ::= { tFpIxrResourceEntry 22 }

tFpIxrResEgrEncapEntriesTotal    OBJECT-TYPE
    SYNTAX      Unsigned32
    MAX-ACCESS  read-only
    STATUS      current
    DESCRIPTION
        "The value of the object tFpIxrResEgrEncapEntriesTotal indicates the
         maximum number of Egress Encapsulation entries at an aggregate level
         that are allowed on this FP."
    ::= { tFpIxrResourceEntry 23 }

tFpIxrResEgrEncapEntriesAlloc    OBJECT-TYPE
    SYNTAX      Unsigned32
    MAX-ACCESS  read-only
    STATUS      current
    DESCRIPTION
        "The value of the object tFpIxrResEgrEncapEntriesAlloc indicates the
         number of Egress Encapsulation entries at an aggregate level that are
         currently in use on this FP."
    ::= { tFpIxrResourceEntry 24 }

tFpIxrResEgrEncapEntriesFree     OBJECT-TYPE
    SYNTAX      Unsigned32
    MAX-ACCESS  read-only
    STATUS      current
    DESCRIPTION
        "The value of the object tFpIxrResEgrEncapEntriesFree indicates the
         number of free Egress Encapsulation entries at an aggregate level that
         are currently available on this FP."
    ::= { tFpIxrResourceEntry 25 }

tFpIxrResEgrRoutedBanks          OBJECT-TYPE
    SYNTAX      Unsigned32
    MAX-ACCESS  read-only
    STATUS      current
    DESCRIPTION
        "The value of the object tFpIxrResEgrRoutedBanks indicates the number
         of Egress Encapsulation entries on per bank basis that are currently
         in use by Routed applications this FP.

         Network interfaces, IP interfaces, R-VPLS IP interfaces and IP-VPN
         Services (one entry per IP-VPN service) are among the stakeholders of
         tFpIxrResEgrRoutedBanks.

         When compatible resources are available, number of banks can grow
         based on usage."
    ::= { tFpIxrResourceEntry 26 }

tFpIxrResEgrRoutedTotal          OBJECT-TYPE
    SYNTAX      Unsigned32
    MAX-ACCESS  read-only
    STATUS      current
    DESCRIPTION
        "The value of the object tFpIxrResEgrRoutedTotal indicates the maximum
         number of Egress Encapsulation entries that are allowed to be used by
         Routed applications on this FP.

         Network interfaces, IP interfaces, R-VPLS IP interfaces and IP-VPN
         Services (one entry per IP-VPN service) are among the stakeholders of
         tFpIxrResEgrRoutedTotal.

         Number of entries available can grow dynamically when compatible free
         banks are available and are claimed. "
    ::= { tFpIxrResourceEntry 27 }

tFpIxrResEgrRoutedAlloc          OBJECT-TYPE
    SYNTAX      Unsigned32
    MAX-ACCESS  read-only
    STATUS      current
    DESCRIPTION
        "The value of the object tFpIxrResEgrRoutedAlloc indicates the number
         of Egress Encapsulation entries that are currently in use by Routed
         applications on this FP.

         Network interfaces, IP interfaces, R-VPLS IP interfaces and IP-VPN
         Services (one entry per IP-VPN service) are among the stakeholders of
         tFpIxrResEgrRoutedTotal.

         Number of entries available can grow dynamically when compatible free
         banks are available and are claimed. "
    ::= { tFpIxrResourceEntry 28 }

tFpIxrResEgrRoutedFree           OBJECT-TYPE
    SYNTAX      Unsigned32
    MAX-ACCESS  read-only
    STATUS      current
    DESCRIPTION
        "The value of the object tFpIxrResEgrRoutedFree indicates the number of
         free Egress Encapsulation entries that are currently available for
         Routed applications on this FP.

         Network interfaces, IP interfaces, R-VPLS IP interfaces and IP-VPN
         Services (one entry per IP-VPN service) are among the stakeholders of
         tFpIxrResEgrRoutedTotal.

         Number of entries available can grow dynamically when compatible free
         banks are available and are claimed. "
    ::= { tFpIxrResourceEntry 29 }

tFpIxrResEgrTdmBanks             OBJECT-TYPE
    SYNTAX      Unsigned32
    MAX-ACCESS  read-only
    STATUS      current
    DESCRIPTION
        "The value of the object tFpIxrResEgrTdmBanks indicates the number of
         Egress Encapsulation entries on per bank basis that are currently in
         use by TDM applications on this FP.

         Circuit Emulation services is the main stakeholder of
         tFpIxrResEgrTdmBanks."
    ::= { tFpIxrResourceEntry 30 }

tFpIxrResEgrTdmTotal             OBJECT-TYPE
    SYNTAX      Unsigned32
    MAX-ACCESS  read-only
    STATUS      current
    DESCRIPTION
        "The value of the object tFpIxrResEgrTdmTotal indicates the maximum
         number of Egress Encapsulation entries that are allowed to be used by
         TDM applications on this FP.

         Circuit Emulation services is the main stakeholder of these resources."
    ::= { tFpIxrResourceEntry 31 }

tFpIxrResEgrTdmAlloc             OBJECT-TYPE
    SYNTAX      Unsigned32
    MAX-ACCESS  read-only
    STATUS      current
    DESCRIPTION
        "The value of the object tFpIxrResEgrTdmAlloc indicates the number of
         Egress Encapsulation entries that are currently in use by TDM
         applications on this FP.

         Circuit Emulation services is the main stakeholder of these resources."
    ::= { tFpIxrResourceEntry 32 }

tFpIxrResEgrTdmFree              OBJECT-TYPE
    SYNTAX      Unsigned32
    MAX-ACCESS  read-only
    STATUS      current
    DESCRIPTION
        "The value of the object tFpIxrResEgrTdmFree indicates the number of
         free Egress Encapsulation entries that are currently available for TDM
         applications on this FP.

         Circuit Emulation services is the main stakeholder of these resources."
    ::= { tFpIxrResourceEntry 33 }

tFpIxrResEgrPortVlanXlatBanks    OBJECT-TYPE
    SYNTAX      Unsigned32
    MAX-ACCESS  read-only
    STATUS      current
    DESCRIPTION
        "The value of the object tFpIxrResEgrPortVlanXlatBanks indicates the
         number of Egress Encapsulation entries on per bank basis that are
         currently in use by Port VLAN Translation applications on this FP.

         Layer-2 SAPs under ETH PW (EPIPE) and VPLS, SAPs attached to IP
         interfaces, Network interfaces and R-VPLS IP interfaces are among the
         stakeholders of Port VLAN translation resources.

         When compatible resources are available, number of banks can grow
         based on usage."
    ::= { tFpIxrResourceEntry 34 }

tFpIxrResEgrPortVlanXlatTotal    OBJECT-TYPE
    SYNTAX      Unsigned32
    MAX-ACCESS  read-only
    STATUS      current
    DESCRIPTION
        "The value of the object tFpIxrResEgrPortVlanXlatTotal indicates the
         maximum number of Egress Encapsulation entries that are allowed to be
         used by Port VLAN Translation applications on this FP.

         Layer-2 SAPs under ETH PW (EPIPE) and VPLS, SAPs attached to IP
         interfaces, Network interfaces and R-VPLS IP interfaces are among the
         stakeholders of Port VLAN translation resources.

         Number of entries available can grow dynamically when compatible free
         banks are available and are claimed. "
    ::= { tFpIxrResourceEntry 35 }

tFpIxrResEgrPortVlanXlatAlloc    OBJECT-TYPE
    SYNTAX      Unsigned32
    MAX-ACCESS  read-only
    STATUS      current
    DESCRIPTION
        "The value of the object tFpIxrResEgrPortVlanXlatAlloc indicates the
         number of Egress Encapsulation entries that are currently in use by
         Port VLAN Translation applications on this FP.

         Layer-2 SAPs under ETH PW (EPIPE) and VPLS, SAPs attached to IP
         interfaces, Network interfaces and R-VPLS IP interfaces are among the
         stakeholders of Port VLAN translation resources.

         Number of entries available can grow dynamically when compatible free
         banks are available and are claimed. "
    ::= { tFpIxrResourceEntry 36 }

tFpIxrResEgrPortVlanXlatFree     OBJECT-TYPE
    SYNTAX      Unsigned32
    MAX-ACCESS  read-only
    STATUS      current
    DESCRIPTION
        "The value of the object tFpIxrResEgrPortVlanXlatFree indicates the
         number of free Egress Encapsulation entries that are currently
         available for Port VLAN Translation applications on this FP.

         Layer-2 SAPs under ETH PW (EPIPE) and VPLS, SAPs attached to IP
         interfaces, Network interfaces and R-VPLS IP interfaces are among the
         stakeholders of Port VLAN translation resources.

         Number of entries available can grow dynamically when compatible free
         banks are available and are claimed. "
    ::= { tFpIxrResourceEntry 37 }

tFpIxrResEgrArpBanks             OBJECT-TYPE
    SYNTAX      Unsigned32
    MAX-ACCESS  read-only
    STATUS      current
    DESCRIPTION
        "The value of the object tFpIxrResEgrArpBanks indicates the number of
         Egress Encapsulation entries on per bank basis that are currently in
         use by ARP/ND and MPLS LSPs on this FP.

         When compatible resources are available, number of banks can grow
         based on usage."
    ::= { tFpIxrResourceEntry 38 }

tFpIxrResEgrArpTotal             OBJECT-TYPE
    SYNTAX      Unsigned32
    MAX-ACCESS  read-only
    STATUS      current
    DESCRIPTION
        "The value of the object tFpIxrResEgrArpTotal indicates the maximum
         number of Egress Encapsulation entries that are allowed to be used by
         ARP/ND and MPLS LSPs on this FP.

         Number of entries available can grow dynamically when compatible free
         banks are available and are claimed. "
    ::= { tFpIxrResourceEntry 39 }

tFpIxrResEgrArpAlloc             OBJECT-TYPE
    SYNTAX      Unsigned32
    MAX-ACCESS  read-only
    STATUS      current
    DESCRIPTION
        "The value of the object tFpIxrResEgrArpAlloc indicates the number of
         Egress Encapsulation entries that are currently in use by ARP/ND and
         MPLS LSPs on this FP.

         Number of entries available can grow dynamically when compatible free
         banks are available and are claimed. "
    ::= { tFpIxrResourceEntry 40 }

tFpIxrResEgrArpFree              OBJECT-TYPE
    SYNTAX      Unsigned32
    MAX-ACCESS  read-only
    STATUS      current
    DESCRIPTION
        "The value of the object tFpIxrResEgrArpFree indicates the number of
         free Egress Encapsulation entries that are currently available for
         ARP/ND and MPLS LSPs on this FP.

         Number of entries available can grow dynamically when compatible free
         banks are available and are claimed. "
    ::= { tFpIxrResourceEntry 41 }

tFpIxrResEgrLabelPushBanks       OBJECT-TYPE
    SYNTAX      Unsigned32
    MAX-ACCESS  read-only
    STATUS      current
    DESCRIPTION
        "The value of the object tFpIxrResEgrLabelPushBanks indicates the
         number of Egress Encapsulation entries on per bank basis that are
         currently in use by Label Push operations on this FP.

         When compatible resources are available, number of banks can grow
         based on usage."
    ::= { tFpIxrResourceEntry 42 }

tFpIxrResEgrLabelPushTotal       OBJECT-TYPE
    SYNTAX      Unsigned32
    MAX-ACCESS  read-only
    STATUS      current
    DESCRIPTION
        "The value of the object tFpIxrResEgrLabelPushTotal indicates the
         maximum number of Egress Encapsulation entries that are allowed to be
         used by Label Push operations on this FP.

         Number of entries available can grow dynamically when compatible free
         banks are available and are claimed. "
    ::= { tFpIxrResourceEntry 43 }

tFpIxrResEgrLabelPushAlloc       OBJECT-TYPE
    SYNTAX      Unsigned32
    MAX-ACCESS  read-only
    STATUS      current
    DESCRIPTION
        "The value of the object tFpIxrResEgrLabelPushAlloc indicates the
         number of Egress Encapsulation entries that are currently in use by
         Label Push operations on this FP.

         Number of entries available can grow dynamically when compatible free
         banks are available and are claimed. "
    ::= { tFpIxrResourceEntry 44 }

tFpIxrResEgrLabelPushFree        OBJECT-TYPE
    SYNTAX      Unsigned32
    MAX-ACCESS  read-only
    STATUS      current
    DESCRIPTION
        "The value of the object tFpIxrResEgrLabelPushFree indicates the number
         of free Egress Encapsulation entries that are currently available for
         Label Push operations on this FP.

         Number of entries available can grow dynamically when compatible free
         banks are available and are claimed. "
    ::= { tFpIxrResourceEntry 45 }

tFpIxrResEgrLabelSwapPushBanks   OBJECT-TYPE
    SYNTAX      Unsigned32
    MAX-ACCESS  read-only
    STATUS      current
    DESCRIPTION
        "The value of the object tFpIxrResEgrLabelSwapPushBanks indicates the
         number of Egress Encapsulation entries on per bank basis that are
         currently in use by Label Swap-and-Push operations on this FP.

         When compatible resources are available, number of banks can grow
         based on usage."
    ::= { tFpIxrResourceEntry 46 }

tFpIxrResEgrLabelSwapPushTotal   OBJECT-TYPE
    SYNTAX      Unsigned32
    MAX-ACCESS  read-only
    STATUS      current
    DESCRIPTION
        "The value of the object tFpIxrResEgrLabelSwapPushTotal indicates the
         maximum number of Egress Encapsulation entries that are allowed to be
         used by Label Swap-and-Push operations on this FP.

         Number of entries available can grow dynamically when compatible free
         banks are available and are claimed. "
    ::= { tFpIxrResourceEntry 47 }

tFpIxrResEgrLabelSwapPushAlloc   OBJECT-TYPE
    SYNTAX      Unsigned32
    MAX-ACCESS  read-only
    STATUS      current
    DESCRIPTION
        "The value of the object tFpIxrResEgrLabelSwapPushAlloc indicates the
         number of Egress Encapsulation entries that are currently in use by
         Label Swap-and-Push operations on this FP.

         Number of entries available can grow dynamically when compatible free
         banks are available and are claimed. "
    ::= { tFpIxrResourceEntry 48 }

tFpIxrResEgrLabelSwapPushFree    OBJECT-TYPE
    SYNTAX      Unsigned32
    MAX-ACCESS  read-only
    STATUS      current
    DESCRIPTION
        "The value of the object tFpIxrResEgrLabelSwapPushFree indicates the
         number of free Egress Encapsulation entries that are currently
         available for Label Swap-and-Push operations on this FP.

         Number of entries available can grow dynamically when compatible free
         banks are available and are claimed. "
    ::= { tFpIxrResourceEntry 49 }

tFpIxrResEgrPortVlanXltExtBanks  OBJECT-TYPE
    SYNTAX      Unsigned32
    MAX-ACCESS  read-only
    STATUS      current
    DESCRIPTION
        "The value of the object tFpIxrResEgrPortVlanXltExtBanks indicates the
         number of Egress Encapsulation entries on per bank basis that are
         currently in use by Port VLAN translation applications that requires a
         reflow on this FP.

         Port VLAN translation applications that require a reflow may consume
         entries from Port VLAN translation Extended banks.

         When compatible resources are available, number of banks can grow
         based on usage."
    ::= { tFpIxrResourceEntry 50 }

tFpIxrResEgrPortVlanXltExtTotal  OBJECT-TYPE
    SYNTAX      Unsigned32
    MAX-ACCESS  read-only
    STATUS      current
    DESCRIPTION
        "The value of the object tFpIxrResEgrPortVlanXltExtTotal indicates the
         maximum number of Egress Encapsulation entries that are allowed to be
         used by Port VLAN translation applications that requires a reflow on
         this FP.

         Port VLAN translation applications that require a reflow may consume
         entries from Port VLAN translation Extended banks.

         Number of entries available can grow dynamically when compatible free
         banks are available and are claimed. "
    ::= { tFpIxrResourceEntry 51 }

tFpIxrResEgrPortVlanXltExtAlloc  OBJECT-TYPE
    SYNTAX      Unsigned32
    MAX-ACCESS  read-only
    STATUS      current
    DESCRIPTION
        "The value of the object tFpIxrResEgrPortVlanXltExtAlloc indicates the
         number of Egress Encapsulation entries that are currently in use by
         Port VLAN translation applications that requires a reflow on this FP.

         Port VLAN translation applications that require a reflow may consume
         entries from Port VLAN translation Extended banks.

         Number of entries available can grow dynamically when compatible free
         banks are available and are claimed. "
    ::= { tFpIxrResourceEntry 52 }

tFpIxrResEgrPortVlanXltExtFree   OBJECT-TYPE
    SYNTAX      Unsigned32
    MAX-ACCESS  read-only
    STATUS      current
    DESCRIPTION
        "The value of the object tFpIxrResEgrPortVlanXltExtFree indicates the
         number of free Egress Encapsulation entries that are currently
         available for Port VLAN translation applications that requires a
         reflow on this FP.

         Port VLAN translation applications that require a reflow may consume
         entries from Port VLAN translation Extended banks.

         Number of entries available can grow dynamically when compatible free
         banks are available and are claimed. "
    ::= { tFpIxrResourceEntry 53 }

tFpIxrResEgrArpExtBanks          OBJECT-TYPE
    SYNTAX      Unsigned32
    MAX-ACCESS  read-only
    STATUS      current
    DESCRIPTION
        "The value of the object tFpIxrResEgrArpExtBanks indicates the number
         of Egress Encapsulation entries on per bank basis that are currently
         in use by ARP/ND and MPLS LSPs Extended applications on this FP.

         ARP/ND resolutions and MPLS LSPs operations after a reflow with large
         label stack may consume entries from ARP Extended banks.

         When compatible resources are available, number of banks can grow
         based on usage."
    ::= { tFpIxrResourceEntry 54 }

tFpIxrResEgrArpExtTotal          OBJECT-TYPE
    SYNTAX      Unsigned32
    MAX-ACCESS  read-only
    STATUS      current
    DESCRIPTION
        "The value of the object tFpIxrResEgrArpExtTotal indicates the maximum
         number of Egress Encapsulation entries that are allowed to be used by
         ARP/ND and MPLS LSPs Extended applications on this FP.

         ARP and ND resolutions and MPLS LSPs operations after a reflow with
         large label stack may consume entries from ARP Extended banks.

         Number of entries available can grow dynamically when compatible free
         banks are available and are claimed. "
    ::= { tFpIxrResourceEntry 55 }

tFpIxrResEgrArpExtAlloc          OBJECT-TYPE
    SYNTAX      Unsigned32
    MAX-ACCESS  read-only
    STATUS      current
    DESCRIPTION
        "The value of the object tFpIxrResEgrArpExtAlloc indicates the number
         of Egress Encapsulation entries that are currently in use by ARP/ND
         and MPLS LSPs Extended applications on this FP.

         ARP and ND resolutions and MPLS LSPs operations after a reflow with
         large label stack may consume entries from ARP Extended banks.

         Number of entries available can grow dynamically when compatible free
         banks are available and are claimed. "
    ::= { tFpIxrResourceEntry 56 }

tFpIxrResEgrArpExtFree           OBJECT-TYPE
    SYNTAX      Unsigned32
    MAX-ACCESS  read-only
    STATUS      current
    DESCRIPTION
        "The value of the object tFpIxrResEgrArpExtFree indicates the number of
         free Egress Encapsulation entries that are currently available for
         ARP/ND and MPLS LSPs Extended applications on this FP.

         ARP and ND resolutions and MPLS LSPs operations after a reflow with
         large label stack may consume entries from ARP Extended banks.

         Number of entries available can grow dynamically when compatible free
         banks are available and are claimed. "
    ::= { tFpIxrResourceEntry 57 }

tFpIxrResEgrLabelPushExtBanks    OBJECT-TYPE
    SYNTAX      Unsigned32
    MAX-ACCESS  read-only
    STATUS      current
    DESCRIPTION
        "The value of the object tFpIxrResEgrLabelPushExtBanks indicates the
         number of Egress Encapsulation entries on per bank basis that are
         currently in use by Label Push Extended applications on this FP.

         Label Push operation entries that requires a reflow may consume
         entries from Label Push Extended banks.

         When compatible resources are available, number of banks can grow
         based on usage."
    ::= { tFpIxrResourceEntry 58 }

tFpIxrResEgrLabelPushExtTotal    OBJECT-TYPE
    SYNTAX      Unsigned32
    MAX-ACCESS  read-only
    STATUS      current
    DESCRIPTION
        "The value of the object tFpIxrResEgrLabelPushExtTotal indicates the
         maximum number of Egress Encapsulation entries that are allowed to be
         used by Label Push Extended applications on this FP.

         Label Push operation entries that requires a reflow may consume
         entries from Label Push Extended banks.

         Number of entries available can grow dynamically when compatible free
         banks are available and are claimed. "
    ::= { tFpIxrResourceEntry 59 }

tFpIxrResEgrLabelPushExtAlloc    OBJECT-TYPE
    SYNTAX      Unsigned32
    MAX-ACCESS  read-only
    STATUS      current
    DESCRIPTION
        "The value of the object tFpIxrResEgrLabelPushExtAlloc indicates the
         number of Egress Encapsulation entries that are currently in use by
         Label Push Extended applications on this FP.

         Label Push operation entries that requires a reflow may consume
         entries from Label Push Extended banks.

         Number of entries available can grow dynamically when compatible free
         banks are available and are claimed. "
    ::= { tFpIxrResourceEntry 60 }

tFpIxrResEgrLabelPushExtFree     OBJECT-TYPE
    SYNTAX      Unsigned32
    MAX-ACCESS  read-only
    STATUS      current
    DESCRIPTION
        "The value of the object tFpIxrResEgrLabelPushExtFree indicates the
         number of free Egress Encapsulation entries that are currently
         available for Label Push Extended applications on this FP.

         Label Push operation entries that requires a reflow may consume
         entries from Label Push Extended banks.

         Number of entries available can grow dynamically when compatible free
         banks are available and are claimed. "
    ::= { tFpIxrResourceEntry 61 }

tFpIxrResEgrLabelSwapPshExBanks  OBJECT-TYPE
    SYNTAX      Unsigned32
    MAX-ACCESS  read-only
    STATUS      current
    DESCRIPTION
        "The value of the object tFpIxrResEgrLabelSwapPshExBanks indicates the
         number of Egress Encapsulation entries on per bank basis that are
         currently in use by Label Swap-and-Push Extended applications on this
         FP.

         Label swap followed by a push operation entries that requires a reflow
         may consume entries from Label Swap and Push Extended banks.

         When compatible resources are available, number of banks can grow
         based on usage."
    ::= { tFpIxrResourceEntry 62 }

tFpIxrResEgrLabelSwapPshExTotal  OBJECT-TYPE
    SYNTAX      Unsigned32
    MAX-ACCESS  read-only
    STATUS      current
    DESCRIPTION
        "The value of the object tFpIxrResEgrLabelSwapPshExTotal indicates the
         maximum number of Egress Encapsulation entries that are allowed to be
         used by Label Swap-and-Push Extended applications on this FP.

         Label swap followed by a push operation entries that requires a reflow
         may consume entries from Label Swap and Push Extended banks.

         Number of entries available can grow dynamically when compatible free
         banks are available and are claimed. "
    ::= { tFpIxrResourceEntry 63 }

tFpIxrResEgrLabelSwapPshExAlloc  OBJECT-TYPE
    SYNTAX      Unsigned32
    MAX-ACCESS  read-only
    STATUS      current
    DESCRIPTION
        "The value of the object tFpIxrResEgrLabelSwapPshExAlloc indicates the
         number of Egress Encapsulation entries that are currently in use by
         Label Swap-and-Push Extended applications on this FP.

         Label swap followed by a push operation entries that requires a reflow
         may consume entries from Label Swap and Push Extended banks.

         Number of entries available can grow dynamically when compatible free
         banks are available and are claimed. "
    ::= { tFpIxrResourceEntry 64 }

tFpIxrResEgrLabelSwapPshExFree   OBJECT-TYPE
    SYNTAX      Unsigned32
    MAX-ACCESS  read-only
    STATUS      current
    DESCRIPTION
        "The value of the object tFpIxrResEgrLabelSwapPshExFree indicates the
         number of free Egress Encapsulation entries that are currently
         available for Label Swap-and-Push Extended applications on this FP.

         Label swap followed by a push operation entries that requires a reflow
         may consume entries from Label Swap and Push Extended banks.

         Number of entries available can grow dynamically when compatible free
         banks are available and are claimed. "
    ::= { tFpIxrResourceEntry 65 }

tFpIxrResEgrEncapExtBanksTotal   OBJECT-TYPE
    SYNTAX      Unsigned32
    MAX-ACCESS  read-only
    STATUS      current
    DESCRIPTION
        "The value of the object tFpIxrResEgrEncapExtBanksTotal indicates the
         maximum number of Egress Encapsulation Extension stage (stage-II)
         banks at aggregate level that are allowed on this FP."
    ::= { tFpIxrResourceEntry 66 }

tFpIxrResEgrEncapExtBanksAlloc   OBJECT-TYPE
    SYNTAX      Unsigned32
    MAX-ACCESS  read-only
    STATUS      current
    DESCRIPTION
        "The value of the object tFpIxrResEgrEncapExtBanksAlloc indicates the
         number of Egress Encapsulation Extension stage (stage-II) banks at an
         aggregate level that are currently in use on this FP."
    ::= { tFpIxrResourceEntry 67 }

tFpIxrResEgrEncapExtBanksFree    OBJECT-TYPE
    SYNTAX      Unsigned32
    MAX-ACCESS  read-only
    STATUS      current
    DESCRIPTION
        "The value of the object tFpIxrResEgrEncapExtBanksFree indicates the
         number of free Egress Encapsulation Extension stage (stage-II) banks
         at an aggregate level that are currently available on this FP."
    ::= { tFpIxrResourceEntry 68 }

tFpIxrResEgrEncapExtEntriesTotal OBJECT-TYPE
    SYNTAX      Unsigned32
    MAX-ACCESS  read-only
    STATUS      current
    DESCRIPTION
        "The value of the object tFpIxrResEgrEncapExtEntriesTotal indicates the
         maximum number of Egress Encapsulation Extension stage (stage-II)
         entries at aggregate level that are allowed on this FP."
    ::= { tFpIxrResourceEntry 69 }

tFpIxrResEgrEncapExtEntriesAlloc OBJECT-TYPE
    SYNTAX      Unsigned32
    MAX-ACCESS  read-only
    STATUS      current
    DESCRIPTION
        "The value of the object tFpIxrResEgrEncapExtEntriesAlloc indicates the
         number of Egress Encapsulation Extension stage (stage-II) entries at
         an aggregate level that are currently in use on this FP."
    ::= { tFpIxrResourceEntry 70 }

tFpIxrResEgrEncapExtEntriesFree  OBJECT-TYPE
    SYNTAX      Unsigned32
    MAX-ACCESS  read-only
    STATUS      current
    DESCRIPTION
        "The value of the object tFpIxrResEgrEncapExtEntriesFree indicates the
         number of free Egress Encapsulation Extension stage (stage-II) entries
         at an aggregate level that are currently available on this FP."
    ::= { tFpIxrResourceEntry 71 }

tFpIxrResEgrExPortVlanXlatBanks  OBJECT-TYPE
    SYNTAX      Unsigned32
    MAX-ACCESS  read-only
    STATUS      current
    DESCRIPTION
        "The value of the object tFpIxrResEgrExPortVlanXlatBanks indicates the
         number of Egress Encapsulation Extension stage (stage-II) banks that
         are currently in use by Port VLAN Translation applications on this FP.

         Layer-2 SAPs under ETH PW (EPIPE) and VPLS, SAPs attached to IP
         interfaces, Network interfaces and R-VPLS IP interfaces catering to
         applications with deep label stack as an example are among the
         stakeholders of Port VLAN translation stage-II bank.

         When compatible resources are available, number of banks can grow
         based on usage."
    ::= { tFpIxrResourceEntry 72 }

tFpIxrResEgrExPortVlanXlatTotal  OBJECT-TYPE
    SYNTAX      Unsigned32
    MAX-ACCESS  read-only
    STATUS      current
    DESCRIPTION
        "The value of the object tFpIxrResEgrExPortVlanXlatTotal indicates the
         maximum number of Egress Encapsulation Extension stage (stage-II)
         entries that are allowed to be used by Port VLAN Translation
         applications on this FP.

         Layer-2 SAPs under ETH PW (EPIPE) and VPLS, SAPs attached to IP
         interfaces, Network interfaces and R-VPLS IP interfaces catering to
         applications with deep label stack as an example are among the
         stakeholders of Port VLAN translation stage-II bank.

         Number of entries available can grow dynamically when compatible free
         banks are available and are claimed."
    ::= { tFpIxrResourceEntry 73 }

tFpIxrResEgrExPortVlanXlatAlloc  OBJECT-TYPE
    SYNTAX      Unsigned32
    MAX-ACCESS  read-only
    STATUS      current
    DESCRIPTION
        "The value of the object tFpIxrResEgrExPortVlanXlatAlloc indicates the
         number of Egress Encapsulation Extension stage (stage-II) entries that
         are currently in use by Port VLAN Translation applications on this FP.

         Layer-2 SAPs under ETH PW (EPIPE) and VPLS, SAPs attached to IP
         interfaces, Network interfaces and R-VPLS IP interfaces catering to
         applications with deep label stack as an example are among the
         stakeholders of Port VLAN translation stage-II bank.

         Number of entries available can grow dynamically when compatible free
         banks are available and are claimed."
    ::= { tFpIxrResourceEntry 74 }

tFpIxrResEgrExPortVlanXlatFree   OBJECT-TYPE
    SYNTAX      Unsigned32
    MAX-ACCESS  read-only
    STATUS      current
    DESCRIPTION
        "The value of the object tFpIxrResEgrExPortVlanXlatFree indicates the
         number of free Egress Encapsulation Extension stage (stage-II) entries
         that are currently available for Port VLAN Translation applications on
         this FP.

         Layer-2 SAPs under ETH PW (EPIPE) and VPLS, SAPs attached to IP
         interfaces, Network interfaces and R-VPLS IP interfaces catering to
         applications with deep label stack as an example are among the
         stakeholders of Port VLAN translation stage-II bank.

         Number of entries available can grow dynamically when compatible free
         banks are available and are claimed."
    ::= { tFpIxrResourceEntry 75 }

tFpIxrResEgrExArpBanks           OBJECT-TYPE
    SYNTAX      Unsigned32
    MAX-ACCESS  read-only
    STATUS      current
    DESCRIPTION
        "The value of the object tFpIxrResEgrExArpBanks indicates the number of
         Egress Encapsulation Extension stage (stage-II) banks that are
         currently in use by ARP and ND on this FP.

         ARP and ND operations catering to applications with deep label stack
         as an example are among the stakeholders of ARP stage-II bank.

         When compatible resources are available, number of banks can grow
         based on usage."
    ::= { tFpIxrResourceEntry 76 }

tFpIxrResEgrExArpTotal           OBJECT-TYPE
    SYNTAX      Unsigned32
    MAX-ACCESS  read-only
    STATUS      current
    DESCRIPTION
        "The value of the object tFpIxrResEgrExArpTotal indicates the maximum
         number of Egress Encapsulation Extension stage (stage-II) entries that
         are allowed to be used by ARP and ND on this FP.

         ARP and ND operations catering to applications with deep label stack
         as an example are among the stakeholders of ARP stage-II bank.

         Number of entries available can grow dynamically when compatible free
         banks are available and are claimed."
    ::= { tFpIxrResourceEntry 77 }

tFpIxrResEgrExArpAlloc           OBJECT-TYPE
    SYNTAX      Unsigned32
    MAX-ACCESS  read-only
    STATUS      current
    DESCRIPTION
        "The value of the object tFpIxrResEgrExArpAlloc indicates the number of
         Egress Encapsulation Extension stage (stage-II) entries that are
         currently in use by ARP and ND on this FP.

         ARP and ND operations catering to applications with deep label stack
         as an example are among the stakeholders of ARP stage-II bank.

         Number of entries available can grow dynamically when compatible free
         banks are available and are claimed."
    ::= { tFpIxrResourceEntry 78 }

tFpIxrResEgrExArpFree            OBJECT-TYPE
    SYNTAX      Unsigned32
    MAX-ACCESS  read-only
    STATUS      current
    DESCRIPTION
        "The value of the object tFpIxrResEgrExArpFree indicates the number of
         free Egress Encapsulation Extension stage (stage-II) entries that are
         currently available for Port ARP and ND on this FP.

         ARP and ND operations catering to applications with deep label stack
         as an example are among the stakeholders of ARP stage-II bank.

         Number of entries available can grow dynamically when compatible free
         banks are available and are claimed."
    ::= { tFpIxrResourceEntry 79 }

tFpIxrResEgrExLabelPushBanks     OBJECT-TYPE
    SYNTAX      Unsigned32
    MAX-ACCESS  read-only
    STATUS      current
    DESCRIPTION
        "The value of the object tFpIxrResEgrExLabelPushBanks indicates the
         number of Egress Encapsulation Extension stage (stage-II) banks that
         are currently in use by Label Push operations on this FP.

         Label push operations with deep label stack is an example stakeholder
         of Label Push stage-II bank.

         When compatible resources are available, number of banks can grow
         based on usage."
    ::= { tFpIxrResourceEntry 80 }

tFpIxrResEgrExLabelPushTotal     OBJECT-TYPE
    SYNTAX      Unsigned32
    MAX-ACCESS  read-only
    STATUS      current
    DESCRIPTION
        "The value of the object tFpIxrResEgrExLabelPushTotal indicates the
         maximum number of Egress Encapsulation Extension stage (stage-II)
         entries that are allowed to be used by Label Push operations on this
         FP.

         Label push operations with deep label stack is an example stakeholder
         of Label Push stage-II bank.

         Number of entries available can grow dynamically when compatible free
         banks are available and are claimed."
    ::= { tFpIxrResourceEntry 81 }

tFpIxrResEgrExLabelPushAlloc     OBJECT-TYPE
    SYNTAX      Unsigned32
    MAX-ACCESS  read-only
    STATUS      current
    DESCRIPTION
        "The value of the object tFpIxrResEgrExLabelPushAlloc indicates the
         number of Egress Encapsulation Extension stage (stage-II) entries that
         are currently in use by Label Push operations on this FP.

         Label push operations with deep label stack is an example stakeholder
         of Label Push stage-II bank.

         Number of entries available can grow dynamically when compatible free
         banks are available and are claimed."
    ::= { tFpIxrResourceEntry 82 }

tFpIxrResEgrExLabelPushFree      OBJECT-TYPE
    SYNTAX      Unsigned32
    MAX-ACCESS  read-only
    STATUS      current
    DESCRIPTION
        "The value of the object tFpIxrResEgrExLabelPushFree indicates the
         number of free Egress Encapsulation Extension stage (stage-II) entries
         that are currently available for Label Push operations on this FP.

         Label push operations with deep label stack is an example stakeholder
         of Label Push stage-II bank.

         Number of entries available can grow dynamically when compatible free
         banks are available and are claimed."
    ::= { tFpIxrResourceEntry 83 }

tFpIxrResEgrExLabelSwapPshBanks  OBJECT-TYPE
    SYNTAX      Unsigned32
    MAX-ACCESS  read-only
    STATUS      current
    DESCRIPTION
        "The value of the object tFpIxrResEgrExLabelSwapPshBanks indicates the
         number of Egress Encapsulation Extension stage (stage-II) banks that
         are currently in use by Label Swap-and-Push operations on this FP.

         Label push operations with deep label stack is an example stakeholder
         of Label Swap-and-Push stage-II bank.

         When compatible resources are available, number of banks can grow
         based on usage."
    ::= { tFpIxrResourceEntry 84 }

tFpIxrResEgrExLabelSwapPshTotal  OBJECT-TYPE
    SYNTAX      Unsigned32
    MAX-ACCESS  read-only
    STATUS      current
    DESCRIPTION
        "The value of the object tFpIxrResEgrExLabelSwapPshTotal indicates the
         maximum number of Egress Encapsulation Extension stage (stage-II)
         entries that are allowed to be used by Label Swap-and-Push operations
         on this FP.

         Label push operations with deep label stack is an example stakeholder
         of Label Swap-and-Push stage-II bank.

         Number of entries available can grow dynamically when compatible free
         banks are available and are claimed."
    ::= { tFpIxrResourceEntry 85 }

tFpIxrResEgrExLabelSwapPshAlloc  OBJECT-TYPE
    SYNTAX      Unsigned32
    MAX-ACCESS  read-only
    STATUS      current
    DESCRIPTION
        "The value of the object tFpIxrResEgrExLabelSwapPshAlloc indicates the
         number of Egress Encapsulation Extension stage (stage-II) entries that
         are currently in use by Label Swap-and-Push operations on this FP.

         Label push operations with deep label stack is an example stakeholder
         of Label Swap-and-Push stage-II bank.

         Number of entries available can grow dynamically when compatible free
         banks are available and are claimed."
    ::= { tFpIxrResourceEntry 86 }

tFpIxrResEgrExLabelSwapPshFree   OBJECT-TYPE
    SYNTAX      Unsigned32
    MAX-ACCESS  read-only
    STATUS      current
    DESCRIPTION
        "The value of the object tFpIxrResEgrExLabelSwapPshFree indicates the
         number of free Egress Encapsulation Extension stage (stage-II) entries
         that are currently available for Label Swap-and-Push operations on
         this FP.

         Label push operations with deep label stack is an example stakeholder
         of Label Swap-and-Push stage-II bank.

         Number of entries available can grow dynamically when compatible free
         banks are available and are claimed."
    ::= { tFpIxrResourceEntry 87 }

tFpIxrResLargeExactMatchTotal    OBJECT-TYPE
    SYNTAX      Unsigned32
    MAX-ACCESS  read-only
    STATUS      current
    DESCRIPTION
        "The value of the object tFpIxrResLargeExactMatchTotal indicates the
         maximum number of Large Exact Match entries that are allowed on this
         FP.

         Large Exact Match entries are used by various applications including
         Services."
    ::= { tFpIxrResourceEntry 88 }

tFpIxrResLargeExactMatchAlloc    OBJECT-TYPE
    SYNTAX      Unsigned32
    MAX-ACCESS  read-only
    STATUS      current
    DESCRIPTION
        "The value of the object tFpIxrResLargeExactMatchAlloc indicates the
         number of Large Exact Match entries that are currently in use on this
         FP.

         Large Exact Match entries are used by various applications including
         Services."
    ::= { tFpIxrResourceEntry 89 }

tFpIxrResLargeExactMatchFree     OBJECT-TYPE
    SYNTAX      Unsigned32
    MAX-ACCESS  read-only
    STATUS      current
    DESCRIPTION
        "The value of the object tFpIxrResLargeExactMatchFree indicates the
         number of Large Exact Match entries that are currently available on
         this FP.

         Large Exact Match entries are used by various applications including
         Services."
    ::= { tFpIxrResourceEntry 90 }

tFpIxrResLargeExactMatch1Total   OBJECT-TYPE
    SYNTAX      Unsigned32
    MAX-ACCESS  read-only
    STATUS      current
    DESCRIPTION
        "The value of the object tFpIxrResLargeExactMatch1Total indicates the
         maximum number of Large Exact Match 1 entries that are allowed on this
         FP.

         Large Exact Match entries are used by various applications including
         Services."
    ::= { tFpIxrResourceEntry 91 }

tFpIxrResLargeExactMatch1Alloc   OBJECT-TYPE
    SYNTAX      Unsigned32
    MAX-ACCESS  read-only
    STATUS      current
    DESCRIPTION
        "The value of the object tFpIxrResLargeExactMatch1Alloc indicates the
         number of Large Exact Match 1 entries that are currently in use on
         this FP.

         Large Exact Match entries are used by various applications including
         Services."
    ::= { tFpIxrResourceEntry 92 }

tFpIxrResLargeExactMatch1Free    OBJECT-TYPE
    SYNTAX      Unsigned32
    MAX-ACCESS  read-only
    STATUS      current
    DESCRIPTION
        "The value of the object tFpIxrResLargeExactMatch1Free indicates the
         number of Large Exact Match 1 entries that are currently available on
         this FP.

         Large Exact Match entries are used by various applications including
         Services."
    ::= { tFpIxrResourceEntry 93 }

tFpIxrResLargeExactMatch2Total   OBJECT-TYPE
    SYNTAX      Unsigned32
    MAX-ACCESS  read-only
    STATUS      current
    DESCRIPTION
        "The value of the object tFpIxrResLargeExactMatch2Total indicates the
         maximum number of Large Exact Match 2 entries that are allowed on this
         FP.

         Large Exact Match entries are used by various applications including
         Services."
    ::= { tFpIxrResourceEntry 94 }

tFpIxrResLargeExactMatch2Alloc   OBJECT-TYPE
    SYNTAX      Unsigned32
    MAX-ACCESS  read-only
    STATUS      current
    DESCRIPTION
        "The value of the object tFpIxrResLargeExactMatch2Alloc indicates the
         number of Large Exact Match 2 entries that are currently in use on
         this FP.

         Large Exact Match entries are used by various applications including
         Services."
    ::= { tFpIxrResourceEntry 95 }

tFpIxrResLargeExactMatch2Free    OBJECT-TYPE
    SYNTAX      Unsigned32
    MAX-ACCESS  read-only
    STATUS      current
    DESCRIPTION
        "The value of the object tFpIxrResLargeExactMatch2Free indicates the
         number of Large Exact Match 2 entries that are currently available on
         this FP.

         Large Exact Match entries are used by various applications including
         Services."
    ::= { tFpIxrResourceEntry 96 }

tFpIxrResourceEgressTable        OBJECT-TYPE
    SYNTAX      SEQUENCE OF TFpIxrResourceEgressEntry
    MAX-ACCESS  not-accessible
    STATUS      current
    DESCRIPTION
        "The tFpIxrResourceEgressTable contains information about FP
         utilization for egress resources specific to the Nokia IXR systems."
    ::= { tmnxCardObjs 103 }

tFpIxrResourceEgressEntry        OBJECT-TYPE
    SYNTAX      TFpIxrResourceEgressEntry
    MAX-ACCESS  not-accessible
    STATUS      current
    DESCRIPTION
        "Each row in the tFpIxrResourceEgressEntry contains information about
         egress resource utilization on the FP specified by the indices.

         Entries cannot be created or deleted by SNMP SET operations. Where
         supported, entries are created automatically by the system."
    INDEX       {
        tmnxChassisIndex,
        tmnxCardSlotNum,
        tFpIxrResourceEgressFpNum,
        tFpIxrResourceEgressType,
        tFpIxrResourceEgressSet
    }
    ::= { tFpIxrResourceEgressTable 1 }

TFpIxrResourceEgressEntry        ::= SEQUENCE
{
    tFpIxrResourceEgressFpNum        TmnxFPNumber,
    tFpIxrResourceEgressType         TmnxCardFpIxrResourceEgressType,
    tFpIxrResourceEgressSet          TmnxCardFpIxrResourceEgressSet,
    tFpIxrResourceEgressBanksTotal   Unsigned32,
    tFpIxrResourceEgressBanksAlloc   Unsigned32,
    tFpIxrResourceEgressBanksFree    Unsigned32,
    tFpIxrResourceEgressPhases       BITS
}

tFpIxrResourceEgressFpNum        OBJECT-TYPE
    SYNTAX      TmnxFPNumber
    MAX-ACCESS  not-accessible
    STATUS      current
    DESCRIPTION
        "The value of tFpIxrResourceEgressFpNum identifies the Forwarding
         Plane."
    ::= { tFpIxrResourceEgressEntry 1 }

tFpIxrResourceEgressType         OBJECT-TYPE
    SYNTAX      TmnxCardFpIxrResourceEgressType
    MAX-ACCESS  not-accessible
    STATUS      current
    DESCRIPTION
        "The value of tFpIxrResourceEgressType identifies the egress table
         type."
    ::= { tFpIxrResourceEgressEntry 2 }

tFpIxrResourceEgressSet          OBJECT-TYPE
    SYNTAX      TmnxCardFpIxrResourceEgressSet
    MAX-ACCESS  not-accessible
    STATUS      current
    DESCRIPTION
        "The value of tFpIxrResourceEgressSet identifies the IXR FP egress
         resource set."
    ::= { tFpIxrResourceEgressEntry 3 }

tFpIxrResourceEgressBanksTotal   OBJECT-TYPE
    SYNTAX      Unsigned32
    MAX-ACCESS  read-only
    STATUS      current
    DESCRIPTION
        "The value of the object tFpIxrResourceEgressBanksTotal indicates the
         maximum number of banks at Egress datapath that are allowed on this
         FP/table type/set."
    ::= { tFpIxrResourceEgressEntry 4 }

tFpIxrResourceEgressBanksAlloc   OBJECT-TYPE
    SYNTAX      Unsigned32
    MAX-ACCESS  read-only
    STATUS      current
    DESCRIPTION
        "The value of the object tFpIxrResourceEgressBanksAlloc indicates the
         number of banks that are currently in use on this FP/table type/set."
    ::= { tFpIxrResourceEgressEntry 5 }

tFpIxrResourceEgressBanksFree    OBJECT-TYPE
    SYNTAX      Unsigned32
    MAX-ACCESS  read-only
    STATUS      current
    DESCRIPTION
        "The value of the object tFpIxrResourceEgressBanksFree indicates the
         number of free banks that are currently available on this FP/table
         type/set."
    ::= { tFpIxrResourceEgressEntry 6 }

tFpIxrResourceEgressPhases       OBJECT-TYPE
    SYNTAX      BITS {
        phase1 (0),
        phase2 (1),
        phase3 (2),
        phase4 (3),
        phase5 (4),
        phase6 (5),
        phase7 (6),
        phase8 (7)
    }
    MAX-ACCESS  read-only
    STATUS      current
    DESCRIPTION
        "The value of the object tFpIxrResourceEgressPhases indicates the
         phases that can use the egress resource set."
    ::= { tFpIxrResourceEgressEntry 7 }

tFpIxrResourceEgressPhaseTable   OBJECT-TYPE
    SYNTAX      SEQUENCE OF TFpIxrResourceEgressPhaseEntry
    MAX-ACCESS  not-accessible
    STATUS      current
    DESCRIPTION
        "The tFpIxrResourceEgressTable contains information about FP
         utilization for egress resources specific to the Nokia IXR systems."
    ::= { tmnxCardObjs 104 }

tFpIxrResourceEgressPhaseEntry   OBJECT-TYPE
    SYNTAX      TFpIxrResourceEgressPhaseEntry
    MAX-ACCESS  not-accessible
    STATUS      current
    DESCRIPTION
        "Each row in the tFpIxrResourceEgressPhaseEntry contains information
         about egress resource utilization for a phase specified by the
         indices.

         Entries cannot be created or deleted by SNMP SET operations. Where
         supported, entries are created automatically by the system."
    INDEX       {
        tmnxChassisIndex,
        tmnxCardSlotNum,
        tFpIxrRsEgPhFpNum,
        tFpIxrRsEgPhType,
        tFpIxrRsEgPhSet,
        tFpIxrRsEgPhPhase
    }
    ::= { tFpIxrResourceEgressPhaseTable 1 }

TFpIxrResourceEgressPhaseEntry   ::= SEQUENCE
{
    tFpIxrRsEgPhFpNum                TmnxFPNumber,
    tFpIxrRsEgPhType                 TmnxCardFpIxrResourceEgressType,
    tFpIxrRsEgPhSet                  TmnxCardFpIxrResourceEgressSet,
    tFpIxrRsEgPhPhase                TmnxCardFpIxrResourceEgressPhase,
    tFpIxrRsEgPhLinkedDataBanks      Unsigned32,
    tFpIxrRsEgPhLinkedDataTotal      Unsigned32,
    tFpIxrRsEgPhLinkedDataAlloc      Unsigned32,
    tFpIxrRsEgPhLinkedDataFree       Unsigned32,
    tFpIxrRsEgPhNonLinkedDataBanks   Unsigned32,
    tFpIxrRsEgPhNonLinkedDataTotal   Unsigned32,
    tFpIxrRsEgPhNonLinkedDataAlloc   Unsigned32,
    tFpIxrRsEgPhNonLinkedDataFree    Unsigned32,
    tFpIxrRsEgPhLinkedListBanks      Unsigned32,
    tFpIxrRsEgPhLinkedListTotal      Unsigned32,
    tFpIxrRsEgPhLinkedListAlloc      Unsigned32,
    tFpIxrRsEgPhLinkedListFree       Unsigned32,
    tFpIxrRsEgPhLinkedDataLifs       TmnxFpIxrAvailableLifs,
    tFpIxrRsEgPhNonLinkedDataLifs    TmnxFpIxrAvailableLifs
}

tFpIxrRsEgPhFpNum                OBJECT-TYPE
    SYNTAX      TmnxFPNumber
    MAX-ACCESS  not-accessible
    STATUS      current
    DESCRIPTION
        "The value of tFpIxrRsEgPhFpNum identifies the Forwarding Plane."
    ::= { tFpIxrResourceEgressPhaseEntry 1 }

tFpIxrRsEgPhType                 OBJECT-TYPE
    SYNTAX      TmnxCardFpIxrResourceEgressType
    MAX-ACCESS  not-accessible
    STATUS      current
    DESCRIPTION
        "The value of tFpIxrRsEgPhType identifies the IXR FP egress resource
         type."
    ::= { tFpIxrResourceEgressPhaseEntry 2 }

tFpIxrRsEgPhSet                  OBJECT-TYPE
    SYNTAX      TmnxCardFpIxrResourceEgressSet
    MAX-ACCESS  not-accessible
    STATUS      current
    DESCRIPTION
        "The value of tFpIxrRsEgPhSet identifies the IXR FP egress resource
         set."
    ::= { tFpIxrResourceEgressPhaseEntry 3 }

tFpIxrRsEgPhPhase                OBJECT-TYPE
    SYNTAX      TmnxCardFpIxrResourceEgressPhase
    MAX-ACCESS  not-accessible
    STATUS      current
    DESCRIPTION
        "The value of tFpIxrRsEgPhPhase identifies the IXR FP egress resource
         phase."
    ::= { tFpIxrResourceEgressPhaseEntry 4 }

tFpIxrRsEgPhLinkedDataBanks      OBJECT-TYPE
    SYNTAX      Unsigned32
    MAX-ACCESS  read-only
    STATUS      current
    DESCRIPTION
        "The value of the object tFpIxrRsEgPhLinkedDataBanks indicates the
         number of Linked Data banks at Egress datapath that are allocated for
         this FP/table type/set/phase.

         Data banks that require linking are called Linked Data banks."
    ::= { tFpIxrResourceEgressPhaseEntry 5 }

tFpIxrRsEgPhLinkedDataTotal      OBJECT-TYPE
    SYNTAX      Unsigned32
    MAX-ACCESS  read-only
    STATUS      current
    DESCRIPTION
        "The value of the object tFpIxrRsEgPhLinkedDataTotal indicates the
         maximum number of Linked Data entries at Egress datapath that are
         allowed on this FP/table type/set/phase.

         Data entries that require linking are called Linked Data entries."
    ::= { tFpIxrResourceEgressPhaseEntry 6 }

tFpIxrRsEgPhLinkedDataAlloc      OBJECT-TYPE
    SYNTAX      Unsigned32
    MAX-ACCESS  read-only
    STATUS      current
    DESCRIPTION
        "The value of the object tFpIxrRsEgPhLinkedDataAlloc indicates the
         number of Linked Data entries that are currently in use on this
         FP/table type/set/phase.

         Data entries that require linking are called Linked Data entries."
    ::= { tFpIxrResourceEgressPhaseEntry 7 }

tFpIxrRsEgPhLinkedDataFree       OBJECT-TYPE
    SYNTAX      Unsigned32
    MAX-ACCESS  read-only
    STATUS      current
    DESCRIPTION
        "The value of the object tFpIxrRsEgPhLinkedDataFree indicates the
         number of free Linked Data entries that are currently available on
         this FP/table type/set/phase.

         Data entries that require linking are called Linked Data entries. Free
         entries can be claimed by various applications for further growth."
    ::= { tFpIxrResourceEgressPhaseEntry 8 }

tFpIxrRsEgPhNonLinkedDataBanks   OBJECT-TYPE
    SYNTAX      Unsigned32
    MAX-ACCESS  read-only
    STATUS      current
    DESCRIPTION
        "The value of the object tFpIxrRsEgPhNonLinkedDataBanks indicates the
         number of Non-Linked Data Banks at Egress datapath that are allocated
         for this FP/table type/set/phase.

         Data banks that do not require linking are called Non-Linked Data
         banks."
    ::= { tFpIxrResourceEgressPhaseEntry 9 }

tFpIxrRsEgPhNonLinkedDataTotal   OBJECT-TYPE
    SYNTAX      Unsigned32
    MAX-ACCESS  read-only
    STATUS      current
    DESCRIPTION
        "The value of the object tFpIxrRsEgPhNonLinkedDataTotal indicates the
         maximum number of Non-Linked Data entries at Egress datapath that are
         allowed on this FP/table type/set/phase.

         Data entries that do not require linking are called Non-Linked Data
         entries."
    ::= { tFpIxrResourceEgressPhaseEntry 10 }

tFpIxrRsEgPhNonLinkedDataAlloc   OBJECT-TYPE
    SYNTAX      Unsigned32
    MAX-ACCESS  read-only
    STATUS      current
    DESCRIPTION
        "The value of the object tFpIxrRsEgPhNonLinkedDataAlloc indicates the
         number of Non-Linked Data entries that are currently in use on this
         FP/table type/set/phase

         Data entries that do not require linking are called Non-Linked Data
         entries."
    ::= { tFpIxrResourceEgressPhaseEntry 11 }

tFpIxrRsEgPhNonLinkedDataFree    OBJECT-TYPE
    SYNTAX      Unsigned32
    MAX-ACCESS  read-only
    STATUS      current
    DESCRIPTION
        "The value of the object tFpIxrRsEgPhNonLinkedDataFree indicates the
         number of free Non Linked Data entries that are currently available on
         this FP/table type/set/phase.

         Free entries can be claimed by various applications for further
         growth.

         Data entries that do not require linking are called Non-Linked Data
         entries. Free entries can be claimed by various applications for
         further growth."
    ::= { tFpIxrResourceEgressPhaseEntry 12 }

tFpIxrRsEgPhLinkedListBanks      OBJECT-TYPE
    SYNTAX      Unsigned32
    MAX-ACCESS  read-only
    STATUS      current
    DESCRIPTION
        "The value of the object tFpIxrRsEgPhLinkedListBanks indicates the
         number of Link-List Banks at Egress datapath that are allocated for
         this FP/table type/set/phase.

         Linked List entries are used to link cluster entries of different
         phases."
    ::= { tFpIxrResourceEgressPhaseEntry 13 }

tFpIxrRsEgPhLinkedListTotal      OBJECT-TYPE
    SYNTAX      Unsigned32
    MAX-ACCESS  read-only
    STATUS      current
    DESCRIPTION
        "The value of the object tFpIxrRsEgPhLinkedListTotal indicates the
         maximum number of Linked List entries at Egress datapath that are
         allowed on this FP/table type/set/phase.

         Linked List entries are used to link cluster entries of different
         phases."
    ::= { tFpIxrResourceEgressPhaseEntry 14 }

tFpIxrRsEgPhLinkedListAlloc      OBJECT-TYPE
    SYNTAX      Unsigned32
    MAX-ACCESS  read-only
    STATUS      current
    DESCRIPTION
        "The value of the object tFpIxrRsEgPhLinkedListAlloc indicates the
         number of Linked List entries that are currently in use on this
         FP/table type/set/phase

         Linked List entries are used to link cluster entries of different
         phases."
    ::= { tFpIxrResourceEgressPhaseEntry 15 }

tFpIxrRsEgPhLinkedListFree       OBJECT-TYPE
    SYNTAX      Unsigned32
    MAX-ACCESS  read-only
    STATUS      current
    DESCRIPTION
        "The value of the object tFpIxrRsEgPhLinkedListFree indicates the
         number of free Linked List entries that are currently available on
         this FP/table type/set/phase.

         Linked List entries are used to link cluster entries of different
         phases. Free entries can be claimed by various applications for
         further growth."
    ::= { tFpIxrResourceEgressPhaseEntry 16 }

tFpIxrRsEgPhLinkedDataLifs       OBJECT-TYPE
    SYNTAX      TmnxFpIxrAvailableLifs
    MAX-ACCESS  read-only
    STATUS      current
    DESCRIPTION
        "The value of the object tFpIxrRsEgPhLinkedDataLifs indicates the
         availability of different LIF types for this FP/table type/set/phase.

         This object applies only to Cluster rows."
    ::= { tFpIxrResourceEgressPhaseEntry 17 }

tFpIxrRsEgPhNonLinkedDataLifs    OBJECT-TYPE
    SYNTAX      TmnxFpIxrAvailableLifs
    MAX-ACCESS  read-only
    STATUS      current
    DESCRIPTION
        "The value of the object tFpIxrRsEgPhNonLinkedDataLifs indicates the
         availability of different LIF types for this FP/table type/set/phase.

         This object applies only to Cluster rows."
    ::= { tFpIxrResourceEgressPhaseEntry 18 }

tmnxVirSchAdjWrkManulCntrlTable  OBJECT-TYPE
    SYNTAX      SEQUENCE OF TmnxVirSchAdjWrkManulCntrlEntry
    MAX-ACCESS  not-accessible
    STATUS      current
    DESCRIPTION
        "The tmnxVirSchAdjWrkManulCntrlTable has an entry to fine tune
         Hierarchical Quality of Service (HQoS) parameters."
    ::= { tmnxCardObjs 105 }

tmnxVirSchAdjWrkManulCntrlEntry  OBJECT-TYPE
    SYNTAX      TmnxVirSchAdjWrkManulCntrlEntry
    MAX-ACCESS  not-accessible
    STATUS      current
    DESCRIPTION
        "The tmnxVirSchAdjWrkManulCntrlEntry allows fine tune the performance
         of the particular Hierarchical Quality of Service (HQoS) parameters on
         the corresponding card. This table configures parameters controlling
         CPU limits available to individual HQoS related tasks.

         The row exists only if the associated card instance identified by
         tmnxCardSlotNum exists in the tmnxCardTable."
    INDEX       {
        tmnxChassisIndex,
        tmnxCardSlotNum,
        tmnxCardManualCntrlParameterName
    }
    ::= { tmnxVirSchAdjWrkManulCntrlTable 2 }

TmnxVirSchAdjWrkManulCntrlEntry  ::= SEQUENCE
{
    tmnxCardManualCntrlParameterName TNamedItem,
    tmnxCardManulCntrlParamRowStatus RowStatus,
    tmnxCardManulCntrlParamLastChngd TimeStamp,
    tmnxCardManualCntrlParamPrcnt    Unsigned32
}

tmnxCardManualCntrlParameterName OBJECT-TYPE
    SYNTAX      TNamedItem
    MAX-ACCESS  not-accessible
    STATUS      current
    DESCRIPTION
        "The value of tmnxCardManualCntrlParameterName defines the manual
         control parameter name."
    ::= { tmnxVirSchAdjWrkManulCntrlEntry 1 }

tmnxCardManulCntrlParamRowStatus OBJECT-TYPE
    SYNTAX      RowStatus
    MAX-ACCESS  read-create
    STATUS      current
    DESCRIPTION
        "The value of tmnxCardManulCntrlParamRowStatus specifies the row
         status. It allows the creation and deletion of user configured HQoS
         tuneable entries per parameter."
    ::= { tmnxVirSchAdjWrkManulCntrlEntry 2 }

tmnxCardManulCntrlParamLastChngd OBJECT-TYPE
    SYNTAX      TimeStamp
    MAX-ACCESS  read-only
    STATUS      current
    DESCRIPTION
        "The value of tmnxCardManulCntrlParamLastChngd indicates the time,
         since system startup, that the configuration of this HQoS tunable
         parameter entry was created or modified."
    ::= { tmnxVirSchAdjWrkManulCntrlEntry 3 }

tmnxCardManualCntrlParamPrcnt    OBJECT-TYPE
    SYNTAX      Unsigned32 (2000..10000)
    UNITS       "centipercent"
    MAX-ACCESS  read-create
    STATUS      current
    DESCRIPTION
        "The value of tmnxCardManualCntrlParamPrcnt specifies the general  or
         configuration percentage by which fine tuning of Hierarchical Quality
         of Service (HQoS) parameter is modified."
    DEFVAL      { 10000 }
    ::= { tmnxVirSchAdjWrkManulCntrlEntry 4 }

tmnxEsaHostPortDDMLaneTable      OBJECT-TYPE
    SYNTAX      SEQUENCE OF TmnxEsaHostPortDDMLaneEntry
    MAX-ACCESS  not-accessible
    STATUS      current
    DESCRIPTION
        "The tmnxEsaHostPortDDMLaneTable represents a lane on
         Extended Services Appliance (ESA) host-port  in the system and
         contains DDM information"
    ::= { tmnxCardObjs 106 }

tmnxEsaHostPortDDMLaneEntry      OBJECT-TYPE
    SYNTAX      TmnxEsaHostPortDDMLaneEntry
    MAX-ACCESS  not-accessible
    STATUS      current
    DESCRIPTION
        "Each tmnxEsaHostPortStatsEntry represents an ESA in the system and
         contains its NUMA cell information.

         Entries in this table are created and destroyed automatically by the
         system."
    INDEX       {
        tmnxEsaId,
        tmnxEsaHostPortId,
        tmnxEsaHostPortNicLaneId
    }
    ::= { tmnxEsaHostPortDDMLaneTable 1 }

TmnxEsaHostPortDDMLaneEntry      ::= SEQUENCE
{
    tmnxEsaHostPortNicLaneId         Unsigned32,
    tmnxEsaHostPortNicDDMTxBiasCurr  Integer32,
    tmnxEsaHostPortNicDDMTxOutPower  Integer32,
    tmnxEsaHostPortNicDDMRxOpPower   Integer32
}

tmnxEsaHostPortNicLaneId         OBJECT-TYPE
    SYNTAX      Unsigned32 (1..16)
    MAX-ACCESS  not-accessible
    STATUS      current
    DESCRIPTION
        "The value of tmnxEsaHostPortNicLaneId specifies the ESA Host-Port Lane
         ID for the row. The maximum ID for a given port is restricted to the
         value of tmnxEsaHostPortNicSFPNumLanes for the given port.

         For QSFP-AMP-ZR optics, lane 1 is the egress amp and lane 2 is the
         ingress amp."
    ::= { tmnxEsaHostPortDDMLaneEntry 1 }

tmnxEsaHostPortNicDDMTxBiasCurr  OBJECT-TYPE
    SYNTAX      Integer32
    MAX-ACCESS  read-only
    STATUS      current
    DESCRIPTION
        "The value of tmnxEsaHostPortNicDDMTxBiasCurr indicates the current
         Transmit Bias Current of the SFF in 1/500 milliamperes (mA).

         The formula for translating between the value of tmnxEsaHostPortNicDDMTxBiasCurr
         and milliamperes is:
            Internally Calibrated only:
                tmnxDDMTxBiasCurrent / 500

         For example (internally calibrated SFF): The SNMP value 2565 is 5.1
         milliamperes (mA)."
    REFERENCE
        "SFF Committee, SFF-8472 Specification for Diagnostic Monitoring
         Interface for Optical Transceivers, Rev 11.3, June 11, 2013"
    ::= { tmnxEsaHostPortDDMLaneEntry 2 }

tmnxEsaHostPortNicDDMTxOutPower  OBJECT-TYPE
    SYNTAX      Integer32
    MAX-ACCESS  read-only
    STATUS      current
    DESCRIPTION
        "The value of tmnxEsaHostPortNicDDMTxOutPower indicates the current
         Output Power of the SFF in one tenths of a microwatt (uW).

         For example (internally calibrated SFF):
         Using the SNMP value of 790, and using units of tenths of microwatt,
         790 becomes 79 microwatts or 0.079 milliwatts. Converting to dBm:
            10 x log10(0.079) = -11.0 dBm"
    REFERENCE
        "SFF Committee, SFF-8472 Specification for Diagnostic Monitoring
         Interface for Optical Transceivers, Rev 11.3, June 11, 2013"
    ::= { tmnxEsaHostPortDDMLaneEntry 3 }

tmnxEsaHostPortNicDDMRxOpPower   OBJECT-TYPE
    SYNTAX      Integer32
    MAX-ACCESS  read-only
    STATUS      current
    DESCRIPTION
        "The value of tmnxEsaHostPortNicDDMRxOpPower indicates the current
         Received Optical Power of the SFF in one tenths of a microwatt (uW).

         For example (internally calibrated SFF):
         Using the SNMP value of 790, and using units of tenths of microwatt,
         790 becomes 79 microwatts or 0.079 milliwatts. Converting to dBm:
            10 x log10(0.079) = -11.0 dBm"
    REFERENCE
        "SFF Committee, SFF-8472 Specification for Diagnostic Monitoring
         Interface for Optical Transceivers, Rev 11.3, June 11, 2013"
    ::= { tmnxEsaHostPortDDMLaneEntry 4 }

tmnxCardFpSarG2StatsTable        OBJECT-TYPE
    SYNTAX      SEQUENCE OF TmnxCardFpSarG2StatsEntry
    MAX-ACCESS  not-accessible
    STATUS      current
    DESCRIPTION
        "The tmnxCardFpSarG2StatsTable contains card-level datapath statistics
         specifically supported on the SAR-1, SAR-Hx and SAR-Mx platforms."
    ::= { tmnxCardObjs 107 }

tmnxCardFpSarG2StatsEntry        OBJECT-TYPE
    SYNTAX      TmnxCardFpSarG2StatsEntry
    MAX-ACCESS  not-accessible
    STATUS      current
    DESCRIPTION
        "Each tmnxCardFpSarG2StatsEntry row represents datapath statistics
         aggregated to the specified card instance."
    INDEX       {
        tmnxChassisIndex,
        tmnxCardSlotNum,
        tmnxFPNum,
        tmnxCardFpSarG2StatsType
    }
    ::= { tmnxCardFpSarG2StatsTable 1 }

TmnxCardFpSarG2StatsEntry        ::= SEQUENCE
{
    tmnxCardFpSarG2StatsType         INTEGER,
    tmnxCardFpSarG2TC0PolCntRed      Counter64,
    tmnxCardFpSarG2TC0PolCntYellow   Counter64,
    tmnxCardFpSarG2TC0PolCntGreen    Counter64,
    tmnxCardFpSarG2TC0PolCntReRed    Counter64,
    tmnxCardFpSarG2TC0PolCntReYellow Counter64,
    tmnxCardFpSarG2TC1PolCntRed      Counter64,
    tmnxCardFpSarG2TC1PolCntYellow   Counter64,
    tmnxCardFpSarG2TC1PolCntGreen    Counter64,
    tmnxCardFpSarG2TC1PolCntReRed    Counter64,
    tmnxCardFpSarG2TC1PolCntReYellow Counter64,
    tmnxCardFpSarG2TC2PolCntRed      Counter64,
    tmnxCardFpSarG2TC2PolCntYellow   Counter64,
    tmnxCardFpSarG2TC2PolCntGreen    Counter64,
    tmnxCardFpSarG2TC2PolCntReRed    Counter64,
    tmnxCardFpSarG2TC2PolCntReYellow Counter64,
    tmnxCardFpSarG2TC3PolCntRed      Counter64,
    tmnxCardFpSarG2TC3PolCntYellow   Counter64,
    tmnxCardFpSarG2TC3PolCntGreen    Counter64,
    tmnxCardFpSarG2TC3PolCntReRed    Counter64,
    tmnxCardFpSarG2TC3PolCntReYellow Counter64,
    tmnxCardFpSarG2TC4PolCntRed      Counter64,
    tmnxCardFpSarG2TC4PolCntYellow   Counter64,
    tmnxCardFpSarG2TC4PolCntGreen    Counter64,
    tmnxCardFpSarG2TC4PolCntReRed    Counter64,
    tmnxCardFpSarG2TC4PolCntReYellow Counter64,
    tmnxCardFpSarG2TC5PolCntRed      Counter64,
    tmnxCardFpSarG2TC5PolCntYellow   Counter64,
    tmnxCardFpSarG2TC5PolCntGreen    Counter64,
    tmnxCardFpSarG2TC5PolCntReRed    Counter64,
    tmnxCardFpSarG2TC5PolCntReYellow Counter64,
    tmnxCardFpSarG2TC6PolCntRed      Counter64,
    tmnxCardFpSarG2TC6PolCntYellow   Counter64,
    tmnxCardFpSarG2TC6PolCntGreen    Counter64,
    tmnxCardFpSarG2TC6PolCntReRed    Counter64,
    tmnxCardFpSarG2TC6PolCntReYellow Counter64,
    tmnxCardFpSarG2TC7PolCntRed      Counter64,
    tmnxCardFpSarG2TC7PolCntYellow   Counter64,
    tmnxCardFpSarG2TC7PolCntGreen    Counter64,
    tmnxCardFpSarG2TC7PolCntReRed    Counter64,
    tmnxCardFpSarG2TC7PolCntReYellow Counter64
}

tmnxCardFpSarG2StatsType         OBJECT-TYPE
    SYNTAX      INTEGER {
        cumulative       (1),
        sinceLastCleared (2)
    }
    MAX-ACCESS  not-accessible
    STATUS      current
    DESCRIPTION
        "The value of tmnxCardFpSarG2StatsType indicates the type of statistics
         counters represented in this entry of the tmnxCardFpSarG2StatsTable.
            cumulative(1)       - Represents statistics since last reboot.
            sinceLastCleared(2) - Represents statistics since the last clear
                                  operation by the user."
    ::= { tmnxCardFpSarG2StatsEntry 1 }

tmnxCardFpSarG2TC0PolCntRed      OBJECT-TYPE
    SYNTAX      Counter64
    MAX-ACCESS  read-only
    STATUS      current
    DESCRIPTION
        "The value of tmnxCardFpSarG2TC0PolCntRed indicates the number of
         inbound packets marked as red by traffic class 0. This indicates the
         packet has exceeded the peak information rate (PIR)."
    ::= { tmnxCardFpSarG2StatsEntry 39 }

tmnxCardFpSarG2TC0PolCntYellow   OBJECT-TYPE
    SYNTAX      Counter64
    MAX-ACCESS  read-only
    STATUS      current
    DESCRIPTION
        "The value of tmnxCardFpSarG2TC0PolCntYellow indicates the number of
         inbound packets marked as yellow by traffic class 0. This indicates
         the packet has exceeded the committed information rate (CIR)."
    ::= { tmnxCardFpSarG2StatsEntry 40 }

tmnxCardFpSarG2TC0PolCntGreen    OBJECT-TYPE
    SYNTAX      Counter64
    MAX-ACCESS  read-only
    STATUS      current
    DESCRIPTION
        "The value of tmnxCardFpSarG2TC0PolCntGreen indicates the number of
         inbound packets marked as green by traffic class 0. This indicates the
         packet is within the peak information rate (PIR) and committed
         information rate (CIR)."
    ::= { tmnxCardFpSarG2StatsEntry 41 }

tmnxCardFpSarG2TC0PolCntReRed    OBJECT-TYPE
    SYNTAX      Counter64
    MAX-ACCESS  read-only
    STATUS      current
    DESCRIPTION
        "The value of tmnxCardFpSarG2TC0PolCntReRed indicates the number of
         inbound packets reclassified as red by traffic class 0."
    ::= { tmnxCardFpSarG2StatsEntry 42 }

tmnxCardFpSarG2TC0PolCntReYellow OBJECT-TYPE
    SYNTAX      Counter64
    MAX-ACCESS  read-only
    STATUS      current
    DESCRIPTION
        "The value of tmnxCardFpSarG2TC0PolCntReYellow indicates the number of
         inbound packets reclassified as yellow by traffic class 0."
    ::= { tmnxCardFpSarG2StatsEntry 43 }

tmnxCardFpSarG2TC1PolCntRed      OBJECT-TYPE
    SYNTAX      Counter64
    MAX-ACCESS  read-only
    STATUS      current
    DESCRIPTION
        "The value of tmnxCardFpSarG2TC1PolCntRed indicates the number of
         inbound packets marked as red by traffic class 1. This indicates the
         packet has exceeded the peak information rate (PIR)."
    ::= { tmnxCardFpSarG2StatsEntry 44 }

tmnxCardFpSarG2TC1PolCntYellow   OBJECT-TYPE
    SYNTAX      Counter64
    MAX-ACCESS  read-only
    STATUS      current
    DESCRIPTION
        "The value of tmnxCardFpSarG2TC1PolCntYellow indicates the number of
         inbound packets marked as yellow by traffic class 1. This indicates
         the packet has exceeded the committed information rate (CIR)."
    ::= { tmnxCardFpSarG2StatsEntry 45 }

tmnxCardFpSarG2TC1PolCntGreen    OBJECT-TYPE
    SYNTAX      Counter64
    MAX-ACCESS  read-only
    STATUS      current
    DESCRIPTION
        "The value of tmnxCardFpSarG2TC1PolCntGreen indicates the number of
         inbound packets marked as green by traffic class 1. This indicates the
         packet is within the peak information rate (PIR) and committed
         information rate (CIR)."
    ::= { tmnxCardFpSarG2StatsEntry 46 }

tmnxCardFpSarG2TC1PolCntReRed    OBJECT-TYPE
    SYNTAX      Counter64
    MAX-ACCESS  read-only
    STATUS      current
    DESCRIPTION
        "The value of tmnxCardFpSarG2TC1PolCntReRed indicates the number of
         inbound packets reclassified as red by traffic class 1."
    ::= { tmnxCardFpSarG2StatsEntry 47 }

tmnxCardFpSarG2TC1PolCntReYellow OBJECT-TYPE
    SYNTAX      Counter64
    MAX-ACCESS  read-only
    STATUS      current
    DESCRIPTION
        "The value of tmnxCardFpSarG2TC1PolCntReYellow indicates the number of
         inbound packets reclassified as yellow by traffic class 1."
    ::= { tmnxCardFpSarG2StatsEntry 48 }

tmnxCardFpSarG2TC2PolCntRed      OBJECT-TYPE
    SYNTAX      Counter64
    MAX-ACCESS  read-only
    STATUS      current
    DESCRIPTION
        "The value of tmnxCardFpSarG2TC2PolCntRed indicates the number of
         inbound packets marked as red by traffic class 2. This indicates the
         packet has exceeded the peak information rate (PIR)."
    ::= { tmnxCardFpSarG2StatsEntry 49 }

tmnxCardFpSarG2TC2PolCntYellow   OBJECT-TYPE
    SYNTAX      Counter64
    MAX-ACCESS  read-only
    STATUS      current
    DESCRIPTION
        "The value of tmnxCardFpSarG2TC2PolCntYellow indicates the number of
         inbound packets marked as yellow by traffic class 2. This indicates
         the packet has exceeded the committed information rate (CIR)."
    ::= { tmnxCardFpSarG2StatsEntry 50 }

tmnxCardFpSarG2TC2PolCntGreen    OBJECT-TYPE
    SYNTAX      Counter64
    MAX-ACCESS  read-only
    STATUS      current
    DESCRIPTION
        "The value of tmnxCardFpSarG2TC2PolCntGreen indicates the number of
         inbound packets marked as green by traffic class 2. This indicates the
         packet is within the peak information rate (PIR) and committed
         information rate (CIR)."
    ::= { tmnxCardFpSarG2StatsEntry 51 }

tmnxCardFpSarG2TC2PolCntReRed    OBJECT-TYPE
    SYNTAX      Counter64
    MAX-ACCESS  read-only
    STATUS      current
    DESCRIPTION
        "The value of tmnxCardFpSarG2TC2PolCntReRed indicates the number of
         inbound packets reclassified as red by traffic class 2."
    ::= { tmnxCardFpSarG2StatsEntry 52 }

tmnxCardFpSarG2TC2PolCntReYellow OBJECT-TYPE
    SYNTAX      Counter64
    MAX-ACCESS  read-only
    STATUS      current
    DESCRIPTION
        "The value of tmnxCardFpSarG2TC2PolCntReYellow indicates the number of
         inbound packets reclassified as yellow by traffic class 2."
    ::= { tmnxCardFpSarG2StatsEntry 53 }

tmnxCardFpSarG2TC3PolCntRed      OBJECT-TYPE
    SYNTAX      Counter64
    MAX-ACCESS  read-only
    STATUS      current
    DESCRIPTION
        "The value of tmnxCardFpSarG2TC3PolCntRed indicates the number of
         inbound packets marked as red by traffic class 3. This indicates the
         packet has exceeded the peak information rate (PIR)."
    ::= { tmnxCardFpSarG2StatsEntry 54 }

tmnxCardFpSarG2TC3PolCntYellow   OBJECT-TYPE
    SYNTAX      Counter64
    MAX-ACCESS  read-only
    STATUS      current
    DESCRIPTION
        "The value of tmnxCardFpSarG2TC3PolCntYellow indicates the number of
         inbound packets marked as yellow by traffic class 3. This indicates
         the packet has exceeded the committed information rate (CIR)."
    ::= { tmnxCardFpSarG2StatsEntry 55 }

tmnxCardFpSarG2TC3PolCntGreen    OBJECT-TYPE
    SYNTAX      Counter64
    MAX-ACCESS  read-only
    STATUS      current
    DESCRIPTION
        "The value of tmnxCardFpSarG2TC3PolCntGreen indicates the number of
         inbound packets marked as green by traffic class 3. This indicates the
         packet is within the peak information rate (PIR) and committed
         information rate (CIR)."
    ::= { tmnxCardFpSarG2StatsEntry 56 }

tmnxCardFpSarG2TC3PolCntReRed    OBJECT-TYPE
    SYNTAX      Counter64
    MAX-ACCESS  read-only
    STATUS      current
    DESCRIPTION
        "The value of tmnxCardFpSarG2TC3PolCntReRed indicates the number of
         inbound packets reclassified as red by traffic class 3."
    ::= { tmnxCardFpSarG2StatsEntry 57 }

tmnxCardFpSarG2TC3PolCntReYellow OBJECT-TYPE
    SYNTAX      Counter64
    MAX-ACCESS  read-only
    STATUS      current
    DESCRIPTION
        "The value of tmnxCardFpSarG2TC3PolCntReYellow indicates the number of
         inbound packets reclassified as yellow by traffic class 3."
    ::= { tmnxCardFpSarG2StatsEntry 58 }

tmnxCardFpSarG2TC4PolCntRed      OBJECT-TYPE
    SYNTAX      Counter64
    MAX-ACCESS  read-only
    STATUS      current
    DESCRIPTION
        "The value of tmnxCardFpSarG2TC4PolCntRed indicates the number of
         inbound packets marked as red by traffic class 4. This indicates the
         packet has exceeded the peak information rate (PIR)."
    ::= { tmnxCardFpSarG2StatsEntry 59 }

tmnxCardFpSarG2TC4PolCntYellow   OBJECT-TYPE
    SYNTAX      Counter64
    MAX-ACCESS  read-only
    STATUS      current
    DESCRIPTION
        "The value of tmnxCardFpSarG2TC4PolCntYellow indicates the number of
         inbound packets marked as yellow by traffic class 4. This indicates
         the packet has exceeded the committed information rate (CIR)."
    ::= { tmnxCardFpSarG2StatsEntry 60 }

tmnxCardFpSarG2TC4PolCntGreen    OBJECT-TYPE
    SYNTAX      Counter64
    MAX-ACCESS  read-only
    STATUS      current
    DESCRIPTION
        "The value of tmnxCardFpSarG2TC4PolCntGreen indicates the number of
         inbound packets marked as green by traffic class 4. This indicates the
         packet is within the peak information rate (PIR) and committed
         information rate (CIR)."
    ::= { tmnxCardFpSarG2StatsEntry 61 }

tmnxCardFpSarG2TC4PolCntReRed    OBJECT-TYPE
    SYNTAX      Counter64
    MAX-ACCESS  read-only
    STATUS      current
    DESCRIPTION
        "The value of tmnxCardFpSarG2TC4PolCntReRed indicates the number of
         inbound packets reclassified as red by traffic class 4."
    ::= { tmnxCardFpSarG2StatsEntry 62 }

tmnxCardFpSarG2TC4PolCntReYellow OBJECT-TYPE
    SYNTAX      Counter64
    MAX-ACCESS  read-only
    STATUS      current
    DESCRIPTION
        "The value of tmnxCardFpSarG2TC4PolCntReYellow indicates the number of
         inbound packets reclassified as yellow by traffic class 4."
    ::= { tmnxCardFpSarG2StatsEntry 63 }

tmnxCardFpSarG2TC5PolCntRed      OBJECT-TYPE
    SYNTAX      Counter64
    MAX-ACCESS  read-only
    STATUS      current
    DESCRIPTION
        "The value of tmnxCardFpSarG2TC5PolCntRed indicates the number of
         inbound packets marked as red by traffic class 5. This indicates the
         packet has exceeded the peak information rate (PIR)."
    ::= { tmnxCardFpSarG2StatsEntry 64 }

tmnxCardFpSarG2TC5PolCntYellow   OBJECT-TYPE
    SYNTAX      Counter64
    MAX-ACCESS  read-only
    STATUS      current
    DESCRIPTION
        "The value of tmnxCardFpSarG2TC5PolCntYellow indicates the number of
         inbound packets marked as yellow by traffic class 5. This indicates
         the packet has exceeded the committed information rate (CIR)."
    ::= { tmnxCardFpSarG2StatsEntry 65 }

tmnxCardFpSarG2TC5PolCntGreen    OBJECT-TYPE
    SYNTAX      Counter64
    MAX-ACCESS  read-only
    STATUS      current
    DESCRIPTION
        "The value of tmnxCardFpSarG2TC5PolCntGreen indicates the number of
         inbound packets marked as green by traffic class 5. This indicates the
         packet is within the peak information rate (PIR) and committed
         information rate (CIR)."
    ::= { tmnxCardFpSarG2StatsEntry 66 }

tmnxCardFpSarG2TC5PolCntReRed    OBJECT-TYPE
    SYNTAX      Counter64
    MAX-ACCESS  read-only
    STATUS      current
    DESCRIPTION
        "The value of tmnxCardFpSarG2TC5PolCntReRed indicates the number of
         inbound packets reclassified as red by traffic class 5."
    ::= { tmnxCardFpSarG2StatsEntry 67 }

tmnxCardFpSarG2TC5PolCntReYellow OBJECT-TYPE
    SYNTAX      Counter64
    MAX-ACCESS  read-only
    STATUS      current
    DESCRIPTION
        "The value of tmnxCardFpSarG2TC5PolCntReYellow indicates the number of
         inbound packets reclassified as yellow by traffic class 5."
    ::= { tmnxCardFpSarG2StatsEntry 68 }

tmnxCardFpSarG2TC6PolCntRed      OBJECT-TYPE
    SYNTAX      Counter64
    MAX-ACCESS  read-only
    STATUS      current
    DESCRIPTION
        "The value of tmnxCardFpSarG2TC6PolCntRed indicates the number of
         inbound packets marked as red by traffic class 6. This indicates the
         packet has exceeded the peak information rate (PIR)."
    ::= { tmnxCardFpSarG2StatsEntry 69 }

tmnxCardFpSarG2TC6PolCntYellow   OBJECT-TYPE
    SYNTAX      Counter64
    MAX-ACCESS  read-only
    STATUS      current
    DESCRIPTION
        "The value of tmnxCardFpSarG2TC6PolCntYellow indicates the number of
         inbound packets marked as yellow by traffic class 6. This indicates
         the packet has exceeded the committed information rate (CIR)."
    ::= { tmnxCardFpSarG2StatsEntry 70 }

tmnxCardFpSarG2TC6PolCntGreen    OBJECT-TYPE
    SYNTAX      Counter64
    MAX-ACCESS  read-only
    STATUS      current
    DESCRIPTION
        "The value of tmnxCardFpSarG2TC6PolCntGreen indicates the number of
         inbound packets marked as green by traffic class 6. This indicates the
         packet is within the peak information rate (PIR) and committed
         information rate (CIR)."
    ::= { tmnxCardFpSarG2StatsEntry 71 }

tmnxCardFpSarG2TC6PolCntReRed    OBJECT-TYPE
    SYNTAX      Counter64
    MAX-ACCESS  read-only
    STATUS      current
    DESCRIPTION
        "The value of tmnxCardFpSarG2TC6PolCntReRed indicates the number of
         inbound packets reclassified as red by traffic class 6."
    ::= { tmnxCardFpSarG2StatsEntry 72 }

tmnxCardFpSarG2TC6PolCntReYellow OBJECT-TYPE
    SYNTAX      Counter64
    MAX-ACCESS  read-only
    STATUS      current
    DESCRIPTION
        "The value of tmnxCardFpSarG2TC6PolCntReYellow indicates the number of
         inbound packets reclassified as yellow by traffic class 6."
    ::= { tmnxCardFpSarG2StatsEntry 73 }

tmnxCardFpSarG2TC7PolCntRed      OBJECT-TYPE
    SYNTAX      Counter64
    MAX-ACCESS  read-only
    STATUS      current
    DESCRIPTION
        "The value of tmnxCardFpSarG2TC7PolCntRed indicates the number of
         inbound packets marked as red by traffic class 7. This indicates the
         packet has exceeded the peak information rate (PIR)."
    ::= { tmnxCardFpSarG2StatsEntry 74 }

tmnxCardFpSarG2TC7PolCntYellow   OBJECT-TYPE
    SYNTAX      Counter64
    MAX-ACCESS  read-only
    STATUS      current
    DESCRIPTION
        "The value of tmnxCardFpSarG2TC7PolCntYellow indicates the number of
         inbound packets marked as yellow by traffic class 7. This indicates
         the packet has exceeded the committed information rate (CIR)."
    ::= { tmnxCardFpSarG2StatsEntry 75 }

tmnxCardFpSarG2TC7PolCntGreen    OBJECT-TYPE
    SYNTAX      Counter64
    MAX-ACCESS  read-only
    STATUS      current
    DESCRIPTION
        "The value of tmnxCardFpSarG2TC7PolCntGreen indicates the number of
         inbound packets marked as green by traffic class 7. This indicates the
         packet is within the peak information rate (PIR) and committed
         information rate (CIR)."
    ::= { tmnxCardFpSarG2StatsEntry 76 }

tmnxCardFpSarG2TC7PolCntReRed    OBJECT-TYPE
    SYNTAX      Counter64
    MAX-ACCESS  read-only
    STATUS      current
    DESCRIPTION
        "The value of tmnxCardFpSarG2TC7PolCntReRed indicates the number of
         inbound packets reclassified as red by traffic class 7."
    ::= { tmnxCardFpSarG2StatsEntry 77 }

tmnxCardFpSarG2TC7PolCntReYellow OBJECT-TYPE
    SYNTAX      Counter64
    MAX-ACCESS  read-only
    STATUS      current
    DESCRIPTION
        "The value of tmnxCardFpSarG2TC7PolCntReYellow indicates the number of
         inbound packets reclassified as yellow by traffic class 7."
    ::= { tmnxCardFpSarG2StatsEntry 78 }

tmnxMdaFpSarG2StatsTable         OBJECT-TYPE
    SYNTAX      SEQUENCE OF TmnxMdaFpSarG2StatsEntry
    MAX-ACCESS  not-accessible
    STATUS      current
    DESCRIPTION
        "The tmnxMdaFpSarG2StatsTable contains MDA-level datapath statistics
         specifically supported on the SAR-1, SAR-Hx and SAR-Mx platforms."
    ::= { tmnxCardObjs 108 }

tmnxMdaFpSarG2StatsEntry         OBJECT-TYPE
    SYNTAX      TmnxMdaFpSarG2StatsEntry
    MAX-ACCESS  not-accessible
    STATUS      current
    DESCRIPTION
        "Each tmnxMdaFpSarG2StatsEntry row represents datapath statistics
         aggregated to the specified MDA instance."
    INDEX       {
        tmnxChassisIndex,
        tmnxCardSlotNum,
        tmnxMDASlotNum,
        tmnxFPNum,
        tmnxMdaFpSarG2StatsType
    }
    ::= { tmnxMdaFpSarG2StatsTable 1 }

TmnxMdaFpSarG2StatsEntry         ::= SEQUENCE
{
    tmnxMdaFpSarG2StatsType          INTEGER,
    tmnxMdaFpSarG2TC0PolCntRed       Counter64,
    tmnxMdaFpSarG2TC0PolCntYellow    Counter64,
    tmnxMdaFpSarG2TC0PolCntGreen     Counter64,
    tmnxMdaFpSarG2TC0PolCntReRed     Counter64,
    tmnxMdaFpSarG2TC0PolCntReYellow  Counter64,
    tmnxMdaFpSarG2TC1PolCntRed       Counter64,
    tmnxMdaFpSarG2TC1PolCntYellow    Counter64,
    tmnxMdaFpSarG2TC1PolCntGreen     Counter64,
    tmnxMdaFpSarG2TC1PolCntReRed     Counter64,
    tmnxMdaFpSarG2TC1PolCntReYellow  Counter64,
    tmnxMdaFpSarG2TC2PolCntRed       Counter64,
    tmnxMdaFpSarG2TC2PolCntYellow    Counter64,
    tmnxMdaFpSarG2TC2PolCntGreen     Counter64,
    tmnxMdaFpSarG2TC2PolCntReRed     Counter64,
    tmnxMdaFpSarG2TC2PolCntReYellow  Counter64,
    tmnxMdaFpSarG2TC3PolCntRed       Counter64,
    tmnxMdaFpSarG2TC3PolCntYellow    Counter64,
    tmnxMdaFpSarG2TC3PolCntGreen     Counter64,
    tmnxMdaFpSarG2TC3PolCntReRed     Counter64,
    tmnxMdaFpSarG2TC3PolCntReYellow  Counter64,
    tmnxMdaFpSarG2TC4PolCntRed       Counter64,
    tmnxMdaFpSarG2TC4PolCntYellow    Counter64,
    tmnxMdaFpSarG2TC4PolCntGreen     Counter64,
    tmnxMdaFpSarG2TC4PolCntReRed     Counter64,
    tmnxMdaFpSarG2TC4PolCntReYellow  Counter64,
    tmnxMdaFpSarG2TC5PolCntRed       Counter64,
    tmnxMdaFpSarG2TC5PolCntYellow    Counter64,
    tmnxMdaFpSarG2TC5PolCntGreen     Counter64,
    tmnxMdaFpSarG2TC5PolCntReRed     Counter64,
    tmnxMdaFpSarG2TC5PolCntReYellow  Counter64,
    tmnxMdaFpSarG2TC6PolCntRed       Counter64,
    tmnxMdaFpSarG2TC6PolCntYellow    Counter64,
    tmnxMdaFpSarG2TC6PolCntGreen     Counter64,
    tmnxMdaFpSarG2TC6PolCntReRed     Counter64,
    tmnxMdaFpSarG2TC6PolCntReYellow  Counter64,
    tmnxMdaFpSarG2TC7PolCntRed       Counter64,
    tmnxMdaFpSarG2TC7PolCntYellow    Counter64,
    tmnxMdaFpSarG2TC7PolCntGreen     Counter64,
    tmnxMdaFpSarG2TC7PolCntReRed     Counter64,
    tmnxMdaFpSarG2TC7PolCntReYellow  Counter64
}

tmnxMdaFpSarG2StatsType          OBJECT-TYPE
    SYNTAX      INTEGER {
        cumulative       (1),
        sinceLastCleared (2)
    }
    MAX-ACCESS  not-accessible
    STATUS      current
    DESCRIPTION
        "The value of tmnxMdaFpSarG2StatsType indicates the type of statistics
         counters represented in this entry of the tmnxMdaFpSarG2StatsTable.
            cumulative(1)       - Represents statistics since last reboot.
            sinceLastCleared(2) - Represents statistics since the last clear
                                  operation by the user."
    ::= { tmnxMdaFpSarG2StatsEntry 1 }

tmnxMdaFpSarG2TC0PolCntRed       OBJECT-TYPE
    SYNTAX      Counter64
    MAX-ACCESS  read-only
    STATUS      current
    DESCRIPTION
        "The value of tmnxMdaFpSarG2TC0PolCntRed indicates the number of
         inbound packets marked as red by traffic class 0. This indicates the
         packet has exceeded the peak information rate (PIR)."
    ::= { tmnxMdaFpSarG2StatsEntry 39 }

tmnxMdaFpSarG2TC0PolCntYellow    OBJECT-TYPE
    SYNTAX      Counter64
    MAX-ACCESS  read-only
    STATUS      current
    DESCRIPTION
        "The value of tmnxMdaFpSarG2TC0PolCntYellow indicates the number of
         inbound packets marked as yellow by traffic class 0. This indicates
         the packet has exceeded the committed information rate (CIR)."
    ::= { tmnxMdaFpSarG2StatsEntry 40 }

tmnxMdaFpSarG2TC0PolCntGreen     OBJECT-TYPE
    SYNTAX      Counter64
    MAX-ACCESS  read-only
    STATUS      current
    DESCRIPTION
        "The value of tmnxMdaFpSarG2TC0PolCntGreen indicates the number of
         inbound packets marked as green by traffic class 0. This indicates the
         packet is within the peak information rate (PIR) and committed
         information rate (CIR)."
    ::= { tmnxMdaFpSarG2StatsEntry 41 }

tmnxMdaFpSarG2TC0PolCntReRed     OBJECT-TYPE
    SYNTAX      Counter64
    MAX-ACCESS  read-only
    STATUS      current
    DESCRIPTION
        "The value of tmnxMdaFpSarG2TC0PolCntReRed indicates the number of
         inbound packets reclassified as red by traffic class 0."
    ::= { tmnxMdaFpSarG2StatsEntry 42 }

tmnxMdaFpSarG2TC0PolCntReYellow  OBJECT-TYPE
    SYNTAX      Counter64
    MAX-ACCESS  read-only
    STATUS      current
    DESCRIPTION
        "The value of tmnxMdaFpSarG2TC0PolCntReYellow indicates the number of
         inbound packets reclassified as yellow by traffic class 0."
    ::= { tmnxMdaFpSarG2StatsEntry 43 }

tmnxMdaFpSarG2TC1PolCntRed       OBJECT-TYPE
    SYNTAX      Counter64
    MAX-ACCESS  read-only
    STATUS      current
    DESCRIPTION
        "The value of tmnxMdaFpSarG2TC1PolCntRed indicates the number of
         inbound packets marked as red by traffic class 1. This indicates the
         packet has exceeded the peak information rate (PIR)."
    ::= { tmnxMdaFpSarG2StatsEntry 44 }

tmnxMdaFpSarG2TC1PolCntYellow    OBJECT-TYPE
    SYNTAX      Counter64
    MAX-ACCESS  read-only
    STATUS      current
    DESCRIPTION
        "The value of tmnxMdaFpSarG2TC1PolCntYellow indicates the number of
         inbound packets marked as yellow by traffic class 1. This indicates
         the packet has exceeded the committed information rate (CIR)."
    ::= { tmnxMdaFpSarG2StatsEntry 45 }

tmnxMdaFpSarG2TC1PolCntGreen     OBJECT-TYPE
    SYNTAX      Counter64
    MAX-ACCESS  read-only
    STATUS      current
    DESCRIPTION
        "The value of tmnxMdaFpSarG2TC1PolCntGreen indicates the number of
         inbound packets marked as green by traffic class 1. This indicates the
         packet is within the peak information rate (PIR) and committed
         information rate (CIR)."
    ::= { tmnxMdaFpSarG2StatsEntry 46 }

tmnxMdaFpSarG2TC1PolCntReRed     OBJECT-TYPE
    SYNTAX      Counter64
    MAX-ACCESS  read-only
    STATUS      current
    DESCRIPTION
        "The value of tmnxMdaFpSarG2TC1PolCntReRed indicates the number of
         inbound packets reclassified as red by traffic class 1."
    ::= { tmnxMdaFpSarG2StatsEntry 47 }

tmnxMdaFpSarG2TC1PolCntReYellow  OBJECT-TYPE
    SYNTAX      Counter64
    MAX-ACCESS  read-only
    STATUS      current
    DESCRIPTION
        "The value of tmnxMdaFpSarG2TC1PolCntReYellow indicates the number of
         inbound packets reclassified as yellow by traffic class 1."
    ::= { tmnxMdaFpSarG2StatsEntry 48 }

tmnxMdaFpSarG2TC2PolCntRed       OBJECT-TYPE
    SYNTAX      Counter64
    MAX-ACCESS  read-only
    STATUS      current
    DESCRIPTION
        "The value of tmnxMdaFpSarG2TC2PolCntRed indicates the number of
         inbound packets marked as red by traffic class 2. This indicates the
         packet has exceeded the peak information rate (PIR)."
    ::= { tmnxMdaFpSarG2StatsEntry 49 }

tmnxMdaFpSarG2TC2PolCntYellow    OBJECT-TYPE
    SYNTAX      Counter64
    MAX-ACCESS  read-only
    STATUS      current
    DESCRIPTION
        "The value of tmnxMdaFpSarG2TC2PolCntYellow indicates the number of
         inbound packets marked as yellow by traffic class 2. This indicates
         the packet has exceeded the committed information rate (CIR)."
    ::= { tmnxMdaFpSarG2StatsEntry 50 }

tmnxMdaFpSarG2TC2PolCntGreen     OBJECT-TYPE
    SYNTAX      Counter64
    MAX-ACCESS  read-only
    STATUS      current
    DESCRIPTION
        "The value of tmnxMdaFpSarG2TC2PolCntGreen indicates the number of
         inbound packets marked as green by traffic class 2. This indicates the
         packet is within the peak information rate (PIR) and committed
         information rate (CIR)."
    ::= { tmnxMdaFpSarG2StatsEntry 51 }

tmnxMdaFpSarG2TC2PolCntReRed     OBJECT-TYPE
    SYNTAX      Counter64
    MAX-ACCESS  read-only
    STATUS      current
    DESCRIPTION
        "The value of tmnxMdaFpSarG2TC2PolCntReRed indicates the number of
         inbound packets reclassified as red by traffic class 2."
    ::= { tmnxMdaFpSarG2StatsEntry 52 }

tmnxMdaFpSarG2TC2PolCntReYellow  OBJECT-TYPE
    SYNTAX      Counter64
    MAX-ACCESS  read-only
    STATUS      current
    DESCRIPTION
        "The value of tmnxMdaFpSarG2TC2PolCntReYellow indicates the number of
         inbound packets reclassified as yellow by traffic class 2."
    ::= { tmnxMdaFpSarG2StatsEntry 53 }

tmnxMdaFpSarG2TC3PolCntRed       OBJECT-TYPE
    SYNTAX      Counter64
    MAX-ACCESS  read-only
    STATUS      current
    DESCRIPTION
        "The value of tmnxMdaFpSarG2TC3PolCntRed indicates the number of
         inbound packets marked as red by traffic class 3. This indicates the
         packet has exceeded the peak information rate (PIR)."
    ::= { tmnxMdaFpSarG2StatsEntry 54 }

tmnxMdaFpSarG2TC3PolCntYellow    OBJECT-TYPE
    SYNTAX      Counter64
    MAX-ACCESS  read-only
    STATUS      current
    DESCRIPTION
        "The value of tmnxMdaFpSarG2TC3PolCntYellow indicates the number of
         inbound packets marked as yellow by traffic class 3. This indicates
         the packet has exceeded the committed information rate (CIR)."
    ::= { tmnxMdaFpSarG2StatsEntry 55 }

tmnxMdaFpSarG2TC3PolCntGreen     OBJECT-TYPE
    SYNTAX      Counter64
    MAX-ACCESS  read-only
    STATUS      current
    DESCRIPTION
        "The value of tmnxMdaFpSarG2TC3PolCntGreen indicates the number of
         inbound packets marked as green by traffic class 3. This indicates the
         packet is within the peak information rate (PIR) and committed
         information rate (CIR)."
    ::= { tmnxMdaFpSarG2StatsEntry 56 }

tmnxMdaFpSarG2TC3PolCntReRed     OBJECT-TYPE
    SYNTAX      Counter64
    MAX-ACCESS  read-only
    STATUS      current
    DESCRIPTION
        "The value of tmnxMdaFpSarG2TC3PolCntReRed indicates the number of
         inbound packets reclassified as red by traffic class 3."
    ::= { tmnxMdaFpSarG2StatsEntry 57 }

tmnxMdaFpSarG2TC3PolCntReYellow  OBJECT-TYPE
    SYNTAX      Counter64
    MAX-ACCESS  read-only
    STATUS      current
    DESCRIPTION
        "The value of tmnxMdaFpSarG2TC3PolCntReYellow indicates the number of
         inbound packets reclassified as yellow by traffic class 3."
    ::= { tmnxMdaFpSarG2StatsEntry 58 }

tmnxMdaFpSarG2TC4PolCntRed       OBJECT-TYPE
    SYNTAX      Counter64
    MAX-ACCESS  read-only
    STATUS      current
    DESCRIPTION
        "The value of tmnxMdaFpSarG2TC4PolCntRed indicates the number of
         inbound packets marked as red by traffic class 4. This indicates the
         packet has exceeded the peak information rate (PIR)."
    ::= { tmnxMdaFpSarG2StatsEntry 59 }

tmnxMdaFpSarG2TC4PolCntYellow    OBJECT-TYPE
    SYNTAX      Counter64
    MAX-ACCESS  read-only
    STATUS      current
    DESCRIPTION
        "The value of tmnxMdaFpSarG2TC4PolCntYellow indicates the number of
         inbound packets marked as yellow by traffic class 4. This indicates
         the packet has exceeded the committed information rate (CIR)."
    ::= { tmnxMdaFpSarG2StatsEntry 60 }

tmnxMdaFpSarG2TC4PolCntGreen     OBJECT-TYPE
    SYNTAX      Counter64
    MAX-ACCESS  read-only
    STATUS      current
    DESCRIPTION
        "The value of tmnxMdaFpSarG2TC4PolCntGreen indicates the number of
         inbound packets marked as green by traffic class 4. This indicates the
         packet is within the peak information rate (PIR) and committed
         information rate (CIR)."
    ::= { tmnxMdaFpSarG2StatsEntry 61 }

tmnxMdaFpSarG2TC4PolCntReRed     OBJECT-TYPE
    SYNTAX      Counter64
    MAX-ACCESS  read-only
    STATUS      current
    DESCRIPTION
        "The value of tmnxMdaFpSarG2TC4PolCntReRed indicates the number of
         inbound packets reclassified as red by traffic class 4."
    ::= { tmnxMdaFpSarG2StatsEntry 62 }

tmnxMdaFpSarG2TC4PolCntReYellow  OBJECT-TYPE
    SYNTAX      Counter64
    MAX-ACCESS  read-only
    STATUS      current
    DESCRIPTION
        "The value of tmnxMdaFpSarG2TC4PolCntReYellow indicates the number of
         inbound packets reclassified as yellow by traffic class 4."
    ::= { tmnxMdaFpSarG2StatsEntry 63 }

tmnxMdaFpSarG2TC5PolCntRed       OBJECT-TYPE
    SYNTAX      Counter64
    MAX-ACCESS  read-only
    STATUS      current
    DESCRIPTION
        "The value of tmnxMdaFpSarG2TC5PolCntRed indicates the number of
         inbound packets marked as red by traffic class 5. This indicates the
         packet has exceeded the peak information rate (PIR)."
    ::= { tmnxMdaFpSarG2StatsEntry 64 }

tmnxMdaFpSarG2TC5PolCntYellow    OBJECT-TYPE
    SYNTAX      Counter64
    MAX-ACCESS  read-only
    STATUS      current
    DESCRIPTION
        "The value of tmnxMdaFpSarG2TC5PolCntYellow indicates the number of
         inbound packets marked as yellow by traffic class 5. This indicates
         the packet has exceeded the committed information rate (CIR)."
    ::= { tmnxMdaFpSarG2StatsEntry 65 }

tmnxMdaFpSarG2TC5PolCntGreen     OBJECT-TYPE
    SYNTAX      Counter64
    MAX-ACCESS  read-only
    STATUS      current
    DESCRIPTION
        "The value of tmnxMdaFpSarG2TC5PolCntGreen indicates the number of
         inbound packets marked as green by traffic class 5. This indicates the
         packet is within the peak information rate (PIR) and committed
         information rate (CIR)."
    ::= { tmnxMdaFpSarG2StatsEntry 66 }

tmnxMdaFpSarG2TC5PolCntReRed     OBJECT-TYPE
    SYNTAX      Counter64
    MAX-ACCESS  read-only
    STATUS      current
    DESCRIPTION
        "The value of tmnxMdaFpSarG2TC5PolCntReRed indicates the number of
         inbound packets reclassified as red by traffic class 5."
    ::= { tmnxMdaFpSarG2StatsEntry 67 }

tmnxMdaFpSarG2TC5PolCntReYellow  OBJECT-TYPE
    SYNTAX      Counter64
    MAX-ACCESS  read-only
    STATUS      current
    DESCRIPTION
        "The value of tmnxMdaFpSarG2TC5PolCntReYellow indicates the number of
         inbound packets reclassified as yellow by traffic class 5."
    ::= { tmnxMdaFpSarG2StatsEntry 68 }

tmnxMdaFpSarG2TC6PolCntRed       OBJECT-TYPE
    SYNTAX      Counter64
    MAX-ACCESS  read-only
    STATUS      current
    DESCRIPTION
        "The value of tmnxMdaFpSarG2TC6PolCntRed indicates the number of
         inbound packets marked as red by traffic class 6. This indicates the
         packet has exceeded the peak information rate (PIR)."
    ::= { tmnxMdaFpSarG2StatsEntry 69 }

tmnxMdaFpSarG2TC6PolCntYellow    OBJECT-TYPE
    SYNTAX      Counter64
    MAX-ACCESS  read-only
    STATUS      current
    DESCRIPTION
        "The value of tmnxMdaFpSarG2TC6PolCntYellow indicates the number of
         inbound packets marked as yellow by traffic class 6. This indicates
         the packet has exceeded the committed information rate (CIR)."
    ::= { tmnxMdaFpSarG2StatsEntry 70 }

tmnxMdaFpSarG2TC6PolCntGreen     OBJECT-TYPE
    SYNTAX      Counter64
    MAX-ACCESS  read-only
    STATUS      current
    DESCRIPTION
        "The value of tmnxMdaFpSarG2TC6PolCntGreen indicates the number of
         inbound packets marked as green by traffic class 6. This indicates the
         packet is within the peak information rate (PIR) and committed
         information rate (CIR)."
    ::= { tmnxMdaFpSarG2StatsEntry 71 }

tmnxMdaFpSarG2TC6PolCntReRed     OBJECT-TYPE
    SYNTAX      Counter64
    MAX-ACCESS  read-only
    STATUS      current
    DESCRIPTION
        "The value of tmnxMdaFpSarG2TC6PolCntReRed indicates the number of
         inbound packets reclassified as red by traffic class 6."
    ::= { tmnxMdaFpSarG2StatsEntry 72 }

tmnxMdaFpSarG2TC6PolCntReYellow  OBJECT-TYPE
    SYNTAX      Counter64
    MAX-ACCESS  read-only
    STATUS      current
    DESCRIPTION
        "The value of tmnxMdaFpSarG2TC6PolCntReYellow indicates the number of
         inbound packets reclassified as yellow by traffic class 6."
    ::= { tmnxMdaFpSarG2StatsEntry 73 }

tmnxMdaFpSarG2TC7PolCntRed       OBJECT-TYPE
    SYNTAX      Counter64
    MAX-ACCESS  read-only
    STATUS      current
    DESCRIPTION
        "The value of tmnxMdaFpSarG2TC7PolCntRed indicates the number of
         inbound packets marked as red by traffic class 7. This indicates the
         packet has exceeded the peak information rate (PIR)."
    ::= { tmnxMdaFpSarG2StatsEntry 74 }

tmnxMdaFpSarG2TC7PolCntYellow    OBJECT-TYPE
    SYNTAX      Counter64
    MAX-ACCESS  read-only
    STATUS      current
    DESCRIPTION
        "The value of tmnxMdaFpSarG2TC7PolCntYellow indicates the number of
         inbound packets marked as yellow by traffic class 7. This indicates
         the packet has exceeded the committed information rate (CIR)."
    ::= { tmnxMdaFpSarG2StatsEntry 75 }

tmnxMdaFpSarG2TC7PolCntGreen     OBJECT-TYPE
    SYNTAX      Counter64
    MAX-ACCESS  read-only
    STATUS      current
    DESCRIPTION
        "The value of tmnxMdaFpSarG2TC7PolCntGreen indicates the number of
         inbound packets marked as green by traffic class 7. This indicates the
         packet is within the peak information rate (PIR) and committed
         information rate (CIR)."
    ::= { tmnxMdaFpSarG2StatsEntry 76 }

tmnxMdaFpSarG2TC7PolCntReRed     OBJECT-TYPE
    SYNTAX      Counter64
    MAX-ACCESS  read-only
    STATUS      current
    DESCRIPTION
        "The value of tmnxMdaFpSarG2TC7PolCntReRed indicates the number of
         inbound packets reclassified as red by traffic class 7."
    ::= { tmnxMdaFpSarG2StatsEntry 77 }

tmnxMdaFpSarG2TC7PolCntReYellow  OBJECT-TYPE
    SYNTAX      Counter64
    MAX-ACCESS  read-only
    STATUS      current
    DESCRIPTION
        "The value of tmnxMdaFpSarG2TC7PolCntReYellow indicates the number of
         inbound packets reclassified as yellow by traffic class 7."
    ::= { tmnxMdaFpSarG2StatsEntry 78 }

tmnxChassisNotificationObjects   OBJECT IDENTIFIER ::= { tmnxHwObjs 6 }

tmnxEqNotificationRow            OBJECT-TYPE
    SYNTAX      RowPointer
    MAX-ACCESS  accessible-for-notify
    STATUS      current
    DESCRIPTION
        "used by tmnx chassis Notifications, the OID indicates the table and
         entry."
    ::= { tmnxChassisNotificationObjects 1 }

tmnxEqTypeNotificationRow        OBJECT-TYPE
    SYNTAX      RowPointer
    MAX-ACCESS  accessible-for-notify
    STATUS      current
    DESCRIPTION
        "used by tmnx chassis notifications, the OID indicates the table and
         entry with the equipment model type information."
    ::= { tmnxChassisNotificationObjects 2 }

tmnxChassisNotifyChassisId       OBJECT-TYPE
    SYNTAX      TmnxChassisIndex
    MAX-ACCESS  accessible-for-notify
    STATUS      current
    DESCRIPTION
        "Used by tmnx chassis and port Notifications, indicates the chassis
         associated with the alarm."
    ::= { tmnxChassisNotificationObjects 3 }

tmnxChassisNotifyHwIndex         OBJECT-TYPE
    SYNTAX      TmnxHwIndex
    MAX-ACCESS  accessible-for-notify
    STATUS      current
    DESCRIPTION
        "Used by tmnx chassis and port Notifications, indicates the entry in
         the tmnxHwTable for the hardware component associated with an alarm."
    ::= { tmnxChassisNotificationObjects 4 }

tmnxRedSecondaryCPMStatus        OBJECT-TYPE
    SYNTAX      INTEGER {
        online  (1),
        offline (2),
        fail    (3)
    }
    MAX-ACCESS  accessible-for-notify
    STATUS      current
    DESCRIPTION
        "Used by the tmnxRedSecondaryCPMStatusChange Notification, indicates
         the status of the secondary CPM."
    ::= { tmnxChassisNotificationObjects 5 }

tmnxChassisNotifyOID             OBJECT-TYPE
    SYNTAX      OBJECT IDENTIFIER
    MAX-ACCESS  accessible-for-notify
    STATUS      current
    DESCRIPTION
        "Used by the tmnxChassisNotificationClear trap, the OID identifies the
         trap which is getting cleared."
    ::= { tmnxChassisNotificationObjects 6 }

tmnxSyncIfTimingNotifyAlarm      OBJECT-TYPE
    SYNTAX      INTEGER {
        notUsed (0),
        los     (1),
        oof     (2),
        oopir   (3)
    }
    MAX-ACCESS  accessible-for-notify
    STATUS      current
    DESCRIPTION
        "Used by synchronous interface timing notifications, the value of
         tmnxSyncIfTimingNotifyAlarm indicates the reason a timing reference
         alarm has been raised."
    ::= { tmnxChassisNotificationObjects 7 }

tmnxChassisNotifyMismatchedVer   OBJECT-TYPE
    SYNTAX      DisplayString
    MAX-ACCESS  accessible-for-notify
    STATUS      current
    DESCRIPTION
        "Used by tmnxPeSoftwareVersionMismatch, the value of
         tmnxChassisNotifyMismatchedVer indicates the software version of the
         mismatched CPM/IOM card."
    ::= { tmnxChassisNotificationObjects 8 }

tmnxChassisNotifySoftwareLocation OBJECT-TYPE
    SYNTAX      DisplayString
    MAX-ACCESS  accessible-for-notify
    STATUS      current
    DESCRIPTION
        "Used by tmnxPeSoftwareLoadFailed, the value of
         tmnxChassisNotifySoftwareLocation contains the location of the
         software."
    ::= { tmnxChassisNotificationObjects 9 }

tmnxChassisNotifyCardFailureReason OBJECT-TYPE
    SYNTAX      DisplayString
    MAX-ACCESS  accessible-for-notify
    STATUS      current
    DESCRIPTION
        "Used by tmnxEqCardFailure, the value of
         tmnxChassisNotifyCardFailureReason contains the reason for card
         failure."
    ::= { tmnxChassisNotificationObjects 10 }

tmnxChassisNotifyCardName        OBJECT-TYPE
    SYNTAX      DisplayString (SIZE (1..32))
    MAX-ACCESS  accessible-for-notify
    STATUS      current
    DESCRIPTION
        "Used by tmnxEqCardInserted and tmnxEqCardRemoved, the value of
         tmnxChassisNotifyCardName specifies the name of the affected card."
    ::= { tmnxChassisNotificationObjects 11 }

tmnxChassisNotifyCardSyncFile    OBJECT-TYPE
    SYNTAX      DisplayString
    MAX-ACCESS  accessible-for-notify
    STATUS      current
    DESCRIPTION
        "Used by tmnxCpmCardSyncFileNotPresent, the value of
         tmnxChassisNotifyCardSyncFile specifies the name of the affected file."
    ::= { tmnxChassisNotificationObjects 12 }

tmnxCardComplexNumber            OBJECT-TYPE
    SYNTAX      Unsigned32
    MAX-ACCESS  accessible-for-notify
    STATUS      current
    DESCRIPTION
        "Used by tmnxEqCardPChipError, the value of tmnxCardComplexNumber
         specifies the number of the affected Complex."
    ::= { tmnxChassisNotificationObjects 13 }

tmnxCardFwdDirection             OBJECT-TYPE
    SYNTAX      INTEGER {
        ingress (1),
        egress  (2)
    }
    MAX-ACCESS  accessible-for-notify
    STATUS      current
    DESCRIPTION
        "Used by tmnxEqCardPChipError, the value of tmnxCardFwdDirection
         specifies the direction of the affected Complex."
    ::= { tmnxChassisNotificationObjects 14 }

tmnxCardSoftResetState           OBJECT-TYPE
    SYNTAX      INTEGER {
        initiated (1),
        aborted   (2),
        complete  (3)
    }
    MAX-ACCESS  accessible-for-notify
    STATUS      current
    DESCRIPTION
        "Used by tmnxEqCardSoftResetAlarm, the value of tmnxCardSoftResetState
         specifies the reset state of the IOM card."
    ::= { tmnxChassisNotificationObjects 15 }

tmnxMdaNotifyType                OBJECT-TYPE
    SYNTAX      TmnxMdaType
    MAX-ACCESS  accessible-for-notify
    STATUS      current
    DESCRIPTION
        "Used by equipment alarms where the type of MDA isn't supported with
         the current configuration."
    ::= { tmnxChassisNotificationObjects 16 }

tmnxCardSrcSlotBitmap            OBJECT-TYPE
    SYNTAX      TmnxCardSlotBitMap
    MAX-ACCESS  accessible-for-notify
    STATUS      current
    DESCRIPTION
        "Used by tmnxEqCardPChipError, the value of tmnxCardSrcSlotBitmap
         specifies the source slots of the affected Complex."
    ::= { tmnxChassisNotificationObjects 17 }

tmnxDcpTimeEventOccured          OBJECT-TYPE
    SYNTAX      TimeStamp
    MAX-ACCESS  accessible-for-notify
    STATUS      current
    DESCRIPTION
        "The value of tmnxDcpTimeEventOccured indicates the actual time the
         event was detected in the system which may differ from the time that
         event was collected by the logging infrastructure."
    ::= { tmnxChassisNotificationObjects 18 }

tmnxDcpMissingNotificationCount  OBJECT-TYPE
    SYNTAX      Unsigned32
    MAX-ACCESS  accessible-for-notify
    STATUS      current
    DESCRIPTION
        "The value of tmnxDcpMissingNotificationCount indicates the number of
         events dropped because of event throttling during the last throttle
         interval for distributed CPU protection events."
    ::= { tmnxChassisNotificationObjects 19 }

tmnxChassisNotifyCardSlotNum     OBJECT-TYPE
    SYNTAX      TmnxSlotNum
    MAX-ACCESS  accessible-for-notify
    STATUS      current
    DESCRIPTION
        "The unique value of tmnxChassisNotifyCardSlotNum identifies the IOM
         slot within a chassis in the system."
    ::= { tmnxChassisNotificationObjects 20 }

tmnxChassisNotifyPowerZone       OBJECT-TYPE
    SYNTAX      Unsigned32
    MAX-ACCESS  accessible-for-notify
    STATUS      current
    DESCRIPTION
        "The value of tmnxChassisNotifyPowerZone indicates, along with the
         value of tmnxChassisNotifyChassisId, the row in the
         tmnxChassisPowerMgmtTable that is affected by the notification."
    ::= { tmnxChassisNotificationObjects 21 }

tmnxChassisNotifyPowerCapacity   OBJECT-TYPE
    SYNTAX      Unsigned32
    MAX-ACCESS  accessible-for-notify
    STATUS      current
    DESCRIPTION
        "The value of tmnxChassisNotifyPowerCapacity indicates the overall
         power capacity available to the system at the time of the
         notification."
    ::= { tmnxChassisNotificationObjects 22 }

tmnxPlcyAcctTimeEventOccured     OBJECT-TYPE
    SYNTAX      TimeStamp
    MAX-ACCESS  accessible-for-notify
    STATUS      current
    DESCRIPTION
        "The value of tmnxPlcyAcctTimeEventOccured indicates the actual time
         the event was detected in the system which may differ from the time
         that event was collected by the logging infrastructure."
    ::= { tmnxChassisNotificationObjects 23 }

tmnxPlcyAcctMissingNotifCount    OBJECT-TYPE
    SYNTAX      Unsigned32
    MAX-ACCESS  accessible-for-notify
    STATUS      current
    DESCRIPTION
        "The value of tmnxPlcyAcctMissingNotifCount indicates the number of
         events dropped because of event throttling during the last throttle
         interval for distributed policy accounting events."
    ::= { tmnxChassisNotificationObjects 24 }

tmnxChassisNotifyCpmCardSlotNum  OBJECT-TYPE
    SYNTAX      TmnxSlotNum
    MAX-ACCESS  accessible-for-notify
    STATUS      current
    DESCRIPTION
        "The unique value of tmnxChassisNotifyCpmCardSlotNum identifies the CPM
         slot within a chassis in the system."
    ::= { tmnxChassisNotificationObjects 25 }

tmnxChassisNotifyFabricSlotNum   OBJECT-TYPE
    SYNTAX      Unsigned32
    MAX-ACCESS  accessible-for-notify
    STATUS      current
    DESCRIPTION
        "The unique value of tmnxChassisNotifyFabricSlotNum identifies the
         fabric slot within a chassis in the system."
    ::= { tmnxChassisNotificationObjects 26 }

tmnxIomResourceType              OBJECT-TYPE
    SYNTAX      INTEGER {
        nextHop       (1),
        tunnelNextHop (2),
        stickyHash    (3),
        arpEntry      (4),
        ecmp          (5),
        ecmpNextHop   (6),
        ecmpTunnel    (7),
        ecmpMpls      (8),
        ecmpIp        (9),
        ecmpIpLevel2  (10),
        fpMemory      (11)
    }
    MAX-ACCESS  accessible-for-notify
    STATUS      current
    DESCRIPTION
        "Used by tmnxIomResHighLimitReached, tmnxIomResExhausted and
         tmnxIomResStateClr, the value of tmnxIomResourceType specifies the
         type of IOM resource."
    ::= { tmnxChassisNotificationObjects 27 }

tmnxIomResourceLimitPct          OBJECT-TYPE
    SYNTAX      Unsigned32
    MAX-ACCESS  accessible-for-notify
    STATUS      current
    DESCRIPTION
        "Used by tmnxIomResHighLimitReached, tmnxIomResExhausted and
         tmnxIomResStateClr, the value of tmnxIomResourceLimitPct specifies the
         percentage of IOM Resource being utilized."
    ::= { tmnxChassisNotificationObjects 28 }

tmnxIomResLimitTimeEventOccured  OBJECT-TYPE
    SYNTAX      TimeStamp
    MAX-ACCESS  accessible-for-notify
    STATUS      current
    DESCRIPTION
        "The value of tmnxIomResLimitTimeEventOccured indicates the actual time
         the event was detected in the system which may differ from the time
         that event was collected by the logging infrastructure."
    ::= { tmnxChassisNotificationObjects 29 }

tmnxIomResLimMissingNotifCount   OBJECT-TYPE
    SYNTAX      Unsigned32
    MAX-ACCESS  accessible-for-notify
    STATUS      current
    DESCRIPTION
        "The value of tmnxIomResLimMissingNotifCount indicates the number of
         events dropped because of event throttling during the last throttle
         interval for next hop resource events."
    ::= { tmnxChassisNotificationObjects 30 }

tmnxChassisNotifyFpNum           OBJECT-TYPE
    SYNTAX      Unsigned32
    MAX-ACCESS  accessible-for-notify
    STATUS      current
    DESCRIPTION
        "The value of tmnxChassisNotifyFpNum indicates the Forwarding Plane."
    ::= { tmnxChassisNotificationObjects 31 }

tmnxChassisNotifyDiskFullReason  OBJECT-TYPE
    SYNTAX      DisplayString
    MAX-ACCESS  accessible-for-notify
    STATUS      current
    DESCRIPTION
        "The value of tmnxChassisNotifyDiskFullReason indicates the reason for
         the disk full condition."
    ::= { tmnxChassisNotificationObjects 32 }

tmnxChassisNotifyMgmtEthRedPort  OBJECT-TYPE
    SYNTAX      TmnxPortID
    MAX-ACCESS  accessible-for-notify
    STATUS      current
    DESCRIPTION
        "The value of tmnxChassisNotifyMgmtEthRedPort indicates the CPM port
         operating as the system's management interface."
    ::= { tmnxChassisNotificationObjects 33 }

tmnxMacScaleCardSlotNum          OBJECT-TYPE
    SYNTAX      TmnxSlotNum
    MAX-ACCESS  accessible-for-notify
    STATUS      current
    DESCRIPTION
        "The unique value of tmnxMacScaleCardSlotNum identifies the card slot
         within a chassis in the system. It is used by the FDB MAC scale
         notifications."
    ::= { tmnxChassisNotificationObjects 38 }

tmnxCpmPowerShelfCommsFail       OBJECT-TYPE
    SYNTAX      TmnxCpmPowerShelfCommsFailStatus
    MAX-ACCESS  accessible-for-notify
    STATUS      current
    DESCRIPTION
        "The values of tmnxCpmPowerShelfCommsFail identify the CPMs which
         cannot communicate to a given power-shelf."
    ::= { tmnxChassisNotificationObjects 39 }

tmnxEqNotifyHwEventType          OBJECT-TYPE
    SYNTAX      TmnxHwEventType
    MAX-ACCESS  accessible-for-notify
    STATUS      current
    DESCRIPTION
        "Used by tmnx equipment event Notifications, indicates the type of
         event detected for the hardware component."
    ::= { tmnxChassisNotificationObjects 40 }

tmnxEqNotifyHwEventDetail        OBJECT-TYPE
    SYNTAX      DisplayString
    MAX-ACCESS  accessible-for-notify
    STATUS      current
    DESCRIPTION
        "Used by tmnx equipment event Notifications, indicates the detail of
         event detected for the hardware component."
    ::= { tmnxChassisNotificationObjects 41 }

tmnxEqNotifyHwEventAction        OBJECT-TYPE
    SYNTAX      TmnxHwEventAction
    MAX-ACCESS  accessible-for-notify
    STATUS      current
    DESCRIPTION
        "Used by tmnx equipment event Notifications, indicates the action taken
         when event detected for the hardware component."
    ::= { tmnxChassisNotificationObjects 42 }

tmnxEsaNotifyId                  OBJECT-TYPE
    SYNTAX      Integer32
    MAX-ACCESS  accessible-for-notify
    STATUS      current
    DESCRIPTION
        "Used by traps to indicate the ESA ID that triggered the notification."
    ::= { tmnxChassisNotificationObjects 43 }

tmnxEsaVmNotifyId                OBJECT-TYPE
    SYNTAX      Integer32
    MAX-ACCESS  accessible-for-notify
    STATUS      current
    DESCRIPTION
        "Used by traps to indicate the ESA VM ID that triggered the
         notification."
    ::= { tmnxChassisNotificationObjects 44 }

tmnxIomRsrcResourceType          OBJECT-TYPE
    SYNTAX      INTEGER {
        fecLevel1           (1),
        fecLevel2           (2),
        fecLevel3           (3),
        fecLevel1n2         (4),
        groupFecLevel1      (21),
        groupFecLevel2      (22),
        groupFecLevel3      (23),
        encap               (100),
        egressEncapsulation (103),
        ingressTerminationA (200),
        ingressTerminationB (201),
        ingressEndpoint1    (202),
        ingressEndpoint2    (203),
        egressEncapPhase1   (204),
        egressEncapPhase2   (205),
        egressEncapPhase3   (206),
        egressEncapPhase4   (207),
        egressEncapPhase5   (208),
        egressEncapPhase6   (209),
        egressEncapPhase7   (210),
        egressEncapPhase8   (211),
        ppmc                (300)
    }
    MAX-ACCESS  accessible-for-notify
    STATUS      current
    DESCRIPTION
        "The value of tmnxIomRsrcResourceType specifies the type of IOM
         resource."
    ::= { tmnxChassisNotificationObjects 45 }

tmnxIomRsrcUserType              OBJECT-TYPE
    SYNTAX      INTEGER {
        mpls      (1),
        interface (2),
        sap       (3),
        sdpb      (4),
        arpNbr    (5),
        ucastTnh  (6),
        mcastTnh  (7),
        mplsArp   (8),
        mplsNhlfe (9),
        mplsIlm   (10),
        bfd       (11),
        ptp       (12),
        system    (13),
        filter    (14),
        multicast (15),
        routing   (16)
    }
    MAX-ACCESS  accessible-for-notify
    STATUS      obsolete
    DESCRIPTION
        "The value of tmnxIomRsrcUserType specifies the user of the IOM
         resource. This object was replaced by tmnxIomRsrcOwnerType in release
         22.10 and obsoleted in release 23.3."
    ::= { tmnxChassisNotificationObjects 46 }

tmnxIomRsrcTimeEventOccured      OBJECT-TYPE
    SYNTAX      TimeStamp
    MAX-ACCESS  accessible-for-notify
    STATUS      current
    DESCRIPTION
        "The value of tmnxIomRsrcTimeEventOccured indicates the actual time
         when the event was detected in the system, which may differ from the
         time that the event was collected by the logging infrastructure."
    ::= { tmnxChassisNotificationObjects 47 }

tmnxIomRsrcUsagePercent          OBJECT-TYPE
    SYNTAX      Integer32 (-1 | 0..100)
    MAX-ACCESS  accessible-for-notify
    STATUS      current
    DESCRIPTION
        "The value of tmnxIomRsrcUsagePercent specifies the percentage of the
         IOM resource being utilized. The value -1 specifies that the
         utilization is not applicable for the resource."
    ::= { tmnxChassisNotificationObjects 48 }

tmnxIomRsrcMissingNotifCount     OBJECT-TYPE
    SYNTAX      Unsigned32
    MAX-ACCESS  accessible-for-notify
    STATUS      current
    DESCRIPTION
        "The value of tmnxIomRsrcMissingNotifCount indicates the number of
         events dropped because of event throttling during the last throttle
         interval for resource events."
    ::= { tmnxChassisNotificationObjects 49 }

tmnxHwAggShpTimeEventOccured     OBJECT-TYPE
    SYNTAX      TimeStamp
    MAX-ACCESS  accessible-for-notify
    STATUS      current
    DESCRIPTION
        "The value of tmnxHwAggShpTimeEventOccured indicates the actual time
         when the event was detected in the system, which may differ from the
         time that the event was collected by the logging infrastructure."
    ::= { tmnxChassisNotificationObjects 50 }

tmnxHwAggShpMissingNotifCount    OBJECT-TYPE
    SYNTAX      Unsigned32
    MAX-ACCESS  accessible-for-notify
    STATUS      current
    DESCRIPTION
        "The value of tmnxHwAggShpMissingNotifCount indicates the number of
         events dropped because of event throttling during the last throttle
         interval for resource events."
    ::= { tmnxChassisNotificationObjects 51 }

tmnxIomRsrcOwnerType             OBJECT-TYPE
    SYNTAX      INTEGER {
        mpls                  (1),
        interface             (2),
        sap                   (3),
        sdpb                  (4),
        arpNbr                (5),
        ucastTnh              (6),
        mcastTnh              (7),
        mplsArp               (8),
        mplsNhlfe             (9),
        mplsIlm               (10),
        bfd                   (11),
        ptp                   (12),
        system                (13),
        filter                (14),
        multicast             (15),
        routing               (16),
        srv6                  (17),
        arp                   (18),
        nd                    (19),
        mplsEcmp              (20),
        ipRoutingEcmp         (21),
        srv6DirectIpTransport (22),
        tunnelEcmp            (23),
        rvplsOism             (24),
        evpn                  (25),
        mvpnNhlfe             (26),
        ppmc                  (27),
        mplsMulticastFrr      (28),
        sbfd                  (29)
    }
    MAX-ACCESS  accessible-for-notify
    STATUS      current
    DESCRIPTION
        "The value of tmnxIomRsrcOwnerType specifies the owner of the IOM
         resource.

         This object was added in 22.10 and  replaces tmnxIomRsrcUserType which is
         obsoleted in release 23.3."
    ::= { tmnxChassisNotificationObjects 52 }

tmnxNotifIxrResourceOwner        OBJECT-TYPE
    SYNTAX      TmnxIxrResourceOwner
    MAX-ACCESS  accessible-for-notify
    STATUS      current
    DESCRIPTION
        "The value of tmnxNotifIxrResourceOwner indicates the application that
         uses the resource."
    ::= { tmnxChassisNotificationObjects 53 }

tmnxNotifIxrResource             OBJECT-TYPE
    SYNTAX      INTEGER {
        acLif            (1),
        arpLif           (2),
        bgpLabelRouteLif (3),
        commonLif        (4),
        fecProtected     (6),
        fecUnpaired      (7),
        l2Service        (8),
        l3VsiRif         (9),
        mplsLif          (10),
        mplsInLif        (11),
        mplsNhlfeLif     (12),
        oamLmCtr         (13),
        sdpBindGreLif    (14),
        sdpBindMplsLif   (15),
        srv6Lif          (16),
        srv6TunnelLif    (17),
        ssidLif          (18),
        stationId        (19),
        vxlanLif         (20)
    }
    MAX-ACCESS  accessible-for-notify
    STATUS      current
    DESCRIPTION
        "The value of tmnxNotifIxrResource indicates the IXR resource."
    ::= { tmnxChassisNotificationObjects 54 }

tmnxNotifIxrRsrcUtilPercentage   OBJECT-TYPE
    SYNTAX      Unsigned32
    MAX-ACCESS  accessible-for-notify
    STATUS      current
    DESCRIPTION
        "The value of tmnxNotifIxrRsrcUtilPercentage indicates the utilization
         percentage at the moment the notification using this object was
         raised."
    ::= { tmnxChassisNotificationObjects 55 }

tmnxEsaPortNotifyPortId          OBJECT-TYPE
    SYNTAX      TmnxPortID
    MAX-ACCESS  accessible-for-notify
    STATUS      current
    DESCRIPTION
        "Used by notifications for ports in tmnxEsaHostPortTable, the OID
         indicates the port or sonet path associated with the alarm."
    ::= { tmnxChassisNotificationObjects 56 }

tmnxEsaHostPortNotifCrcThreshold OBJECT-TYPE
    SYNTAX      Unsigned32
    MAX-ACCESS  accessible-for-notify
    STATUS      current
    DESCRIPTION
        "The value of tmnxEsaHostPortNotifCrcThreshold indicates the threshold
         value used in a Esa Host Port CRC Monitoring alarm."
    ::= { tmnxChassisNotificationObjects 57 }

tmnxEsaHostPortNotifCrcMltiplier OBJECT-TYPE
    SYNTAX      Unsigned32
    MAX-ACCESS  accessible-for-notify
    STATUS      current
    DESCRIPTION
        "The value of tmnxEsaHostPortNotifCrcMltiplier indicates the threshold
         multiplier value used in a Esa Host Port CRC Monitoring alarm."
    ::= { tmnxChassisNotificationObjects 58 }

tmnxEsaHostPortNotifCrcAlrmValue OBJECT-TYPE
    SYNTAX      TmnxEsaHostPortMonReportValue
    MAX-ACCESS  accessible-for-notify
    STATUS      current
    DESCRIPTION
        "The value of tmnxEsaHostPortNotifCrcAlrmValue indicates the enumerated
         alarm raised or cleared in a Esa Host Port CRC Monitoring alarm."
    ::= { tmnxChassisNotificationObjects 59 }

tmnxChassisNotifyDiskFormatType  OBJECT-TYPE
    SYNTAX      INTEGER {
        format      (1),
        secureErase (2)
    }
    MAX-ACCESS  accessible-for-notify
    STATUS      current
    DESCRIPTION
        "The value of tmnxChassisNotifyDiskFormatType indicates the type of
         formatting being initiated."
    ::= { tmnxChassisNotificationObjects 60 }

tmnxChassisAdminObjects          OBJECT IDENTIFIER ::= { tmnxHwObjs 8 }

tmnxChassisAdminCtrlObjs         OBJECT IDENTIFIER ::= { tmnxChassisAdminObjects 1 }

tmnxChassisAdminOwner            OBJECT-TYPE
    SYNTAX      SnmpAdminString
    MAX-ACCESS  read-write
    STATUS      current
    DESCRIPTION
        "Who has last initialized the chassis administrative table, who is
         making all the changes, and who is expected to either commit or
         re-initialize (ABORT-TRANSACTION).

         tmnxChassisAdminOwner is advisory only. Before beginning a transaction,
         read tmnxChassisAdminOwner.  if it is empty then proceed with the
         configuration.

         Set tmnxChassisAdminOwner after setting tmnxChassisAdminControlApply
         so that other users will be advised to not make changes to the Admin
         tables.

         Agent sets tmnxChassisAdminOwner to empty string after
         tmnxChassisAdminControlApply is set - either by user initializing or
         committing, or by agent timing out the uncommitted transactions."
    ::= { tmnxChassisAdminCtrlObjs 1 }

tmnxChassisAdminControlApply     OBJECT-TYPE
    SYNTAX      INTEGER {
        none       (1),
        initialize (2),
        commit     (3)
    }
    MAX-ACCESS  read-write
    STATUS      current
    DESCRIPTION
        "The value of tmnxChassisAdminControlApply specifies how the chassis
         administrative table is used in order to update tmnxChassisTable table
         objects.

         When set to initialize(2) (BEGIN-TRANSACTION), the objects in the
         chassis administrative table are set to the current Operational
         values, from the tmnxChassisTable.

         When set to commit(3) (END-TRANSACTION), all of the objects from the
         chassis administrative table are copied to the corresponding
         tmnxChassisTable table objects.

         When set to none(1) (ABORT-TRANSACTION) any uncommitted changes will
         be lost.

         If changes are not committed within a predefined timeout, they will be
         lost."
    ::= { tmnxChassisAdminCtrlObjs 2 }

tmnxChassisAdminLastSetTimer     OBJECT-TYPE
    SYNTAX      TimeInterval
    UNITS       "seconds"
    MAX-ACCESS  read-only
    STATUS      obsolete
    DESCRIPTION
        "The time remaining until the agent re-initializes the administrative
         tables.

         If tmnxChassisAdminControlApply is not set to commit(3) within
         tmnxChassisAdminLastSetTimeout seconds, the agent will set it to
         initialize(2) and all uncommitted changes will be lost.

         This way, uncommitted changes from failed (uncompleted) change sets
         will eventually be removed, and another transaction can safely begin.

         this object is reset to tmnxChassisAdminLastSetTimeout after SNMP SET
         operation to any of the chassis administrative value tables."
    ::= { tmnxChassisAdminCtrlObjs 3 }

tmnxChassisAdminLastSetTimeout   OBJECT-TYPE
    SYNTAX      TimeInterval
    UNITS       "seconds"
    MAX-ACCESS  read-write
    STATUS      obsolete
    DESCRIPTION
        "Timeout for tmnxChassisAdminLastSetTimer. The value zero is not
         allowed."
    DEFVAL      { 1800 }
    ::= { tmnxChassisAdminCtrlObjs 4 }

tmnxChassisAdminValueObjs        OBJECT IDENTIFIER ::= { tmnxChassisAdminObjects 2 }

tSyncIfTimingAdmTable            OBJECT-TYPE
    SYNTAX      SEQUENCE OF TSyncIfTimingAdmEntry
    MAX-ACCESS  not-accessible
    STATUS      current
    DESCRIPTION
        "Values for the synchronous interface timing for the chassis.

         The VSR system does not support synchronous interface timing."
    ::= { tmnxChassisAdminValueObjs 1 }

tSyncIfTimingAdmEntry            OBJECT-TYPE
    SYNTAX      TSyncIfTimingAdmEntry
    MAX-ACCESS  not-accessible
    STATUS      current
    DESCRIPTION
        "Information about the synchronous interface timing. Entries are
         created by user. Entries are deleted by user. Note that the first
         Nokia SROS series product release does not support configuration of
         synchronous timing equipment on the secondary CPM. All SNMP operations
         with tmnxCpmCardSlotNum of the secondary CPM will be denied.

         In an XRS-40 system, the configuration of synchronous timing equipment
         on the extension chassis is not supported.

         The 7x50 systems supports 3 timing references (reference1, reference2
         and bits).

         The 7710 system only supports 2 timing references (reference1 and
         reference2).  On 7710 system, references can be a source port
         or a BITS input on a CES CMA.  If the value of the reference source
         port is a valid Port ID then the reference is a source port.  If the
         value of the source hardware is a valid HWIndex of a CES CMA then the
         source is a BITS on the CES CMA.

         The VSR system does not support synchronous interface timing."
    INDEX       {
        tmnxChassisIndex,
        tmnxCpmCardSlotNum,
        tmnxCpmCardNum
    }
    ::= { tSyncIfTimingAdmTable 1 }

TSyncIfTimingAdmEntry            ::= SEQUENCE
{
    tSyncIfTimingAdmRevert           TruthValue,
    tSyncIfTimingAdmRefOrder1        TmnxSETSRefSource,
    tSyncIfTimingAdmRefOrder2        TmnxSETSRefSource,
    tSyncIfTimingAdmRef1SrcPort      TmnxPortID,
    tSyncIfTimingAdmRef1AdminStatus  TmnxPortAdminStatus,
    tSyncIfTimingAdmRef2SrcPort      TmnxPortID,
    tSyncIfTimingAdmRef2AdminStatus  TmnxPortAdminStatus,
    tSyncIfTimingAdmChanged          Unsigned32,
    tSyncIfTimingAdmRefOrder3        TmnxSETSRefSource,
    tSyncIfTimingAdmBITSIfType       TmnxBITSIfType,
    tSyncIfTimingAdmBITSAdminStatus  TmnxPortAdminStatus,
    tSyncIfTimingAdmRef1SrcHw        TmnxHwIndexOrZero,
    tSyncIfTimingAdmRef1BITSIfType   TmnxBITSIfType,
    tSyncIfTimingAdmRef2SrcHw        TmnxHwIndexOrZero,
    tSyncIfTimingAdmRef2BITSIfType   TmnxBITSIfType,
    tSyncIfTimingAdmBITSOutAdmStatus TmnxPortAdminStatus,
    tSyncIfTimingAdmBITSOutLineLen   INTEGER,
    tSyncIfTimingAdmRef1CfgQltyLevel TmnxSSMQualityLevel,
    tSyncIfTimingAdmRef2CfgQltyLevel TmnxSSMQualityLevel,
    tSyncIfTimingAdmBITSCfgQltyLevel TmnxSSMQualityLevel,
    tSyncIfTimingAdmRef1NationalUse  Unsigned32,
    tSyncIfTimingAdmRef2NationalUse  Unsigned32,
    tSyncIfTimingAdmBITSNationalUse  Unsigned32,
    tSyncIfTimingAdmQLSelection      TmnxEnabledDisabled,
    tSyncIfTimingAdmRefOrder4        TmnxSETSRefSource,
    tSyncIfTimingAdmPTPAdminStatus   TmnxPortAdminStatus,
    tSyncIfTimingAdmPTPCfgQltyLevel  TmnxSSMQualityLevel,
    tSyncIfTimingAdmBITSOutSource    TmnxBITSOutSource,
    tSyncIfTimingAdmBITSOutQlMin     TmnxSSMQualityLevel,
    tSyncIfTimingAdmBITSOutSquelch   TruthValue,
    tSyncIfTimingAdmQlMin            TmnxSSMQualityLevel,
    tSyncIfTimingAdmWaitToRestorTime Unsigned32,
    tSyncIfTimingAdmChangedMask      BITS,
    tSyncIfTimingAdmSyncECfgQltyLevl TmnxSSMQualityLevel,
    tSyncIfTimingAdmSyncEAdminStatus TmnxPortAdminStatus,
    tSyncIfTimingAdmRefOrder5        TmnxSETSRefSource,
    tSyncIfTimingAdmGnssCfgQltyLevel TmnxSSMQualityLevel,
    tSyncIfTimingAdmGnssAdminStatus  TmnxPortAdminStatus,
    tSyncIfTimingAdmRefOrder6        TmnxSETSRefSource
}

tSyncIfTimingAdmRevert           OBJECT-TYPE
    SYNTAX      TruthValue
    MAX-ACCESS  read-create
    STATUS      current
    DESCRIPTION
        "The value of tSyncIfTimingAdmRevert specifies whether the reference
         source will revert to a higher priority source that has been
         re-validated or newly validated.

         The synchronous interface timing subsystem is by default non-revertive
         ('false')."
    DEFVAL      { false }
    ::= { tSyncIfTimingAdmEntry 1 }

tSyncIfTimingAdmRefOrder1        OBJECT-TYPE
    SYNTAX      TmnxSETSRefSource
    MAX-ACCESS  read-create
    STATUS      current
    DESCRIPTION
        "The value of tSyncIfTimingAdmRefOrder1 specifies the most preferred
         timing reference source.

         The synchronous equipment timing subsystem chooses a timing reference
         based on priority.

         The user can configure the priority order of the following timing
         reference inputs ('bits', 'reference1', 'reference2', and 'ptp').

         If the platform does not support that timing reference input, it
         cannot be configured in the reference priority order.  For example,
         the 'bits' timing reference cannot be configured on a 7750 SR-c12
         system.

         Other values of TmnxSETSRefSource (e.g. 'bits2') cannot be configured
         in the reference order."
    DEFVAL      { bits }
    ::= { tSyncIfTimingAdmEntry 2 }

tSyncIfTimingAdmRefOrder2        OBJECT-TYPE
    SYNTAX      TmnxSETSRefSource
    MAX-ACCESS  read-create
    STATUS      current
    DESCRIPTION
        "The value of tSyncIfTimingAdmRefOrder2 specifies the second most
         preferred timing reference for the synchronous equipment timing
         subsystem."
    DEFVAL      { reference1 }
    ::= { tSyncIfTimingAdmEntry 3 }

tSyncIfTimingAdmRef1SrcPort      OBJECT-TYPE
    SYNTAX      TmnxPortID
    MAX-ACCESS  read-create
    STATUS      current
    DESCRIPTION
        "The value of tSyncIfTimingAdmRef1SrcPort specifies the source port of
         the first timing reference."
    DEFVAL      { '1e000000'H }
    ::= { tSyncIfTimingAdmEntry 4 }

tSyncIfTimingAdmRef1AdminStatus  OBJECT-TYPE
    SYNTAX      TmnxPortAdminStatus
    MAX-ACCESS  read-create
    STATUS      current
    DESCRIPTION
        "The value of tSyncIfTimingAdmRef1AdminStatus specifies the desired
         administrative status of the first timing reference."
    DEFVAL      { outOfService }
    ::= { tSyncIfTimingAdmEntry 5 }

tSyncIfTimingAdmRef2SrcPort      OBJECT-TYPE
    SYNTAX      TmnxPortID
    MAX-ACCESS  read-create
    STATUS      current
    DESCRIPTION
        "The value of tSyncIfTimingAdmRef2SrcPort specifies the source port of
         the second timing reference."
    DEFVAL      { '1e000000'H }
    ::= { tSyncIfTimingAdmEntry 6 }

tSyncIfTimingAdmRef2AdminStatus  OBJECT-TYPE
    SYNTAX      TmnxPortAdminStatus
    MAX-ACCESS  read-create
    STATUS      current
    DESCRIPTION
        "The value of tSyncIfTimingAdmRef2AdminStatus specifies the desired
         administrative status of the second timing reference."
    DEFVAL      { outOfService }
    ::= { tSyncIfTimingAdmEntry 7 }

tSyncIfTimingAdmChanged          OBJECT-TYPE
    SYNTAX      Unsigned32
    MAX-ACCESS  read-create
    STATUS      current
    DESCRIPTION
        "The value of tSyncIfTimingAdmChanged is a bitmask that indicates which
         objects have been set, but not committed.  bit values used here are:

         0x0001:    tSyncIfTimingAdmRevert
         0x0002:    tSyncIfTimingAdmRefOrder1
         0x0004:    tSyncIfTimingAdmRefOrder2
         0x0008:    tSyncIfTimingAdmRef1SrcPort
         0x0010:    tSyncIfTimingAdmRef1AdminStatus
         0x0020:    tSyncIfTimingAdmRef2SrcPort
         0x0040:    tSyncIfTimingAdmRef2AdminStatus
         0x0080:    tSyncIfTimingAdmRefOrder3
         0x0100:    tSyncIfTimingAdmBITSIfType
         0x0200:    tSyncIfTimingAdmBITSAdminStatus
         0x0400:    tSyncIfTimingAdmRef1SrcHw
         0x0800:    tSyncIfTimingAdmRef1BITSIfType
         0x1000:    tSyncIfTimingAdmRef2SrcHw
         0x2000:    tSyncIfTimingAdmRef2BITSIfType

         The agent sets these bits when an object in the row
         is set.  This object is cleared to zero by setting
         tmnxChassisAdminControlApply to initialize(2) or commit(3)."
    ::= { tSyncIfTimingAdmEntry 8 }

tSyncIfTimingAdmRefOrder3        OBJECT-TYPE
    SYNTAX      TmnxSETSRefSource
    MAX-ACCESS  read-create
    STATUS      current
    DESCRIPTION
        "The value of tSyncIfTimingAdmRefOrder3 specifies the third most
         preferred timing reference for the synchronous equipment timing
         subsystem."
    DEFVAL      { reference2 }
    ::= { tSyncIfTimingAdmEntry 9 }

tSyncIfTimingAdmBITSIfType       OBJECT-TYPE
    SYNTAX      TmnxBITSIfType
    MAX-ACCESS  read-create
    STATUS      current
    DESCRIPTION
        "The value of tSyncIfTimingAdmBITSIfType specifies the interface type
         of the BITS (Building Integrated Timing Supply) timing reference."
    DEFVAL      { t1-esf }
    ::= { tSyncIfTimingAdmEntry 10 }

tSyncIfTimingAdmBITSAdminStatus  OBJECT-TYPE
    SYNTAX      TmnxPortAdminStatus
    MAX-ACCESS  read-create
    STATUS      current
    DESCRIPTION
        "The value of tSyncIfTimingAdmBITSAdminStatus specifies the desired
         administrative status of the BITS (Building Integrated Timing Supply)
         input timing reference."
    DEFVAL      { outOfService }
    ::= { tSyncIfTimingAdmEntry 11 }

tSyncIfTimingAdmRef1SrcHw        OBJECT-TYPE
    SYNTAX      TmnxHwIndexOrZero
    MAX-ACCESS  read-create
    STATUS      obsolete
    DESCRIPTION
        "The value of tSyncIfTimingAdmRef1SrcHw specifies the source HW Index
         of the first timing reference if the source is not a port.

         This can only be set to a valid HW Index if the value of
         tSyncIfTimingAdmRef1SrcPort is '1e000000'H.

         Setting the value of tSyncIfTimingAdmRef1SrcHw from non-zero to zero
         will cause the value of tSyncIfTimingAdmRef1BITSIfType to be reset to
         its default value of 't1-esf'.

         This object was obsoleted in release 20.5."
    DEFVAL      { 0 }
    ::= { tSyncIfTimingAdmEntry 12 }

tSyncIfTimingAdmRef1BITSIfType   OBJECT-TYPE
    SYNTAX      TmnxBITSIfType
    MAX-ACCESS  read-create
    STATUS      obsolete
    DESCRIPTION
        "The value of tSyncIfTimingAdmRef1BITSIfType specifies the interface
         type of the first timing reference if the source is BITS.

         This can only be changed if the value of tSyncIfTimingAdmRef1SrcHw is
         not 0.

         This object was obsoleted in release 20.5."
    DEFVAL      { t1-esf }
    ::= { tSyncIfTimingAdmEntry 13 }

tSyncIfTimingAdmRef2SrcHw        OBJECT-TYPE
    SYNTAX      TmnxHwIndexOrZero
    MAX-ACCESS  read-create
    STATUS      obsolete
    DESCRIPTION
        "The value of tSyncIfTimingAdmRef2SrcHw specifies the source HW Index
         of the second timing reference if the source is not a port.

         This can only be set to a valid HW Index if the value of
         tSyncIfTimingAdmRef2SrcPort is '1e000000'H.

         Setting the value of tSyncIfTimingAdmRef2SrcHw from non-zero to zero
         will cause the value of tSyncIfTimingAdmRef2BITSIfType to be reset to
         its default value of 't1-esf'.

         This object was obsoleted in release 20.5."
    DEFVAL      { 0 }
    ::= { tSyncIfTimingAdmEntry 14 }

tSyncIfTimingAdmRef2BITSIfType   OBJECT-TYPE
    SYNTAX      TmnxBITSIfType
    MAX-ACCESS  read-create
    STATUS      obsolete
    DESCRIPTION
        "The value of tSyncIfTimingAdmRef2BITSIfType specifies the interface
         type of the second timing reference if the source is BITS.

         This can only be changed if the value of tSyncIfTimingAdmRef2SrcHw is
         not 0.

         This object was obsoleted in release 20.5."
    DEFVAL      { t1-esf }
    ::= { tSyncIfTimingAdmEntry 15 }

tSyncIfTimingAdmBITSOutAdmStatus OBJECT-TYPE
    SYNTAX      TmnxPortAdminStatus
    MAX-ACCESS  read-create
    STATUS      current
    DESCRIPTION
        "The value of tSyncIfTimingAdmBITSOutAdmStatus specifies administrative
         status of the BITS (Building Integrated Timing Supply) output timing
         reference.

         In an XRS-40 system, tSyncIfTimingAdmBITSOutAdmStatus is always
         'inService(2)', and cannot be changed.  In an XRS-40 system, the
         extension chassis is synchronized with the master chassis via the BITS
         ports.  See the description of tSyncIfTimingAdmBITSOutSource for
         details on how the BITS ports are used to synchronize the master and
         extension chassis of the XRS-40 system."
    DEFVAL      { outOfService }
    ::= { tSyncIfTimingAdmEntry 16 }

tSyncIfTimingAdmBITSOutLineLen   OBJECT-TYPE
    SYNTAX      INTEGER {
        lengthNotApplicable (0),
        length0To110        (1),
        length110To220      (2),
        length220To330      (3),
        length330To440      (4),
        length440To550      (5),
        length550To660      (6)
    }
    MAX-ACCESS  read-create
    STATUS      current
    DESCRIPTION
        "tSyncIfTimingAdmBITSOutLineLen specifies the length of the line
         (in feet) for the BITS (Building Integrated Timing Supply) output.
         The following values are valid:
             lengthNotApplicable (0) - When BITS output is not supported
             length0To110        (1) - For line length from 0 to 110 feet
             length110To220      (2) - For line length from 110 to 220 feet
             length220To330      (3) - For line length from 230 to 330 feet
             length330To440      (4) - For line length from 330 to 440 feet
             length440To550      (5) - For line length from 440 to 550 feet
             length550To660      (6) - For line length from 550 to 660 feet
         The default is 'lengthNotApplicable' on CPM cards which do not
         support line length.  Otherwise, the default is 'length0To110'."
    DEFVAL      { lengthNotApplicable }
    ::= { tSyncIfTimingAdmEntry 17 }

tSyncIfTimingAdmRef1CfgQltyLevel OBJECT-TYPE
    SYNTAX      TmnxSSMQualityLevel
    MAX-ACCESS  read-create
    STATUS      current
    DESCRIPTION
        "The value of tSyncIfTimingAdmRef1CfgQltyLevel specifies the configured
         Quality Level of Reference 1. A value of 'unknown (0)' indicates
         Reference 1 is not forced to a specific quality level."
    DEFVAL      { unknown }
    ::= { tSyncIfTimingAdmEntry 18 }

tSyncIfTimingAdmRef2CfgQltyLevel OBJECT-TYPE
    SYNTAX      TmnxSSMQualityLevel
    MAX-ACCESS  read-create
    STATUS      current
    DESCRIPTION
        "The value of tSyncIfTimingAdmRef2CfgQltyLevel specifies the configured
         Quality Level of Reference 2. A value of 'unknown (0)' indicates
         Reference 2 is not forced to a specific quality level."
    DEFVAL      { unknown }
    ::= { tSyncIfTimingAdmEntry 19 }

tSyncIfTimingAdmBITSCfgQltyLevel OBJECT-TYPE
    SYNTAX      TmnxSSMQualityLevel
    MAX-ACCESS  read-create
    STATUS      current
    DESCRIPTION
        "The value of tSyncIfTimingAdmBITSCfgQltyLevel specifies the configured
         Quality Level of the BITS interface. A value of 'unknown (0)'
         indicates the BITS interface is not forced to a specific quality
         level."
    DEFVAL      { unknown }
    ::= { tSyncIfTimingAdmEntry 20 }

tSyncIfTimingAdmRef1NationalUse  OBJECT-TYPE
    SYNTAX      Unsigned32 (4..8)
    MAX-ACCESS  read-create
    STATUS      obsolete
    DESCRIPTION
        "The value of tSyncIfTimingAdmRef1NationalUse specifies the national
         use bit to carry SSM Messages. This applies only to E1 BITS
         interfaces.

         This object was obsoleted in release 20.5."
    DEFVAL      { 8 }
    ::= { tSyncIfTimingAdmEntry 21 }

tSyncIfTimingAdmRef2NationalUse  OBJECT-TYPE
    SYNTAX      Unsigned32 (4..8)
    MAX-ACCESS  read-create
    STATUS      obsolete
    DESCRIPTION
        "The value of tSyncIfTimingAdmRef2NationalUse specifies the national
         use bit to carry SSM Messages. This applies only to E1 BITS
         interfaces.

         This object was obsoleted in release 20.5."
    DEFVAL      { 8 }
    ::= { tSyncIfTimingAdmEntry 22 }

tSyncIfTimingAdmBITSNationalUse  OBJECT-TYPE
    SYNTAX      Unsigned32 (4..8)
    MAX-ACCESS  read-create
    STATUS      current
    DESCRIPTION
        "The value of tSyncIfTimingAdmBITSNationalUse specifies the national
         use bit to carry SSM Messages. This applies only to E1 BITS
         interfaces."
    DEFVAL      { 8 }
    ::= { tSyncIfTimingAdmEntry 23 }

tSyncIfTimingAdmQLSelection      OBJECT-TYPE
    SYNTAX      TmnxEnabledDisabled
    MAX-ACCESS  read-create
    STATUS      current
    DESCRIPTION
        "The value of tSyncIfTimingAdmQLSelection specifies whether or not the
         timing reference selection process uses the quality level of each
         timing reference when making the decision on which reference should
         provide system timing."
    REFERENCE
        "ITU-T Recommendation G.781, June 1999, Section 5.12"
    DEFVAL      { disabled }
    ::= { tSyncIfTimingAdmEntry 24 }

tSyncIfTimingAdmRefOrder4        OBJECT-TYPE
    SYNTAX      TmnxSETSRefSource
    MAX-ACCESS  read-create
    STATUS      current
    DESCRIPTION
        "The value of tSyncIfTimingAdmRefOrder4 specifies the fourth most
         preferred timing reference for the synchronous equipment timing
         subsystem."
    DEFVAL      { ptp }
    ::= { tSyncIfTimingAdmEntry 25 }

tSyncIfTimingAdmPTPAdminStatus   OBJECT-TYPE
    SYNTAX      TmnxPortAdminStatus
    MAX-ACCESS  read-create
    STATUS      current
    DESCRIPTION
        "The value of tSyncIfTimingAdmPTPAdminStatus specifies the desired
         administrative status of the Precision Timing Protocol (PTP) timing
         reference."
    DEFVAL      { outOfService }
    ::= { tSyncIfTimingAdmEntry 26 }

tSyncIfTimingAdmPTPCfgQltyLevel  OBJECT-TYPE
    SYNTAX      TmnxSSMQualityLevel
    MAX-ACCESS  read-create
    STATUS      current
    DESCRIPTION
        "The value of tSyncIfTimingAdmPTPCfgQltyLevel specifies the configured
         Quality Level of the Precision Timing Protocol (PTP). A value of
         'unknown (0)' specifies PTP is not forced to a specific quality level."
    DEFVAL      { unknown }
    ::= { tSyncIfTimingAdmEntry 27 }

tSyncIfTimingAdmBITSOutSource    OBJECT-TYPE
    SYNTAX      TmnxBITSOutSource
    MAX-ACCESS  read-create
    STATUS      current
    DESCRIPTION
        "The value of tSyncIfTimingAdmBITSOutSource specifies the source of the
         BITS (Building Integrated Timing Supply) output.

         In an XRS-40 system, the extension chassis is synchronized with the
         master chassis via the BITS ports.  Two modes of operation are
         permitted:
         1)  The BITS output ports of the master chassis CPMs are connected to
             the BITS input ports of the extension chassis CPMs.  In this mode,
             tSyncIfTimingAdmBITSOutSource should be set to 'internalClock(2)',
             to ensure that a valid clock signal is transmitted on the master
             chassis's CPMs' BITS output ports.
         2)  The BITS input ports of all 4 CPMs are connected to external BITS
             equipment.  In this mode, the customer may connect the master
             chassis's BITS output ports to the external BITS equipment's input
             ports.  This allows for recovered line references to be provided as
             a frequency source into the external BITS equipment following the
             inter-site synchronization mode of SDH/SONET.  In this case,
             tSyncIfTimingAdmBITSOutSource should be set to 'lineRef(1)'."
    DEFVAL      { lineRef }
    ::= { tSyncIfTimingAdmEntry 28 }

tSyncIfTimingAdmBITSOutQlMin     OBJECT-TYPE
    SYNTAX      TmnxSSMQualityLevel
    MAX-ACCESS  read-create
    STATUS      current
    DESCRIPTION
        "The value of tSyncIfTimingAdmBITSOutQlMin specifies the minimum
         quality level that a signal must have for it to be selected for BITS
         output. This can be used to ensure that the signal has traceability to
         a source with at least a specific quality level so that the attached
         equipment can function properly.

         A value of 'unknown (0)' indicates that there is no minimum quality
         level.

         Values: 'smc (7)', st4 (8)', 'dus (9)', 'dnu (14)', 'inv (15)', 'pno
         (16)', and 'failed (19)' are not supported for this object."
    DEFVAL      { unknown }
    ::= { tSyncIfTimingAdmEntry 29 }

tSyncIfTimingAdmBITSOutSquelch   OBJECT-TYPE
    SYNTAX      TruthValue
    MAX-ACCESS  read-create
    STATUS      current
    DESCRIPTION
        "The value of tSyncIfTimingAdmBITSOutSquelch specifies whether or not
         to squelch the output signal. This object is only valid when there is
         no valid reference selected.

         If the value is 'true (1)' and there is no valid reference, then no
         signal is sent out the port.

         If the value is 'false (2)' and there is no valid reference, then the
         AIS signal is presented along with the QL-DNU/QL-DUS SSM if the signal
         format supports SSM."
    DEFVAL      { false }
    ::= { tSyncIfTimingAdmEntry 30 }

tSyncIfTimingAdmQlMin            OBJECT-TYPE
    SYNTAX      TmnxSSMQualityLevel
    MAX-ACCESS  read-create
    STATUS      current
    DESCRIPTION
        "The value of tSyncIfTimingAdmQlMin specifies the minimum acceptable
         quality level that a signal must have for it to be considered for
         selection by the system timing module.

         A value of 'unknown (0)' indicates that there is no minimum quality
         level.

         Values: 'st4 (8)', 'dus (9)', 'prc (10)', 'dnu (14)', 'inv (15)', 'pno
         (16)', and 'failed (19)' are not supported for this object."
    DEFVAL      { unknown }
    ::= { tSyncIfTimingAdmEntry 32 }

tSyncIfTimingAdmWaitToRestorTime OBJECT-TYPE
    SYNTAX      Unsigned32 (0..12)
    UNITS       "minutes"
    MAX-ACCESS  read-create
    STATUS      current
    DESCRIPTION
        "The value of tSyncIfTimingAdmWaitToRestorTime specifies the time, in
         minutes, that a previously failed input reference must be valid before
         it will be used for either the BITS output or the central clock input
         reference.

         A value of '0' indicates that the wait-to-restore timer is disabled."
    DEFVAL      { 0 }
    ::= { tSyncIfTimingAdmEntry 33 }

tSyncIfTimingAdmChangedMask      OBJECT-TYPE
    SYNTAX      BITS {
        tSyncIfTimingAdmRevert           (0),
        tSyncIfTimingAdmRefOrder1        (1),
        tSyncIfTimingAdmRefOrder2        (2),
        tSyncIfTimingAdmRef1SrcPort      (3),
        tSyncIfTimingAdmRef1AdminStatus  (4),
        tSyncIfTimingAdmRef2SrcPort      (5),
        tSyncIfTimingAdmRef2AdminStatus  (6),
        tSyncIfTimingAdmChanged          (7),
        tSyncIfTimingAdmRefOrder3        (8),
        tSyncIfTimingAdmBITSIfType       (9),
        tSyncIfTimingAdmBITSAdminStatus  (10),
        tSyncIfTimingAdmRef1SrcHw        (11),
        tSyncIfTimingAdmRef1BITSIfType   (12),
        tSyncIfTimingAdmRef2SrcHw        (13),
        tSyncIfTimingAdmRef2BITSIfType   (14),
        tSyncIfTimingAdmBITSOutAdmStatus (15),
        tSyncIfTimingAdmBITSOutLineLen   (16),
        tSyncIfTimingAdmRef1CfgQltyLevel (17),
        tSyncIfTimingAdmRef2CfgQltyLevel (18),
        tSyncIfTimingAdmBITSCfgQltyLevel (19),
        tSyncIfTimingAdmRef1NationalUse  (20),
        tSyncIfTimingAdmRef2NationalUse  (21),
        tSyncIfTimingAdmBITSNationalUse  (22),
        tSyncIfTimingAdmQLSelection      (23),
        tSyncIfTimingAdmRefOrder4        (24),
        tSyncIfTimingAdmPTPAdminStatus   (25),
        tSyncIfTimingAdmPTPCfgQltyLevel  (26),
        tSyncIfTimingAdmBITSOutSource    (27),
        tSyncIfTimingAdmBITSOutQlMin     (28),
        tSyncIfTimingAdmBITSOutSquelch   (29),
        tSyncIfTimingAdmHoldOffTime      (30),
        tSyncIfTimingAdmQlMin            (31),
        tSyncIfTimingAdmWaitToRestorTime (32),
        tSyncIfTimingAdmChangedMask      (33),
        tSyncIfTimingAdmSyncECfgQltyLevl (34),
        tSyncIfTimingAdmSyncEAdminStatus (35),
        tSyncIfTimingAdmRefOrder5        (36),
        tSyncIfTimingAdmGnssCfgQltyLevel (37),
        tSyncIfTimingAdmGnssAdminStatus  (38),
        tSyncIfTimingAdmRefOrder6        (39)
    }
    MAX-ACCESS  read-only
    STATUS      current
    DESCRIPTION
        "The value of tSyncIfTimingAdmChangedMask indicates a bitmask of which
         synchronous interface timing objects have been set, but not committed.

         The agent sets these bits when an object in tSyncIfTimingAdmEntry is
         set. All bits are cleared when tmnxChassisAdminControlApply is set to
         'initialize (2)' or 'commit (3)'.

         Bits 'tSyncIfTimingAdmChanged (7)' and 'tSyncIfTimingAdmChangedMask
         (33)' are not valid. This object replaces the functionality of
         tSyncIfTimingAdmChanged."
    ::= { tSyncIfTimingAdmEntry 34 }

tSyncIfTimingAdmSyncECfgQltyLevl OBJECT-TYPE
    SYNTAX      TmnxSSMQualityLevel
    MAX-ACCESS  read-create
    STATUS      current
    DESCRIPTION
        "The value of tSyncIfTimingAdmSyncECfgQltyLevl specifies the configured
         Quality Level of the Synchronous Ethernet (SyncE) timing reference. A
         value of 'unknown (0)' specifies SyncE is not forced to a specific
         quality level."
    DEFVAL      { unknown }
    ::= { tSyncIfTimingAdmEntry 35 }

tSyncIfTimingAdmSyncEAdminStatus OBJECT-TYPE
    SYNTAX      TmnxPortAdminStatus
    MAX-ACCESS  read-create
    STATUS      current
    DESCRIPTION
        "The value of tSyncIfTimingAdmSyncEAdminStatus specifies the desired
         administrative status of the Synchronous Ethernet (SyncE) timing
         reference."
    DEFVAL      { outOfService }
    ::= { tSyncIfTimingAdmEntry 36 }

tSyncIfTimingAdmRefOrder5        OBJECT-TYPE
    SYNTAX      TmnxSETSRefSource
    MAX-ACCESS  read-create
    STATUS      current
    DESCRIPTION
        "The value of tSyncIfTimingAdmRefOrder5 specifies the fifth most
         preferred timing reference for the synchronous equipment timing
         subsystem."
    DEFVAL      { noReference }
    ::= { tSyncIfTimingAdmEntry 37 }

tSyncIfTimingAdmGnssCfgQltyLevel OBJECT-TYPE
    SYNTAX      TmnxSSMQualityLevel
    MAX-ACCESS  read-create
    STATUS      current
    DESCRIPTION
        "The value of tSyncIfTimingAdmGnssCfgQltyLevel specifies the configured
         Quality Level of the GNSS (Global Navigation Satellite System) timing
         reference. A value of 'unknown (0)' specifies GNSS is not forced to a
         specific quality level."
    DEFVAL      { unknown }
    ::= { tSyncIfTimingAdmEntry 38 }

tSyncIfTimingAdmGnssAdminStatus  OBJECT-TYPE
    SYNTAX      TmnxPortAdminStatus
    MAX-ACCESS  read-create
    STATUS      current
    DESCRIPTION
        "The value of tSyncIfTimingAdmGnssAdminStatus specifies the desired
         administrative status of the GNSS (Global Navigation Satellite System)
         timing reference."
    DEFVAL      { outOfService }
    ::= { tSyncIfTimingAdmEntry 39 }

tSyncIfTimingAdmRefOrder6        OBJECT-TYPE
    SYNTAX      TmnxSETSRefSource
    MAX-ACCESS  read-create
    STATUS      current
    DESCRIPTION
        "The value of tSyncIfTimingAdmRefOrder6 specifies the sixth most
         preferred timing reference for the synchronous equipment timing
         subsystem."
    DEFVAL      { noReference }
    ::= { tSyncIfTimingAdmEntry 40 }

tmnxHwConformance                OBJECT IDENTIFIER ::= { tmnxSRConfs 2 }

tmnxChassisConformance           OBJECT IDENTIFIER ::= { tmnxHwConformance 1 }

tmnxChassisCompliances           OBJECT IDENTIFIER ::= { tmnxChassisConformance 1 }

tmnxChassisV4v0Compliance        MODULE-COMPLIANCE
    STATUS      obsolete
    DESCRIPTION
        "The compliance statement for management of chassis features in the
         TIMETRA-CHASSIS-MIB."
    MODULE
        MANDATORY-GROUPS {
            tmnxChassisV3v0Group,
            tmnxCardV3v0Group,
            tmnxMDAV4v0Group,
            tmnxChassisNotificationV4v0Group
        }
    ::= { tmnxChassisCompliances 4 }

tmnxChassisComp7710              OBJECT IDENTIFIER ::= { tmnxChassisCompliances 5 }

tmnxChassisComp7710V3v0          MODULE-COMPLIANCE
    STATUS      obsolete
    DESCRIPTION
        "The compliance statement for management of chassis features for the
         7710 in the TIMETRA-CHASSIS-MIB."
    MODULE
        MANDATORY-GROUPS {
            tmnxChassisV3v0Group,
            tmnxCardV3v0Group,
            tmnxMDAV3v0Group,
            tmnxChassisNotificationV3v0Group,
            tmnx7710HwV3v0Group
        }
    ::= { tmnxChassisComp7710 1 }

tmnxChassisComp7710V5v0          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV4v0Group,
            tmnxChassisNotificationV4v0Group,
            tmnx7710HwV3v0Group
        }
    ::= { tmnxChassisComp7710 2 }

tmnxChassisComp7710V6v0          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV4v0Group,
            tmnxChassisNotificationV6v0Group,
            tmnx7710HwV3v0Group,
            tmnx77x0CESMDAV6v0Group,
            tmnxIPsecIsaGrpV6v0Group,
            tmnx7710SETSRefSrcHwV6v0Group,
            tmnxCardV6v0NamedPoolPlcyGroup,
            tmnxSyncV6v0Group,
            tmnxChassisV6v0Group
        }
    ::= { tmnxChassisComp7710 3 }

tmnxChassisComp7710V6v1          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV6v1Group,
            tmnxChassisNotificationV6v1Group,
            tmnx7710HwV3v0Group,
            tmnx77x0CESMDAV6v0Group,
            tmnxIPsecIsaGrpV6v0Group,
            tmnx7710SETSRefSrcHwV6v0Group,
            tmnxCardV6v0NamedPoolPlcyGroup,
            tmnxChassisV6v1Group,
            tmnxMdaXplV5v0Group,
            tmnxCardPchipV5v0Group,
            tmnxCardCamErrorV6v1Group,
            tmnxSyncV6v0Group,
            tmnxChassisHwV6v1Group
        }
    ::= { tmnxChassisComp7710 4 }

tmnxChassisComp7710V7v0          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV6v1Group,
            tmnxChassisNotificationV7v0Group,
            tmnx7710HwV3v0Group,
            tmnx77x0CESMDAV6v0Group,
            tmnxIPsecIsaGrpV6v0Group,
            tmnx7710SETSRefSrcHwV6v0Group,
            tmnxCardV6v0NamedPoolPlcyGroup,
            tmnxChassisV6v1Group,
            tmnxChassisV7v0Group,
            tmnxMdaXplV5v0Group,
            tmnxChassisUserModV7v0Group,
            tmnxCardPchipV5v0Group,
            tmnxCardCamErrorV6v1Group,
            tmnxCardV7v0Group,
            tmnxFPWredV7v0Group,
            tmnxIPsecV7v0Group,
            tmnxIPsecNotifV7v0Group,
            tmnxSyncV6v0Group,
            tmnxChassisHwV6v1Group
        }
    ::= { tmnxChassisComp7710 5 }

tmnxChassisComp7710V8v0          MODULE-COMPLIANCE
    STATUS      obsolete
    DESCRIPTION
        "The compliance statement for management of chassis features for the
         7710 in the TIMETRA-CHASSIS-MIB.

         This MODULE-COMPLIANCE has been replaced by tmnxChassisV9v0Compliance."
    MODULE
        MANDATORY-GROUPS {
            tmnxChassisV5v0Group,
            tmnxChassisV8v0Group,
            tmnxCardV3v0Group,
            tmnxMDAV6v1Group,
            tmnxChassisNotificationV7v0Group,
            tmnx7710HwV3v0Group,
            tmnx77x0CESMDAV6v0Group,
            tmnxIPsecIsaGrpV6v0Group,
            tmnx7710SETSRefSrcHwV6v0Group,
            tmnxCardV6v0NamedPoolPlcyGroup,
            tmnxChassisV6v1Group,
            tmnxChassisV7v0Group,
            tmnxMdaXplV5v0Group,
            tmnxChassisUserModV7v0Group,
            tmnxCardPchipV5v0Group,
            tmnxCardPchipV8v0Group,
            tmnxCardCamErrorV6v1Group,
            tmnxCardV7v0Group,
            tmnxFPWredV7v0Group,
            tmnxIPsecV7v0Group,
            tmnxIPsecNotifV7v0Group,
            tmnxSyncIfTimingV8v0Group,
            tmnxSyncV6v0Group,
            tmnxSyncIfTimingNotifV8v0Group,
            tmnxChassisHwV6v1Group
        }
    ::= { tmnxChassisComp7710 6 }

tmnxChassisV5v0Compliance        MODULE-COMPLIANCE
    STATUS      obsolete
    DESCRIPTION
        "The compliance statement for management of chassis features in the
         TIMETRA-CHASSIS-MIB."
    MODULE
        MANDATORY-GROUPS {
            tmnxChassisV5v0Group,
            tmnxCardV3v0Group,
            tmnxMDAV4v0Group,
            tmnxChassisNotificationV4v0Group,
            tmnxChassisNotificationV5v0Group,
            tmnxMdaXplV5v0Group,
            tmnxCardPchipV5v0Group
        }
    ::= { tmnxChassisCompliances 6 }

tmnxChassis7750V6v0Compliance    MODULE-COMPLIANCE
    STATUS      obsolete
    DESCRIPTION
        "The compliance statement for management of chassis features on the
         7750 in the TIMETRA-CHASSIS-MIB."
    MODULE
        MANDATORY-GROUPS {
            tmnxChassisV5v0Group,
            tmnxCardV3v0Group,
            tmnxMDAV4v0Group,
            tmnxChassisNotificationV6v0Group,
            tmnx77x0CESMDAV6v0Group,
            tmnxCardV6v0NamedPoolPlcyGroup,
            tmnxIPsecIsaGrpV6v0Group,
            tmnxMDAMcPathMgmtV6v0Group,
            tmnxMdaXplV5v0Group,
            tmnxCardPchipV5v0Group,
            tmnxSyncV6v0Group,
            tmnxChassisV6v0Group
        }
    ::= { tmnxChassisCompliances 7 }

tmnxChassis7450V6v0Compliance    MODULE-COMPLIANCE
    STATUS      obsolete
    DESCRIPTION
        "The compliance statement for management of chassis features on the
         7450 in the TIMETRA-CHASSIS-MIB."
    MODULE
        MANDATORY-GROUPS {
            tmnxChassisV5v0Group,
            tmnxCardV3v0Group,
            tmnxMDAV4v0Group,
            tmnxCardV6v0NamedPoolPlcyGroup,
            tmnxChassisNotificationV6v0Group,
            tmnxMDAMcPathMgmtV6v0Group,
            tmnxMdaXplV5v0Group,
            tmnxCardPchipV5v0Group,
            tmnxSyncV6v0Group,
            tmnxChassisV6v0Group
        }
    ::= { tmnxChassisCompliances 8 }

tmnxChassis7750V6v1Compliance    MODULE-COMPLIANCE
    STATUS      obsolete
    DESCRIPTION
        "The compliance statement for management of chassis features on the
         7750 in the TIMETRA-CHASSIS-MIB."
    MODULE
        MANDATORY-GROUPS {
            tmnxChassisV5v0Group,
            tmnxCardV3v0Group,
            tmnxMDAV6v1Group,
            tmnxChassisNotificationV6v0Group,
            tmnx77x0CESMDAV6v0Group,
            tmnxCardV6v0NamedPoolPlcyGroup,
            tmnxIPsecIsaGrpV6v0Group,
            tmnxMDAMcPathMgmtV6v0Group,
            tmnxChassisV6v1Group,
            tmnxFPMcPathMgmtV6v1Group,
            tmnxMDACcagV6v1Group,
            tmnxMdaXplV5v0Group,
            tmnxCardPchipV5v0Group,
            tmnxCardCamErrorV6v1Group,
            tmnxSyncV6v0Group,
            tmnxChassisHwV6v1Group
        }
    ::= { tmnxChassisCompliances 9 }

tmnxChassis7450V6v1Compliance    MODULE-COMPLIANCE
    STATUS      obsolete
    DESCRIPTION
        "The compliance statement for management of chassis features on the
         7450 in the TIMETRA-CHASSIS-MIB."
    MODULE
        MANDATORY-GROUPS {
            tmnxChassisV5v0Group,
            tmnxCardV3v0Group,
            tmnxMDAV6v1Group,
            tmnxCardV6v0NamedPoolPlcyGroup,
            tmnxChassisNotificationV6v0Group,
            tmnxMDAMcPathMgmtV6v0Group,
            tmnxChassisV6v1Group,
            tmnxFPMcPathMgmtV6v1Group,
            tmnxMDACcagV6v1Group,
            tmnxMdaXplV5v0Group,
            tmnxCardPchipV5v0Group,
            tmnxCardCamErrorV6v1Group,
            tmnxSyncV6v0Group,
            tmnxChassisHwV6v1Group
        }
    ::= { tmnxChassisCompliances 10 }

tmnxChassis7750V7v0Compliance    MODULE-COMPLIANCE
    STATUS      obsolete
    DESCRIPTION
        "The compliance statement for management of chassis features on the
         7750 in the TIMETRA-CHASSIS-MIB."
    MODULE
        MANDATORY-GROUPS {
            tmnxChassisV5v0Group,
            tmnxCardV3v0Group,
            tmnxMDAV6v1Group,
            tmnxChassisNotificationV7v0Group,
            tmnx77x0CESMDAV6v0Group,
            tmnxCardV6v0NamedPoolPlcyGroup,
            tmnxIPsecIsaGrpV6v0Group,
            tmnxMDAMcPathMgmtV6v0Group,
            tmnxChassisV6v1Group,
            tmnxFPMcPathMgmtV6v1Group,
            tmnxMDACcagV6v1Group,
            tmnxChassisUserModV7v0Group,
            tmnxCardV7v0Group,
            tmnxFPWredV7v0Group,
            tmnxIPsecV7v0Group,
            tmnxIPsecNotifV7v0Group,
            tmnxMdaXplV5v0Group,
            tmnxCardPchipV5v0Group,
            tmnxCardCamErrorV6v1Group,
            tmnxSyncV6v0Group,
            tmnxChassisHwV6v1Group
        }
    ::= { tmnxChassisCompliances 11 }

tmnxChassis7450V7v0Compliance    MODULE-COMPLIANCE
    STATUS      obsolete
    DESCRIPTION
        "The compliance statement for management of chassis features on the
         7450 in the TIMETRA-CHASSIS-MIB."
    MODULE
        MANDATORY-GROUPS {
            tmnxChassisV5v0Group,
            tmnxCardV3v0Group,
            tmnxMDAV6v1Group,
            tmnxCardV6v0NamedPoolPlcyGroup,
            tmnxChassisNotificationV7v0Group,
            tmnxMDAMcPathMgmtV6v0Group,
            tmnxChassisV6v1Group,
            tmnxFPMcPathMgmtV6v1Group,
            tmnxMDACcagV6v1Group,
            tmnxChassisUserModV7v0Group,
            tmnxCardV7v0Group,
            tmnxFPWredV7v0Group,
            tmnxMdaXplV5v0Group,
            tmnxCardPchipV5v0Group,
            tmnxCardCamErrorV6v1Group,
            tmnxSyncV6v0Group,
            tmnxChassisHwV6v1Group
        }
    ::= { tmnxChassisCompliances 12 }

tmnxChassis7x50V8v0Compliance    MODULE-COMPLIANCE
    STATUS      obsolete
    DESCRIPTION
        "The compliance statement for management of chassis features on the
         7x50 in the TIMETRA-CHASSIS-MIB."
    MODULE
        MANDATORY-GROUPS {
            tmnxChassisV5v0Group,
            tmnxChassisV8v0Group,
            tmnxCardV3v0Group,
            tmnxMDAV6v1Group,
            tmnxChassisNotificationV7v0Group,
            tmnx77x0CESMDAV6v0Group,
            tmnxCardV6v0NamedPoolPlcyGroup,
            tmnxIPsecIsaGrpV6v0Group,
            tmnx7710HwV3v0Group,
            tmnx7710SETSRefSrcHwV6v0Group,
            tmnxMDAMcPathMgmtV6v0Group,
            tmnxChassisV6v1Group,
            tmnxChassisV7v0Group,
            tmnxFPMcPathMgmtV6v1Group,
            tmnxMDACcagV6v1Group,
            tmnxChassisUserModV7v0Group,
            tmnxCardV7v0Group,
            tmnxFPWredV7v0Group,
            tmnxIPsecV7v0Group,
            tmnxIPsecNotifV7v0Group,
            tmnxSyncIfTimingV8v0Group,
            tmnxChassisMixedModeIomV8v0Group,
            tmnxMdaXplV5v0Group,
            tmnxCardPchipV5v0Group,
            tmnxCardPchipV8v0Group,
            tmnxCardCamErrorV6v1Group,
            tmnxSyncV6v0Group,
            tmnxSyncIfTimingNotifV8v0Group,
            tmnxChassisHwV6v1Group
        }
    ::= { tmnxChassisCompliances 13 }

tmnxChassisV9v0Compliance        MODULE-COMPLIANCE
    STATUS      obsolete
    DESCRIPTION
        "The compliance statement for management of chassis features on SROS
         series systems in the TIMETRA-CHASSIS-MIB."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV3v0Group,
            tmnxCardV6v0NamedPoolPlcyGroup,
            tmnxCardV7v0Group,
            tmnxChassisHwEventGroup,
            tmnxChassisHwEventNotifyGroup,
            tmnxChassisHwV6v1Group,
            tmnxChassisHwV9v0Group,
            tmnxChassisMixedModeIomV8v0Group,
            tmnxChassisNotificationV7v0Group,
            tmnxChassisNotificationV9v0Group,
            tmnxChassisUserModV7v0Group,
            tmnxChassisV5v0Group,
            tmnxChassisV6v1Group,
            tmnxChassisV7v0Group,
            tmnxChassisV8v0Group,
            tmnxFPMcPathMgmtV6v1Group,
            tmnxFPWredV7v0Group,
            tmnxIPsecIsaGrpV6v0Group,
            tmnxIPsecNotifV7v0Group,
            tmnxIPsecV7v0Group,
            tmnxMDACcagV6v1Group,
            tmnxMDAMcPathMgmtV6v0Group,
            tmnxMDAV6v1Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group
        }
    ::= { tmnxChassisCompliances 14 }

tmnxChassisV10v0Compliance       MODULE-COMPLIANCE
    STATUS      obsolete
    DESCRIPTION
        "The compliance statement for management of chassis features on SROS
         series systems in the TIMETRA-CHASSIS-MIB."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV3v0Group,
            tmnxCardV6v0NamedPoolPlcyGroup,
            tmnxCardV7v0Group,
            tmnxChassisHwEventGroup,
            tmnxChassisHwEventNotifyGroup,
            tmnxChassisHwV6v1Group,
            tmnxChassisHwV9v0Group,
            tmnxChassisMixedModeIomV8v0Group,
            tmnxChassisNotificationV7v0Group,
            tmnxChassisNotificationV9v0Group,
            tmnxChassisUserModV7v0Group,
            tmnxChassisV5v0Group,
            tmnxChassisV6v1Group,
            tmnxChassisV7v0Group,
            tmnxChassisV8v0Group,
            tmnxChassisV10v0Group,
            tmnxFPMcPathMgmtV6v1Group,
            tmnxFPWredV7v0Group,
            tmnxIPsecIsaGrpV6v0Group,
            tmnxIPsecNotifV7v0Group,
            tmnxIPsecV7v0Group,
            tmnxMDACcagV6v1Group,
            tmnxMDAMcPathMgmtV6v0Group,
            tmnxMDAV6v1Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxCardV10v0Group,
            tmnxIpsecV10v0Group,
            tmnxFPQGrpGroup,
            tmnxFPQGrpV10v0R4Group,
            tmnxMdaV10v0Group,
            tmnxChassisNotifyV10v0Group,
            tmnxChassisHwEventGroupV10v0,
            tmnxChassisHwEventNotifyGrpV10v0
        }
    ::= { tmnxChassisCompliances 15 }

tmnxChassisV11v0Compliance       MODULE-COMPLIANCE
    STATUS      obsolete
    DESCRIPTION
        "The compliance statement for management of chassis features on SROS
         series systems in the TIMETRA-CHASSIS-MIB release 11.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyV10v0Group,
            tmnxChassisPowerMgmtGroup,
            tmnxChassisPowerMgmtNotifyGroup,
            tmnxChassisPowerV11v0Group,
            tmnxChassisQGrpOvrGroup,
            tmnxChassisSwitchFabNtfyV11v0Grp,
            tmnxChassisUserModV7v0Group,
            tmnxChassisV10v0Group,
            tmnxChassisV11v0Group,
            tmnxChassisV6v1Group,
            tmnxChassisV7v0Group,
            tmnxChassisV8v0Group,
            tmnxFPDCpuProtV11v0R0Group,
            tmnxFPDcpNotifyObjsV11v0Group,
            tmnxFPDcpNotifyV11v0Group,
            tmnxFPMcPathMgmtV6v1Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAMcPathMgmtV6v0Group,
            tmnxMDAV6v1Group,
            tmnxMdaV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxFPPoolSizingV11v0Group,
            tmnxCpmCardCmplxMemErrV9v0Group,
            tmnxCardCmplQChipMemErrV9v0Group,
            tmnxCardCmplChipIfErrV9v0Group,
            tmnxChassisSmartPeqV11v0Group,
            tmnxChassisSmartPeqNtfyV11v0Grp,
            tmnxChassisHwEventGroupV10v0,
            tmnxChassisHwEventNotifyGrpV10v0,
            tmnxCpmCardRebootHoldV11v0Group
        }
    ::= { tmnxChassisCompliances 16 }

tmnxChassisV12v0Compliance       MODULE-COMPLIANCE
    STATUS      obsolete
    DESCRIPTION
        "The compliance statement for management of chassis features on SROS
         series systems in the TIMETRA-CHASSIS-MIB release 12.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisPowerNotifV12v0Group,
            tmnxChassisQGrpOvrGroup,
            tmnxChassisSwitchFabNtfyV11v0Grp,
            tmnxChassisUserModV7v0Group,
            tmnxChassisV10v0Group,
            tmnxChassisV11v0Group,
            tmnxChassisV6v1Group,
            tmnxChassisV7v0Group,
            tmnxChassisV8v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAMcPathMgmtV6v0Group,
            tmnxMDAV6v1Group,
            tmnxMdaV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxChassisResourceV12v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassisSmartPeqNtfyV11v0Grp,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardResetOnRecoverErGrp,
            tmnxMDAResetOnRecoverErGrp,
            tmnxCpmMemSizeNotifGroupV12v0,
            tmnxCpmPChipFcsObjGroupV12v0
        }
    ::= { tmnxChassisCompliances 17 }

tmnxChassisV13v0Compliance       MODULE-COMPLIANCE
    STATUS      obsolete
    DESCRIPTION
        "The compliance statement for management of chassis features on SROS
         series systems in the TIMETRA-CHASSIS-MIB release 13.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisPowerNotifV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV8v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAMcPathMgmtV6v0Group,
            tmnxMDAV6v1Group,
            tmnxMdaV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassisSmartPeqNtfyV11v0Grp,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxChassisResourceV13v0Group,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0
        }
    ::= { tmnxChassisCompliances 18 }

tmnxChassisV14v0Compliance       MODULE-COMPLIANCE
    STATUS      obsolete
    DESCRIPTION
        "The compliance statement for management of chassis features on SROS
         series systems in the TIMETRA-CHASSIS-MIB release 14.0."
    MODULE
        MANDATORY-GROUPS {
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0
        }
    ::= { tmnxChassisCompliances 19 }

tmnxChassisV15v0Compliance       MODULE-COMPLIANCE
    STATUS      obsolete
    DESCRIPTION
        "The compliance statement for management of chassis features on SROS
         series systems in the TIMETRA-CHASSIS-MIB release 15.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV8v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAV15v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxChassisResourceV15v0Group,
            tmnxCardFPResIngV15v0QGroup,
            tmnxCardFPResEgrV15v0QGroup,
            tmnxIPsecIsaGrpV15v0Group,
            tmnxPhysChassisPCMGroupV15v0,
            tmnxMinFpGenerationGroupV15v0,
            tmnxPhysChassPCMNotifGroupV15v0
        }
    ::= { tmnxChassisCompliances 20 }

tmnxChassisV16v0Compliance       MODULE-COMPLIANCE
    STATUS      obsolete
    DESCRIPTION
        "The compliance statement for management of chassis features on SROS
         series systems in the TIMETRA-CHASSIS-MIB release 16.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV8v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAV15v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxCardFPResIngV15v0QGroup,
            tmnxCardFPResEgrV15v0QGroup,
            tmnxIPsecIsaGrpV15v0Group,
            tmnxPhysChassisPCMGroupV15v0,
            tmnxMinFpGenerationGroupV15v0,
            tmnxPhysChassPCMNotifGroupV15v0,
            tmnxCardV16v0Group,
            tmnxCardComplexGroupV16v0,
            tmnxChassisGroupV16v0,
            tmnxChassisResourceV16v0Group,
            tmnxChassisCardLevelGroupV15v1,
            tmnxPhysChassisPMGroupV16v0,
            tmnxChassisGnssGroup,
            tmnxChassisGnssNotifGroup,
            tmnxMdaFlexGroupV16v0,
            tmnxChassisMdaLevelGroupV15v1,
            tmnxPhysChassisPMNotifGroupV16v0,
            tmnxNearFullNotifGroupV16v0,
            tmnxCardV16v0ObsoleteGroup,
            tmnxCardV16v0FpgaSoftErrNotifGrp,
            tmnxMDAIsaTnlStatsV16v0Group,
            tmnxCardPowerSaveGroupV16v0
        }
    ::= { tmnxChassisCompliances 21 }

tmnxChassisV15v1Compliance       MODULE-COMPLIANCE
    STATUS      obsolete
    DESCRIPTION
        "The compliance statement for management of chassis features on SROS
         series systems in the TIMETRA-CHASSIS-MIB release 15.1."
    MODULE
        MANDATORY-GROUPS {
            tmnxBluetoothGroupV15v1,
            tmnxOverloadNotifGroupV15v1,
            tmnxChassisSystemProfGroupV15v1,
            tmnxCardResourceV15v1Group,
            tmnxBluetoothNotifGroupV15v1,
            tmnxFPResourceV15v1Group
        }
    ::= { tmnxChassisCompliances 22 }

tmnxChassisV16v5Compliance       MODULE-COMPLIANCE
    STATUS      current
    DESCRIPTION
        "The compliance statement for management of chassis features on SROS
         series systems in the TIMETRA-CHASSIS-MIB release 16.5."
    MODULE
        MANDATORY-GROUPS {
            tmnxCardEncapGrpV16v5Group
        }
    ::= { tmnxChassisCompliances 23 }

tmnxChassisV19Compliance         MODULE-COMPLIANCE
    STATUS      obsolete
    DESCRIPTION
        "The compliance statement for management of chassis features on SROS
         series systems in the TIMETRA-CHASSIS-MIB release 19."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV19v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxCardFPResIngV15v0QGroup,
            tmnxCardFPResEgrV15v0QGroup,
            tmnxIPsecIsaGrpV15v0Group,
            tmnxPhysChassisPCMGroupV15v0,
            tmnxMinFpGenerationGroupV15v0,
            tmnxPhysChassPCMNotifGroupV15v0,
            tmnxCardV16v0Group,
            tmnxCardComplexGroupV16v0,
            tmnxChassisGroupV16v0,
            tmnxChassisResourceV16v0Group,
            tmnxChassisCardLevelGroupV15v1,
            tmnxPhysChassisPMGroupV16v0,
            tmnxChassisGnssGroup,
            tmnxChassisGnssNotifGroup,
            tmnxMdaFlexGroupV16v0,
            tmnxChassisMdaLevelGroupV15v1,
            tmnxPhysChassisPMNotifGroupV16v0,
            tmnxNearFullNotifGroupV16v0,
            tmnxCardV16v0ObsoleteGroup,
            tmnxCardV16v0FpgaSoftErrNotifGrp,
            tmnxMDAIsaTnlStatsV16v0Group,
            tmnxCardPowerSaveGroupV16v0,
            tmnxEsaGroup,
            tmnxFPNetworkIngressGroupV19v5,
            tmnxCardV19v5Group,
            tmnxSyncIfTimingV19v0Group,
            tmnxMDAV19v0Group,
            tmnxTunnelGrpEsaVmGroupV19v0,
            tmnxChassisResEgrV19v0Group,
            tmnxChassisResEgrRmrkV19v0Group,
            tmnxChassisResIngClassV19v0Group,
            tmnxChassisResDynCAMV19v0Group,
            tmnxChassisResIpMacCAMV19v0Group,
            tmnxChassisCoreResV19v0Group,
            tmnxSyncIfTimingV19v0NotifGroup,
            tmnxHwEventGroupV19v0,
            tmnxHwEventNotifyObjsGrpV19v0,
            tmnxHwEventNotifGroupV19v0,
            tmnxTunnelGrpEsaVmNotifGrpV19v0,
            tmnxEsaNotificationObjectGroup,
            tmnxEsaNotificationGroup,
            tmnxCardSapInstV19v0Group,
            tmnxChassisResQMgmtV19v0Group,
            tmnxSapResourceUsageV19v0Group,
            tmnxIPv6MCastCamV19v0Group,
            tmnxChassisCoreResPlcrV19v0Group
        }
    ::= { tmnxChassisCompliances 24 }

tmnxChassisV20Compliance         MODULE-COMPLIANCE
    STATUS      obsolete
    DESCRIPTION
        "The compliance statement for management of chassis features on SROS
         series systems in the TIMETRA-CHASSIS-MIB release 20."
    MODULE
        MANDATORY-GROUPS {
            tmnxXiomGroupV20v0,
            tmnxChassisNotifGroupV20v0,
            tmnx7710HwV3v0Group,
            tmnx7710SETSRefSrcHwV6v0Group,
            tmnxAtmGroup,
            tmnxCardCamErrorV6v1Group,
            tmnxCardPchipV5v0Group,
            tmnxCardPchipV8v0Group,
            tmnxCardV10v0Group,
            tmnxCardV3v0Group,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV19v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxCardFPResIngV15v0QGroup,
            tmnxCardFPResEgrV15v0QGroup,
            tmnxIPsecIsaGrpV15v0Group,
            tmnxPhysChassisPCMGroupV15v0,
            tmnxMinFpGenerationGroupV15v0,
            tmnxPhysChassPCMNotifGroupV15v0,
            tmnxCardV16v0Group,
            tmnxCardComplexGroupV16v0,
            tmnxChassisGroupV16v0,
            tmnxChassisCardLevelGroupV15v1,
            tmnxPhysChassisPMGroupV16v0,
            tmnxChassisGnssGroup,
            tmnxChassisGnssNotifGroup,
            tmnxMdaFlexGroupV16v0,
            tmnxChassisMdaLevelGroupV15v1,
            tmnxPhysChassisPMNotifGroupV16v0,
            tmnxNearFullNotifGroupV16v0,
            tmnxCardV16v0ObsoleteGroup,
            tmnxCardV16v0FpgaSoftErrNotifGrp,
            tmnxMDAIsaTnlStatsV16v0Group,
            tmnxCardPowerSaveGroupV16v0,
            tmnxEsaGroup,
            tmnxFPNetworkIngressGroupV19v5,
            tmnxCardV19v5Group,
            tmnxSyncIfTimingV19v0Group,
            tmnxMDAV19v0Group,
            tmnxTunnelGrpEsaVmGroupV19v0,
            tmnxChassisResEgrV19v0Group,
            tmnxChassisResEgrRmrkV19v0Group,
            tmnxChassisResIngClassV19v0Group,
            tmnxChassisResDynCAMV19v0Group,
            tmnxChassisResIpMacCAMV19v0Group,
            tmnxChassisCoreResV19v0Group,
            tmnxSyncIfTimingV19v0NotifGroup,
            tmnxHwEventGroupV19v0,
            tmnxHwEventNotifyObjsGrpV19v0,
            tmnxHwEventNotifGroupV19v0,
            tmnxTunnelGrpEsaVmNotifGrpV19v0,
            tmnxEsaNotificationObjectGroup,
            tmnxEsaNotificationGroup,
            tmnxCardSapInstV19v0Group,
            tmnxCardFPQosPolicyV20v0Group,
            tmnxChassisResQMgmtV19v0Group,
            tmnxSapResourceUsageV19v0Group,
            tmnxChassisV20v0ObsoleteGroup,
            tmnx77x0CESMDAV20v0Group,
            tmnxIPv6MCastCamV19v0Group,
            tmnxChassisResourceV20v0Group,
            tmnxSyncIfTimingV20v0ObsoleteGrp,
            tmnxSyncIfTimingGnssV20v0Group,
            tmnxChassisResEgrRmrkV20v0Group,
            tmnxSyncIfTimingV20v0NotifGroup,
            tmnxChassisDot1xHostV20v0Group,
            tmnxChassisResDepthMQV20v0Group,
            tmnxChassisFPQppbPolV20v0Group,
            tmnxChassisCoreResV20v0Group,
            tmnxFPNotificationV20Group,
            tmnxChassisCoreResPlcrV19v0Group,
            tmnxChassisIxrXFanV20v0Group
        }
    ::= { tmnxChassisCompliances 25 }

tmnxChassisV21Compliance         MODULE-COMPLIANCE
    STATUS      obsolete
    DESCRIPTION
        "The compliance statement for management of chassis features on SROS
         series systems in the TIMETRA-CHASSIS-MIB release 21."
    MODULE
        MANDATORY-GROUPS {
            tmnxXiomGroupV20v0,
            tmnxChassisNotifGroupV20v0,
            tmnx7710HwV3v0Group,
            tmnx7710SETSRefSrcHwV6v0Group,
            tmnxAtmGroup,
            tmnxCardCamErrorV6v1Group,
            tmnxCardPchipV5v0Group,
            tmnxCardPchipV8v0Group,
            tmnxCardV10v0Group,
            tmnxCardV3v0Group,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV19v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxCardFPResIngV15v0QGroup,
            tmnxCardFPResEgrV15v0QGroup,
            tmnxIPsecIsaGrpV15v0Group,
            tmnxPhysChassisPCMGroupV15v0,
            tmnxMinFpGenerationGroupV15v0,
            tmnxPhysChassPCMNotifGroupV15v0,
            tmnxCardV16v0Group,
            tmnxCardComplexGroupV16v0,
            tmnxChassisGroupV16v0,
            tmnxChassisCardLevelGroupV15v1,
            tmnxPhysChassisPMGroupV16v0,
            tmnxChassisGnssGroup,
            tmnxChassisGnssNotifGroup,
            tmnxMdaFlexGroupV16v0,
            tmnxChassisMdaLevelGroupV15v1,
            tmnxPhysChassisPMNotifGroupV16v0,
            tmnxNearFullNotifGroupV16v0,
            tmnxCardV16v0ObsoleteGroup,
            tmnxCardV16v0FpgaSoftErrNotifGrp,
            tmnxMDAIsaTnlStatsV16v0Group,
            tmnxCardPowerSaveGroupV16v0,
            tmnxEsaGroup,
            tmnxFPNetworkIngressGroupV19v5,
            tmnxCardV19v5Group,
            tmnxSyncIfTimingV19v0Group,
            tmnxMDAV21v0Group,
            tmnxTunnelGrpEsaVmGroupV19v0,
            tmnxChassisResEgrV19v0Group,
            tmnxChassisResEgrRmrkV19v0Group,
            tmnxChassisResIngClassV19v0Group,
            tmnxChassisResDynCAMV19v0Group,
            tmnxChassisResIpMacCAMV19v0Group,
            tmnxChassisCoreResV19v0Group,
            tmnxSyncIfTimingV19v0NotifGroup,
            tmnxHwEventGroupV19v0,
            tmnxHwEventNotifyObjsGrpV19v0,
            tmnxHwEventNotifGroupV19v0,
            tmnxTunnelGrpEsaVmNotifGrpV19v0,
            tmnxEsaNotificationObjectGroup,
            tmnxEsaNotificationGroup,
            tmnxCardSapInstV19v0Group,
            tmnxCardFPQosPolicyV20v0Group,
            tmnxChassisResQMgmtV19v0Group,
            tmnxSapResourceUsageV19v0Group,
            tmnxChassisV20v0ObsoleteGroup,
            tmnx77x0CESMDAV20v0Group,
            tmnxIPv6MCastCamV19v0Group,
            tmnxChassisResourceV21v0Group,
            tmnxSyncIfTimingV20v0ObsoleteGrp,
            tmnxSyncIfTimingGnssV20v0Group,
            tmnxChassisResEgrRmrkV20v0Group,
            tmnxSyncIfTimingV20v0NotifGroup,
            tmnxChassisDot1xHostV20v0Group,
            tmnxChassisResDepthMQV20v0Group,
            tmnxChassisFPQppbPolV20v0Group,
            tmnxChassisCoreResV20v0Group,
            tmnxFPNotificationV20Group,
            tmnxChassisCoreResPlcrV19v0Group,
            tmnxChassisIxrXFanV20v0Group,
            tmnxIpsecV21Group,
            tmnxMdaXConnectGroupV21,
            tmnxCoreDdctdPolicerResGroupV21,
            tmnxFPToFPStatGroupV21,
            tmnxChassisCoreResPlcrV19v0Group,
            tFPResEgrHwAggShaperV21v0Group,
            tCardResTLSMcastV21v0Group,
            tmnxChassisNotifGroupV21v0,
            tmnxChassisResIngClassV21v0Group,
            tmnxChassisResEgrRmrkV21v0Group,
            tmnxChassisResIngrMapsV21v0Group,
            tmnxChassisResEgrMapsV21v0Group,
            tmnxChassisResLagBundl1V21v0Grp,
            tmnxChassisResLagBundl2V21v0Grp,
            tmnxChassisResSysBundleV21v0Grp,
            tmnxIomRsrcNotifyObjsV21v0Grp,
            tmnxIomRsrcNotifyV21v0Grp,
            tmnxChassisResPerHostAutV21v0Grp,
            tmnxChassisDrpCntrJ1V21v0Group,
            tmnxChassisPwrMgmtV21v0Group,
            tmnxChassisResMacCamBnkV21v0Grp
        }
    ::= { tmnxChassisCompliances 26 }

tmnxChassisV22v0Compliance       MODULE-COMPLIANCE
    STATUS      obsolete
    DESCRIPTION
        "The compliance statement for management of chassis features on SROS
         series systems in the TIMETRA-CHASSIS-MIB release 22."
    MODULE
        MANDATORY-GROUPS {
            tmnxMinFpGenerationV22v0Group,
            tmnxHwAggShpNotifyObjsV22v0Grp,
            tmnxHwAggShpNotifGroupV22v0,
            tmnxEsa400gGroupV22v0,
            tmnxEsaHwStatusMonGroupV22v0,
            tmnxChassisGnssGroupV22v0,
            tmnxChassPSStateGroupV22v0,
            tmnxChassisResPortFwdIdGrpV22v0,
            tmnxChassisResShardPlcrGrpV22v0,
            tmnxFPCoreResUsgStatsGroupV22v0,
            tmnxHwTempGroupV22v0,
            tmnxCamOverloadGroupV22v0,
            tmnxSyncIfTimingGroupV22v0,
            tChassisResShardPlcrStatGrpV22v0,
            tmnxCpmSecureBootGroupV22v0,
            tmnxIomRsrcNotifyObjsV22v0Grp,
            tmnxIomRsrcNotifyV22v0Grp,
            tmnxIsaGrpESPSeqNumGroupV22v0,
            tFPResOversubGroupV22v0,
            tmnxFPResOversubNotifGroupV22v0,
            tmnxEsaHwStatusMonNotifGrpV22v0,
            tFPResEgrHwAggShaperV22v0Group,
            tmnxEsaStallNotifV22v0Grp
        }
    ::= { tmnxChassisCompliances 27 }

tmnxChassisV23v0Compliance       MODULE-COMPLIANCE
    STATUS      obsolete
    DESCRIPTION
        "The compliance statement for management of chassis features on SROS
         series systems in the TIMETRA-CHASSIS-MIB release 23."
    MODULE
        MANDATORY-GROUPS {
            tmnxChassisIxrResourceGroup,
            tmnxXiomGroupV23v0,
            tmnxCoreDdctdPolicerResGroupV23,
            tmnxChassisRebootReqdGroupV23v0,
            tmnxXiomGroupV20v0,
            tmnxChassisNotifGroupV20v0,
            tmnx7710HwV3v0Group,
            tmnx7710SETSRefSrcHwV6v0Group,
            tmnxCardCamErrorV6v1Group,
            tmnxCardPchipV5v0Group,
            tmnxCardPchipV8v0Group,
            tmnxCardV10v0Group,
            tmnxCardV3v0Group,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV19v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxCardFPResIngV15v0QGroup,
            tmnxCardFPResEgrV15v0QGroup,
            tmnxIPsecIsaGrpV15v0Group,
            tmnxPhysChassisPCMGroupV15v0,
            tmnxMinFpGenerationGroupV15v0,
            tmnxPhysChassPCMNotifGroupV15v0,
            tmnxCardV16v0Group,
            tmnxCardComplexGroupV16v0,
            tmnxChassisGroupV16v0,
            tmnxChassisCardLevelGroupV15v1,
            tmnxPhysChassisPMGroupV16v0,
            tmnxChassisGnssGroup,
            tmnxChassisGnssNotifGroup,
            tmnxMdaFlexGroupV16v0,
            tmnxChassisMdaLevelGroupV15v1,
            tmnxPhysChassisPMNotifGroupV16v0,
            tmnxNearFullNotifGroupV16v0,
            tmnxCardV16v0ObsoleteGroup,
            tmnxCardV16v0FpgaSoftErrNotifGrp,
            tmnxMDAIsaTnlStatsV16v0Group,
            tmnxCardPowerSaveGroupV16v0,
            tmnxEsaGroup,
            tmnxFPNetworkIngressGroupV19v5,
            tmnxCardV19v5Group,
            tmnxSyncIfTimingV19v0Group,
            tmnxMDAV21v0Group,
            tmnxTunnelGrpEsaVmGroupV19v0,
            tmnxChassisResEgrV19v0Group,
            tmnxChassisResEgrRmrkV19v0Group,
            tmnxChassisResIngClassV19v0Group,
            tmnxChassisResDynCAMV19v0Group,
            tmnxChassisResIpMacCAMV19v0Group,
            tmnxChassisCoreResV19v0Group,
            tmnxSyncIfTimingV19v0NotifGroup,
            tmnxHwEventGroupV19v0,
            tmnxHwEventNotifyObjsGrpV19v0,
            tmnxHwEventNotifGroupV19v0,
            tmnxTunnelGrpEsaVmNotifGrpV19v0,
            tmnxEsaNotificationObjectGroup,
            tmnxEsaNotificationGroup,
            tmnxCardSapInstV19v0Group,
            tmnxCardFPQosPolicyV20v0Group,
            tmnxChassisResQMgmtV19v0Group,
            tmnxSapResourceUsageV23v0Group,
            tmnxChassisV20v0ObsoleteGroup,
            tmnx77x0CESMDAV20v0Group,
            tmnxIPv6MCastCamV19v0Group,
            tmnxChassisResourceV23v0Group,
            tmnxSyncIfTimingV20v0ObsoleteGrp,
            tmnxSyncIfTimingGnssV20v0Group,
            tmnxChassisResEgrRmrkV20v0Group,
            tmnxSyncIfTimingV20v0NotifGroup,
            tmnxChassisDot1xHostV20v0Group,
            tmnxChassisResDepthMQV20v0Group,
            tmnxChassisFPQppbPolV20v0Group,
            tmnxChassisCoreResV20v0Group,
            tmnxFPNotificationV20Group,
            tmnxChassisCoreResPlcrV19v0Group,
            tmnxChassisIxrXFanV20v0Group,
            tmnxIpsecV21Group,
            tmnxMdaXConnectGroupV21,
            tmnxCoreDdctdPolicerResGroupV21,
            tmnxFPToFPStatGroupV21,
            tmnxChassisCoreResPlcrV19v0Group,
            tFPResEgrHwAggShaperV21v0Group,
            tCardResTLSMcastV21v0Group,
            tmnxChassisNotifGroupV21v0,
            tmnxChassisResIngClassV21v0Group,
            tmnxChassisResEgrRmrkV21v0Group,
            tmnxChassisResIngrMapsV21v0Group,
            tmnxChassisResEgrMapsV21v0Group,
            tmnxChassisResLagBundl1V21v0Grp,
            tmnxChassisResLagBundl2V21v0Grp,
            tmnxChassisResSysBundleV21v0Grp,
            tmnxChassisResPerHostAutV21v0Grp,
            tmnxChassisDrpCntrJ1V21v0Group,
            tmnxChassisPwrMgmtV21v0Group,
            tmnxChassisResMacCamBnkV21v0Grp,
            tmnxIomRsrcNotifyObjsV23v0Grp,
            tmnxIomRsrcNotifyV23v0Grp,
            tmnxIomRsrcObjObsoleteGrpV23v0,
            tmnxFPCoreResUsgStatsGroupV23v0,
            tmnxEsa100g2GroupV23v0,
            tmnxChassisResIOCapacityV23v0Grp,
            tFPResSharedPolicersV23v0Group,
            tmnxChassisPwrMgmtV23v0Group,
            tmnxChassisPwrMgmtNotifsV23v0Grp,
            tmnxIxrRsrcNotifyObjsGroup,
            tmnxIxrRsrcNotifsGroup,
            tmnxIsaGrpESPSeqNumGroupV23v0,
            tnmxCardEqNotifsV23v0Grp,
            tFPResSrv6TunnelTermV23v0Group,
            tmnxIsaMemberPoolV23v0Group,
            tFPResEgrHwAggShaperV23v0Group,
            tmnxChassisIxrResourceJ2Group,
            tChassisIxrResDynEcmpAllocGroup,
            tmnxChassisResMtuProfileV23v0Grp,
            tmnxChassisResEprirSrV23v0Grp,
            tmnxChassisResEprirIxrV23v0Grp,
            tmnxChassisResEprirSrIxrV23v0Grp,
            tmnxChassisResEprirNotSrV23v0Grp,
            tmnxEsaStallNotifV22v0Grp
        }
    ::= { tmnxChassisCompliances 28 }

tmnxChassisV24v0Compliance       MODULE-COMPLIANCE
    STATUS      current
    DESCRIPTION
        "The compliance statement for management of chassis features on SROS
         series systems in the TIMETRA-CHASSIS-MIB release 24."
    MODULE
        MANDATORY-GROUPS {
            tmnxMinFpGenerationV22v0Group,
            tmnxHwAggShpNotifyObjsV22v0Grp,
            tmnxHwAggShpNotifGroupV22v0,
            tmnxEsa400gGroupV22v0,
            tmnxEsaHwStatusMonGroupV22v0,
            tmnxChassisGnssGroupV22v0,
            tmnxChassPSStateGroupV22v0,
            tmnxChassisResPortFwdIdGrpV22v0,
            tmnxChassisResShardPlcrGrpV22v0,
            tmnxFPCoreResUsgStatsGroupV22v0,
            tmnxHwTempGroupV22v0,
            tmnxCamOverloadGroupV22v0,
            tmnxSyncIfTimingGroupV22v0,
            tChassisResShardPlcrStatGrpV22v0,
            tmnxCpmSecureBootGroupV22v0,
            tmnxIomRsrcNotifyObjsV22v0Grp,
            tmnxIomRsrcNotifyV22v0Grp,
            tmnxIsaGrpESPSeqNumGroupV22v0,
            tFPResOversubGroupV22v0,
            tmnxFPResOversubNotifGroupV22v0,
            tmnxEsaHwStatusMonNotifGrpV22v0,
            tmnxChassisIxrResourceV24v0Group,
            tmnxXiomGroupV23v0,
            tmnxCoreDdctdPolicerResGroupV23,
            tmnxChassisRebootReqdGroupV23v0,
            tmnxXiomGroupV20v0,
            tmnxChassisNotifGroupV20v0,
            tmnx7710HwV3v0Group,
            tmnx7710SETSRefSrcHwV6v0Group,
            tmnxCardCamErrorV6v1Group,
            tmnxCardPchipV5v0Group,
            tmnxCardPchipV8v0Group,
            tmnxCardV10v0Group,
            tmnxCardV3v0Group,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV19v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxCardFPResIngV15v0QGroup,
            tmnxCardFPResEgrV15v0QGroup,
            tmnxIPsecIsaGrpV15v0Group,
            tmnxPhysChassisPCMGroupV15v0,
            tmnxMinFpGenerationGroupV15v0,
            tmnxPhysChassPCMNotifGroupV15v0,
            tmnxCardV16v0Group,
            tmnxCardComplexGroupV16v0,
            tmnxChassisGroupV16v0,
            tmnxChassisCardLevelGroupV15v1,
            tmnxPhysChassisPMGroupV16v0,
            tmnxChassisGnssGroup,
            tmnxChassisGnssNotifGroup,
            tmnxMdaFlexGroupV16v0,
            tmnxChassisMdaLevelGroupV15v1,
            tmnxPhysChassisPMNotifGroupV16v0,
            tmnxNearFullNotifGroupV16v0,
            tmnxCardV16v0ObsoleteGroup,
            tmnxCardV16v0FpgaSoftErrNotifGrp,
            tmnxMDAIsaTnlStatsV16v0Group,
            tmnxCardPowerSaveGroupV16v0,
            tmnxEsaGroup,
            tmnxFPNetworkIngressGroupV19v5,
            tmnxCardV19v5Group,
            tmnxSyncIfTimingV19v0Group,
            tmnxMDAV21v0Group,
            tmnxTunnelGrpEsaVmGroupV19v0,
            tmnxChassisResEgrV19v0Group,
            tmnxChassisResEgrRmrkV19v0Group,
            tmnxChassisResIngClassV19v0Group,
            tmnxChassisResDynCAMV19v0Group,
            tmnxChassisResIpMacCAMV19v0Group,
            tmnxChassisCoreResV19v0Group,
            tmnxSyncIfTimingV19v0NotifGroup,
            tmnxHwEventGroupV19v0,
            tmnxHwEventNotifyObjsGrpV19v0,
            tmnxHwEventNotifGroupV19v0,
            tmnxTunnelGrpEsaVmNotifGrpV19v0,
            tmnxEsaNotificationObjectGroup,
            tmnxEsaNotificationGroup,
            tmnxCardSapInstV19v0Group,
            tmnxCardFPQosPolicyV20v0Group,
            tmnxChassisResQMgmtV19v0Group,
            tmnxSapResourceUsageV23v0Group,
            tmnxChassisV20v0ObsoleteGroup,
            tmnxIPv6MCastCamV19v0Group,
            tmnxChassisResourceV23v0Group,
            tmnxSyncIfTimingV20v0ObsoleteGrp,
            tmnxSyncIfTimingGnssV20v0Group,
            tmnxChassisResEgrRmrkV20v0Group,
            tmnxSyncIfTimingV20v0NotifGroup,
            tmnxChassisDot1xHostV20v0Group,
            tmnxChassisResDepthMQV20v0Group,
            tmnxChassisFPQppbPolV20v0Group,
            tmnxChassisCoreResV20v0Group,
            tmnxFPNotificationV20Group,
            tmnxChassisCoreResPlcrV19v0Group,
            tmnxChassisIxrXFanV20v0Group,
            tmnxIpsecV21Group,
            tmnxMdaXConnectGroupV21,
            tmnxCoreDdctdPolicerResGroupV21,
            tmnxFPToFPStatGroupV21,
            tmnxChassisCoreResPlcrV19v0Group,
            tFPResEgrHwAggShaperV21v0Group,
            tCardResTLSMcastV21v0Group,
            tmnxChassisNotifGroupV21v0,
            tmnxChassisResIngClassV21v0Group,
            tmnxChassisResEgrRmrkV21v0Group,
            tmnxChassisResIngrMapsV21v0Group,
            tmnxChassisResEgrMapsV21v0Group,
            tmnxChassisResLagBundl1V21v0Grp,
            tmnxChassisResLagBundl2V21v0Grp,
            tmnxChassisResSysBundleV21v0Grp,
            tmnxChassisResPerHostAutV21v0Grp,
            tmnxChassisDrpCntrJ1V21v0Group,
            tmnxChassisPwrMgmtV21v0Group,
            tmnxChassisResMacCamBnkV21v0Grp,
            tmnxIomRsrcNotifyObjsV23v0Grp,
            tmnxIomRsrcNotifyV23v0Grp,
            tmnxIomRsrcObjObsoleteGrpV23v0,
            tmnxFPCoreResUsgStatsGroupV23v0,
            tmnxEsa100g2GroupV23v0,
            tmnxChassisResIOCapacityV23v0Grp,
            tFPResSharedPolicersV23v0Group,
            tmnxChassisPwrMgmtV23v0Group,
            tmnxChassisPwrMgmtNotifsV23v0Grp,
            tmnxIxrRsrcNotifyObjsGroup,
            tmnxIxrRsrcNotifsGroup,
            tmnxIsaGrpESPSeqNumGroupV23v0,
            tnmxCardEqNotifsV23v0Grp,
            tFPResSrv6TunnelTermV23v0Group,
            tmnxIsaMemberPoolV23v0Group,
            tmnxChassisIxrResourceJ2Group,
            tChassisIxrResDynEcmpAllocGroup,
            tmnxChassisResMtuProfileV23v0Grp,
            tmnxChassisResEprirSrV23v0Grp,
            tmnxChassisResEprirIxrV23v0Grp,
            tmnxChassisResEprirSrIxrV23v0Grp,
            tmnxChassisResEprirNotSrV23v0Grp,
            tmnxChassisCemMDAV24v0Group,
            tFPResEgrHwAggShaperV24v0Group,
            tmnxFlashV24v0Group,
            tmnxEsaHwStatusPwrLoadV24v0Grp,
            tmnxEsaHwStatusTempV24v0Grp,
            tmnxVirtualSchedAdjV24v0Grp,
            tmnxEsaStallNotifV22v0Grp,
            tmnxEsaHostPortStatsV24v0Grp,
            tmnxIpsecLoadBalV24Group,
            tmnxChassisPwrMgmtV24v0Grp,
            tFPResV24v0Group,
            tmnxMdaFlexEV24v0Grp,
            tmnxEsaHostPortCrcMonV24v0Group,
            tmnxChassisFpIxrResV24v0Group,
            tmnxEsaHostPortNotifV24v0Group,
            tmnxChassisOsSecV24v0Group,
            tmnxEsaFirmUpgNotifV24v0Group,
            tmnxVlanQosScalingModeGroup,
            tmnxChassisIxrResOwnV24v0Group,
            tmnxChassisIxrResScaleV24v0Grp,
            tmnxCardIxrResourcesV24v0Group,
            tmnxChassisOsSecV24v0NotifGrp,
            tmnxCardIxrPpmcResourcesGroup,
            tmnxCardIxrPpmcResourcesGroup2
        }
    ::= { tmnxChassisCompliances 29 }

tmnxChassisV25v0Compliance       MODULE-COMPLIANCE
    STATUS      current
    DESCRIPTION
        "The compliance statement for management of chassis features on SROS
         series systems in the TIMETRA-CHASSIS-MIB release 25."
    MODULE
        MANDATORY-GROUPS {
            tmnxChassisPwrMgmtLowPwrV25v0Grp,
            tFPResV25v0Group,
            tmnxLowPowerSwFabV25v0NotifGrp,
            tmnxChGoldenStatusV25v0Group,
            tmnxSyncFreqOffsetInPpbGroup,
            tmnxMDAMacModeV25v0Grp,
            tmnxFltrSharedPlcrV25v0Grp,
            tmnxSchedulerFlowsV25v0Grp,
            tmnxChassisFpIxrResV25v0Group,
            tmnxChassisPortSpeedModeV25v0Grp,
            tmnxCpmCardOsSecurityV25v0Grp,
            tmnxSecEraseNotifyObjsV25v0Grp,
            tmnxSecEraseNotificationGrpV25v0,
            tmnxVirtualFlowsV25v0Grp,
            tmnxBfdMHopV25v0Grp
        }
    ::= { tmnxChassisCompliances 30 }

tmnxChassisV26v0Compliance       MODULE-COMPLIANCE
    STATUS      current
    DESCRIPTION
        "The compliance statement for management of chassis features on SROS
         series systems in the TIMETRA-CHASSIS-MIB release 26."
    MODULE
        MANDATORY-GROUPS {
            tmnxChassisFpSarG2PolStatsV26Grp,
            tmnxOverloadNotifGroupV15v1,
            tmnxChassisSystemProfGroupV15v1,
            tmnxCardResourceV15v1Group,
            tmnxFPResourceV15v1Group,
            tmnxMDAPreClassPlcyV26v0Grp,
            tmnxLowRateVlanVoqV26v0Grp,
            tmnxEthStormCtrlV26v0Grp,
            tmnxChassisOsSecV26v0NotifGrp
        }
    ::= { tmnxChassisCompliances 31 }

tmnxChassisGroups                OBJECT IDENTIFIER ::= { tmnxChassisConformance 2 }

tmnxChassisNotifyObjsGroup       OBJECT-GROUP
    OBJECTS     {
        tmnxEqNotificationRow,
        tmnxEqTypeNotificationRow,
        tmnxChassisNotifyChassisId,
        tmnxChassisNotifyHwIndex,
        tmnxRedSecondaryCPMStatus,
        tmnxChassisNotifyOID,
        tmnxSyncIfTimingNotifyAlarm,
        tmnxChassisNotifyMismatchedVer,
        tmnxChassisNotifySoftwareLocation,
        tmnxChassisNotifyCardFailureReason,
        tmnxCpmPowerShelfCommsFail
    }
    STATUS      current
    DESCRIPTION
        "The group of objects supporting chassis hardware notifications on
         Nokia SROS series systems."
    ::= { tmnxChassisGroups 4 }

tmnxChassisNotifyObsoleteGroup   NOTIFICATION-GROUP
    NOTIFICATIONS {
        tmnxHwConfigChange,
        tmnxEqCpuFailure,
        tmnxEqMemoryFailure,
        tmnxEqBackdoorBusFailure,
        tmnxPeSoftwareError,
        tmnxPeSoftwareAbnormalHalt,
        tmnxPeOutOfMemory,
        tmnxPeConfigurationError,
        tmnxPeStorageProblem,
        tmnxPeCpuCyclesExceeded,
        tmnxRedSecondaryCPMStatusChange,
        tmnxRedRestoreSuccess,
        tmnxRedRestoreFail
    }
    STATUS      current
    DESCRIPTION
        "The group of notifications supporting the management of chassis
         hardware made obsolete for revision 2.1 on Nokia SROS series systems."
    ::= { tmnxChassisGroups 7 }

tmnxChassisV3v0Group             OBJECT-GROUP
    OBJECTS     {
        tmnxChassisTotalNumber,
        tmnxChassisLastChange,
        tmnxChassisRowStatus,
        tmnxChassisName,
        tmnxChassisType,
        tmnxChassisLocation,
        tmnxChassisCoordinates,
        tmnxChassisNumSlots,
        tmnxChassisNumPorts,
        tmnxChassisNumPwrSupplies,
        tmnxChassisNumFanTrays,
        tmnxChassisNumFans,
        tmnxChassisCriticalLEDState,
        tmnxChassisMajorLEDState,
        tmnxChassisMinorLEDState,
        tmnxChassisBaseMacAddress,
        tmnxChassisCLLICode,
        tmnxChassisReboot,
        tmnxChassisUpgrade,
        tmnxChassisAdminMode,
        tmnxChassisOperMode,
        tmnxChassisModeForce,
        tmnxChassisUpdateWaitTime,
        tmnxChassisUpdateTimeLeft,
        tmnxChassisFanOperStatus,
        tmnxChassisFanSpeed,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType,
        tmnxChassisTypeName,
        tmnxChassisTypeDescription,
        tmnxChassisTypeStatus,
        tmnxHwLastChange,
        tmnxHwID,
        tmnxHwMfgString,
        tmnxHwMfgBoardNumber,
        tmnxHwSerialNumber,
        tmnxHwManufactureDate,
        tmnxHwClass,
        tmnxHwName,
        tmnxHwAlias,
        tmnxHwAssetID,
        tmnxHwCLEI,
        tmnxHwIsFRU,
        tmnxHwContainedIn,
        tmnxHwParentRelPos,
        tmnxHwAdminState,
        tmnxHwOperState,
        tmnxHwTempSensor,
        tmnxHwTemperature,
        tmnxHwTempThreshold,
        tmnxHwBootCodeVersion,
        tmnxHwSoftwareCodeVersion,
        tmnxHwSwLastBoot,
        tmnxHwAlarmState,
        tmnxHwLastAlarmEvent,
        tmnxHwClearAlarms,
        tmnxHwSwImageSource,
        tmnxHwMfgDeviations,
        tmnxHwBaseMacAddress,
        tmnxHwFailureReason,
        tmnxHwContainedIndex
    }
    STATUS      obsolete
    DESCRIPTION
        "The group of objects supporting management of chassis hardware
         capabilities on release 3.0 of  Nokia SROS series systems."
    ::= { tmnxChassisGroups 9 }

tmnxMDAV3v0Group                 OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMDACcagId,
        tmnxMdaTypeName,
        tmnxMdaTypeDescription,
        tmnxMdaTypeStatus,
        tmnxCcagRowStatus,
        tmnxCcagDescription,
        tmnxCcagAdminStatus,
        tmnxCcagOperStatus,
        tmnxCcagCcaRate,
        tmnxCcagLastChanged,
        tmnxCcagAccessAdaptQos,
        tmnxCcagPathLastChanged,
        tmnxCcagPathRate,
        tmnxCcagPathRateOption,
        tmnxCcagPathWeight,
        tmnxCcagPathCcLastChanged,
        tmnxCcagPathCcEgrPoolResvCbs,
        tmnxCcagPathCcEgrPoolSlpPlcy,
        tmnxCcagPathCcIngPoolResvCbs,
        tmnxCcagPathCcIngPoolSlpPlcy,
        tmnxCcagPathCcAcctPolicyId,
        tmnxCcagPathCcCollectStats,
        tmnxCcagPathCcQueuePlcy,
        tmnxCcagPathCcMac,
        tmnxCcagPathCcMtu,
        tmnxCcagPathCcHwMac,
        tmnxCcagPathCcUserAssignedMac
    }
    STATUS      obsolete
    DESCRIPTION
        "The group of objects supporting management of MDAs on Nokia SROS
         series systems."
    ::= { tmnxChassisGroups 10 }

tmnxChassisObsoleteGroup         OBJECT-GROUP
    OBJECTS     {
        tmnxHwSwState,
        tmnxCardAllowedTypes,
        tmnxCpmCardAllowedTypes,
        tmnxMDAAllowedTypes
    }
    STATUS      current
    DESCRIPTION
        "The group of objects supporting the allowed types of CPM cards, IOM
         cards and MDA made obsolete for revision 3.0 on Nokia SROS series
         systems."
    ::= { tmnxChassisGroups 11 }

tmnxCardV3v0Group                OBJECT-GROUP
    OBJECTS     {
        tmnxCardLastChange,
        tmnxCardTypeName,
        tmnxCardTypeDescription,
        tmnxCardTypeStatus,
        tmnxCardSupportedTypes,
        tmnxCardAssignedType,
        tmnxCardEquippedType,
        tmnxCardHwIndex,
        tmnxCardClockSource,
        tmnxCardNumMdaSlots,
        tmnxCardNumMdas,
        tmnxCardReboot,
        tmnxCardMemorySize,
        tmnxCpmCardLastChange,
        tmnxCpmCardSupportedTypes,
        tmnxCpmCardAssignedType,
        tmnxCpmCardEquippedType,
        tmnxCpmCardHwIndex,
        tmnxCpmCardBootOptionVersion,
        tmnxCpmCardBootOptionLastModified,
        tmnxCpmCardConfigBootedVersion,
        tmnxCpmCardIndexBootedVersion,
        tmnxCpmCardConfigLastModified,
        tmnxCpmCardConfigLastSaved,
        tmnxCpmCardRedundant,
        tmnxCpmCardClockSource,
        tmnxCpmCardNumCpus,
        tmnxCpmCardCpuType,
        tmnxCpmCardMemorySize,
        tmnxCpmCardSwitchToRedundantCard,
        tmnxCpmCardReboot,
        tmnxCpmCardRereadBootOptions,
        tmnxCpmCardConfigFileLastBooted,
        tmnxCpmCardConfigFileLastSaved,
        tmnxCpmCardConfigFileLastBootedHeader,
        tmnxCpmCardIndexFileLastBootedHeader,
        tmnxCpmCardBootOptionSource,
        tmnxCpmCardConfigSource,
        tmnxCpmCardBootOptionLastSaved,
        tmnxFabricLastChange,
        tmnxFabricAssignedType,
        tmnxFabricEquippedType,
        tmnxFabricHwIndex,
        tmnxCpmFlashOperStatus,
        tmnxCpmFlashSerialNumber,
        tmnxCpmFlashFirmwareRevision,
        tmnxCpmFlashModelNumber,
        tmnxCpmFlashCapacity,
        tmnxCpmFlashUsed,
        tmnxCpmFlashHwIndex,
        tmnxSyncIfTimingRevert,
        tmnxSyncIfTimingRefOrder1,
        tmnxSyncIfTimingRefOrder2,
        tmnxSyncIfTimingRef1SrcPort,
        tmnxSyncIfTimingRef1AdminStatus,
        tmnxSyncIfTimingRef1InUse,
        tmnxSyncIfTimingRef1Qualified,
        tmnxSyncIfTimingRef1Alarm,
        tmnxSyncIfTimingRef2SrcPort,
        tmnxSyncIfTimingRef2AdminStatus,
        tmnxSyncIfTimingRef2InUse,
        tmnxSyncIfTimingRef2Qualified,
        tmnxSyncIfTimingRef2Alarm,
        tmnxSyncIfTimingFreqOffset,
        tmnxSyncIfTimingStatus,
        tmnxSyncIfTimingRefOrder3,
        tmnxSyncIfTimingBITSIfType,
        tmnxSyncIfTimingBITSAdminStatus,
        tmnxSyncIfTimingBITSInUse,
        tmnxSyncIfTimingBITSQualified,
        tmnxSyncIfTimingBITSAlarm,
        tSyncIfTimingAdmRevert,
        tSyncIfTimingAdmRefOrder1,
        tSyncIfTimingAdmRefOrder2,
        tSyncIfTimingAdmRef1SrcPort,
        tSyncIfTimingAdmRef1AdminStatus,
        tSyncIfTimingAdmRef2SrcPort,
        tSyncIfTimingAdmRef2AdminStatus,
        tSyncIfTimingAdmChanged,
        tSyncIfTimingAdmRefOrder3,
        tSyncIfTimingAdmBITSIfType,
        tSyncIfTimingAdmBITSAdminStatus,
        tmnxChassisAdminOwner,
        tmnxChassisAdminControlApply
    }
    STATUS      current
    DESCRIPTION
        "The group of objects supporting management of hardware cards on Nokia
         SROS series systems."
    ::= { tmnxChassisGroups 12 }

tmnxMDAV4v0Group                 OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMDACcagId,
        tmnxMdaTypeName,
        tmnxMdaTypeDescription,
        tmnxMdaTypeStatus,
        tmnxMDAReboot,
        tmnxCcagRowStatus,
        tmnxCcagDescription,
        tmnxCcagAdminStatus,
        tmnxCcagOperStatus,
        tmnxCcagCcaRate,
        tmnxCcagLastChanged,
        tmnxCcagAccessAdaptQos,
        tmnxCcagPathLastChanged,
        tmnxCcagPathRate,
        tmnxCcagPathRateOption,
        tmnxCcagPathWeight,
        tmnxCcagPathCcLastChanged,
        tmnxCcagPathCcEgrPoolResvCbs,
        tmnxCcagPathCcEgrPoolSlpPlcy,
        tmnxCcagPathCcIngPoolResvCbs,
        tmnxCcagPathCcIngPoolSlpPlcy,
        tmnxCcagPathCcAcctPolicyId,
        tmnxCcagPathCcCollectStats,
        tmnxCcagPathCcQueuePlcy,
        tmnxCcagPathCcMac,
        tmnxCcagPathCcMtu,
        tmnxCcagPathCcHwMac,
        tmnxCcagPathCcUserAssignedMac,
        tmnxMDAHiBwMcastSource,
        tmnxMDAHiBwMcastAlarm,
        tmnxMDAHiBwMcastTapCount,
        tmnxMDAHiBwMcastGroup
    }
    STATUS      obsolete
    DESCRIPTION
        "The group of objects supporting management of MDAs for release 4.0 on
         Nokia SROS series systems."
    ::= { tmnxChassisGroups 13 }

tmnxChassisNotificationV4v0Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible
    }
    STATUS      obsolete
    DESCRIPTION
        "The group of notifications supporting the management of chassis
         hardware for release 4.0 on Nokia SROS series systems."
    ::= { tmnxChassisGroups 14 }

tmnx7710HwV3v0Group              OBJECT-GROUP
    OBJECTS     {
        tmnxChassisOverTempState,
        tmnxCpmCardMasterSlaveRefState,
        tmnxCcmOperStatus,
        tmnxCcmHwIndex,
        tmnxCcmEquippedType,
        tmnxCcmTypeName,
        tmnxCcmTypeDescription,
        tmnxCcmTypeStatus,
        tmnxChassisPowerSupplyInputStatus,
        tmnxChassisPowerSupplyOutputStatus,
        tmnxMDAReboot
    }
    STATUS      current
    DESCRIPTION
        "The group of objects supporting management of hardware specific to the
         Nokia 7710 SR series systems."
    ::= { tmnxChassisGroups 15 }

tmnxChassisV5v0Group             OBJECT-GROUP
    OBJECTS     {
        tmnxChassisTotalNumber,
        tmnxChassisLastChange,
        tmnxChassisRowStatus,
        tmnxChassisName,
        tmnxChassisType,
        tmnxChassisLocation,
        tmnxChassisCoordinates,
        tmnxChassisNumSlots,
        tmnxChassisNumPorts,
        tmnxChassisNumPwrSupplies,
        tmnxChassisNumFanTrays,
        tmnxChassisNumFans,
        tmnxChassisCriticalLEDState,
        tmnxChassisMajorLEDState,
        tmnxChassisMinorLEDState,
        tmnxChassisBaseMacAddress,
        tmnxChassisCLLICode,
        tmnxChassisReboot,
        tmnxChassisUpgrade,
        tmnxChassisAdminMode,
        tmnxChassisOperMode,
        tmnxChassisModeForce,
        tmnxChassisUpdateTimeLeft,
        tmnxChassisFanOperStatus,
        tmnxChassisFanSpeed,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType,
        tmnxChassisTypeName,
        tmnxChassisTypeDescription,
        tmnxChassisTypeStatus,
        tmnxHwLastChange,
        tmnxHwID,
        tmnxHwMfgString,
        tmnxHwMfgBoardNumber,
        tmnxHwSerialNumber,
        tmnxHwManufactureDate,
        tmnxHwClass,
        tmnxHwName,
        tmnxHwAlias,
        tmnxHwAssetID,
        tmnxHwCLEI,
        tmnxHwIsFRU,
        tmnxHwContainedIn,
        tmnxHwParentRelPos,
        tmnxHwAdminState,
        tmnxHwOperState,
        tmnxHwTempSensor,
        tmnxHwTemperature,
        tmnxHwTempThreshold,
        tmnxHwBootCodeVersion,
        tmnxHwSoftwareCodeVersion,
        tmnxHwSwLastBoot,
        tmnxHwAlarmState,
        tmnxHwLastAlarmEvent,
        tmnxHwClearAlarms,
        tmnxHwSwImageSource,
        tmnxHwMfgDeviations,
        tmnxHwBaseMacAddress,
        tmnxHwFailureReason,
        tmnxHwContainedIndex
    }
    STATUS      obsolete
    DESCRIPTION
        "The group of objects supporting management of chassis hardware
         capabilities on release 5.0 of Nokia SROS series systems."
    ::= { tmnxChassisGroups 16 }

tmnxChassisV5v0ObsoleteGroup     OBJECT-GROUP
    OBJECTS     {
        tmnxChassisUpdateWaitTime
    }
    STATUS      current
    DESCRIPTION
        "The group of obsolete objects for managing the chassis hardware
         capabilities on release 5.0 of Nokia SROS series systems."
    ::= { tmnxChassisGroups 17 }

tmnx77x0CESMDAV6v0Group          OBJECT-GROUP
    OBJECTS     {
        tmnxMDAClockMode,
        tmnxMDADiffTimestampFreq,
        tmnxMDAIngNamedPoolPolicy,
        tmnxMDAEgrNamedPoolPolicy
    }
    STATUS      obsolete
    DESCRIPTION
        "The group of objects supporting management of CES MDAs for release 6.0
         on Nokia 77x0 SR series systems."
    ::= { tmnxChassisGroups 18 }

tmnxIPsecIsaGrpV6v0Group         OBJECT-GROUP
    OBJECTS     {
        tmnxIPsecIsaGrpTableLastChanged,
        tmnxIPsecIsaGrpRowStatus,
        tmnxIPsecIsaGrpLastChanged,
        tmnxIPsecIsaGrpDescription,
        tmnxIPsecIsaGrpAdminState,
        tmnxIPsecIsaGrpOperState,
        tmnxIPsecIsaGrpIsaChassis,
        tmnxIPsecIsaGrpPrimaryIsa,
        tmnxIPsecIsaGrpBackupIsa,
        tmnxIPsecIsaGrpActiveIsa
    }
    STATUS      current
    DESCRIPTION
        "The group of objects supporting management of IPsec MDAs for release
         6.0 on Nokia 7750 and 7710 SR series systems."
    ::= { tmnxChassisGroups 19 }

tmnxChassisNotificationV3v0Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxEqMdaCfgNotCompatible
    }
    STATUS      obsolete
    DESCRIPTION
        "The group of notifications supporting the management of chassis
         hardware for release 3.0 on Nokia SROS series systems."
    ::= { tmnxChassisGroups 20 }

tmnxChassisNotificationV6v0Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible,
        tmnxCpmCardSyncFileNotPresent,
        tmnxEqMdaXplError,
        tmnxEqCardPChipError,
        tmnxEqCardPChipMemoryEvent
    }
    STATUS      obsolete
    DESCRIPTION
        "The group of notifications supporting the management of chassis
         hardware for release 6.0 on Nokia SROS series systems."
    ::= { tmnxChassisGroups 21 }

tmnx7710SETSRefSrcHwV6v0Group    OBJECT-GROUP
    OBJECTS     {
        tmnxSyncIfTimingRef1SrcHw,
        tmnxSyncIfTimingRef1BITSIfType,
        tmnxSyncIfTimingRef2SrcHw,
        tmnxSyncIfTimingRef2BITSIfType,
        tSyncIfTimingAdmRef1SrcHw,
        tSyncIfTimingAdmRef1BITSIfType,
        tSyncIfTimingAdmRef2SrcHw,
        tSyncIfTimingAdmRef2BITSIfType
    }
    STATUS      current
    DESCRIPTION
        "The group of objects supporting management of 'Synchronous Equipment
         Timing' (SETS) when the references are of type 'Building Integrated
         Timing Supply' (BITS) for release 6.0 on Nokia 7710 SR series systems."
    ::= { tmnxChassisGroups 22 }

tmnxMDAMcPathMgmtV6v0Group       OBJECT-GROUP
    OBJECTS     {
        tmnxMDAMcPathMgmtBwPlcyName,
        tmnxMDAMcPathMgmtPriPathLimit,
        tmnxMDAMcPathMgmtSecPathLimit,
        tmnxMDAMcPathMgmtAncPathLimit,
        tmnxMDAMcPathMgmtAdminState,
        tmnxMDAMcPathMgmtPriInUseBw,
        tmnxMDAMcPathMgmtSecInUseBw,
        tmnxMDAMcPathMgmtAncInUseBw,
        tmnxMDAMcPathMgmtBlkHoleInUseBw
    }
    STATUS      obsolete
    DESCRIPTION
        "The group of objects supporting management of Multicast Path
         Management feature for release 6.0 on Nokia SROS series systems."
    ::= { tmnxChassisGroups 24 }

tmnxCardV6v0NamedPoolPlcyGroup   OBJECT-GROUP
    OBJECTS     {
        tmnxCardNamedPoolAdminMode,
        tmnxCardNamedPoolOperMode
    }
    STATUS      obsolete
    DESCRIPTION
        "The group of objects supporting named buffer pools for release 6.0 on
         Nokia SROS series systems."
    ::= { tmnxChassisGroups 25 }

tmnxChassisNotifyObjsV6v0Group   OBJECT-GROUP
    OBJECTS     {
        tmnxChassisNotifyCardName,
        tmnxChassisNotifyCardSyncFile
    }
    STATUS      current
    DESCRIPTION
        "The group of objects added in 6.0 release to support chassis hardware
         notifications on Nokia SROS series systems."
    ::= { tmnxChassisGroups 26 }

tmnxChassisV6v1Group             OBJECT-GROUP
    OBJECTS     {
        tmnxChassisPowerSupplyPemType,
        tmnxCardSoftReset,
        tmnxCardLastBootupReason
    }
    STATUS      current
    DESCRIPTION
        "The group of objects added in 6.1 release on Nokia 7xx0 SR series
         systems."
    ::= { tmnxChassisGroups 27 }

tmnxFPMcPathMgmtV6v1Group        OBJECT-GROUP
    OBJECTS     {
        tmnxFPMcPathMgmtBwPlcyName,
        tmnxFPMcPathMgmtAdminState,
        tmnxFPLastChanged,
        tmnxFPHiBwMcastSource,
        tmnxFPHiBwMcastAlarm,
        tmnxFPHiBwMcastTapCount,
        tmnxFPHiBwMcastGroup,
        tmnxFPHiBwMcastDefaultPathsOnly
    }
    STATUS      current
    DESCRIPTION
        "The group of objects supporting management of Multicast Path
         Management feature for release 6.1 on Nokia SROS series systems."
    ::= { tmnxChassisGroups 28 }

tmnxMDAV6v1Group                 OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMdaTypeName,
        tmnxMdaTypeDescription,
        tmnxMdaTypeStatus,
        tmnxMDAReboot,
        tmnxMDAHiBwMcastSource,
        tmnxMDAHiBwMcastAlarm,
        tmnxMDAHiBwMcastTapCount,
        tmnxMDAHiBwMcastGroup,
        tmnxMDASynchronousEthernet
    }
    STATUS      obsolete
    DESCRIPTION
        "The group of objects supporting management of MDAs for release 6.1 on
         Nokia SROS series systems."
    ::= { tmnxChassisGroups 29 }

tmnxMDACcagV6v1Group             OBJECT-GROUP
    OBJECTS     {
        tmnxMDACcagId,
        tmnxCcagRowStatus,
        tmnxCcagDescription,
        tmnxCcagAdminStatus,
        tmnxCcagOperStatus,
        tmnxCcagCcaRate,
        tmnxCcagLastChanged,
        tmnxCcagAccessAdaptQos,
        tmnxCcagPathLastChanged,
        tmnxCcagPathRate,
        tmnxCcagPathRateOption,
        tmnxCcagPathWeight,
        tmnxCcagPathCcLastChanged,
        tmnxCcagPathCcEgrPoolResvCbs,
        tmnxCcagPathCcEgrPoolSlpPlcy,
        tmnxCcagPathCcIngPoolResvCbs,
        tmnxCcagPathCcIngPoolSlpPlcy,
        tmnxCcagPathCcAcctPolicyId,
        tmnxCcagPathCcCollectStats,
        tmnxCcagPathCcQueuePlcy,
        tmnxCcagPathCcMac,
        tmnxCcagPathCcMtu,
        tmnxCcagPathCcHwMac,
        tmnxCcagPathCcUserAssignedMac
    }
    STATUS      obsolete
    DESCRIPTION
        "The group of objects supporting management of MDA CCAG for release 6.1
         on Nokia SROS series systems."
    ::= { tmnxChassisGroups 30 }

tmnxMdaXplV5v0Group              OBJECT-GROUP
    OBJECTS     {
        tmnxMDAXplErrorTime,
        tmnxMDAXplFailedCount
    }
    STATUS      current
    DESCRIPTION
        "The group of objects added in 5.0 release to support MDA XPL error
         indications on Nokia SROS series systems."
    ::= { tmnxChassisGroups 31 }

tmnxChassisNotifyObjsV5v0Group   OBJECT-GROUP
    OBJECTS     {
        tmnxCardComplexNumber,
        tmnxCardFwdDirection
    }
    STATUS      current
    DESCRIPTION
        "The group of objects added in 5.0 release to support chassis hardware
         notifications on Nokia SROS series systems."
    ::= { tmnxChassisGroups 32 }

tmnxChassisNotificationV5v0Group NOTIFICATION-GROUP
    NOTIFICATIONS {
        tmnxEqMdaXplError,
        tmnxEqCardPChipError,
        tmnxEqCardPChipMemoryEvent
    }
    STATUS      obsolete
    DESCRIPTION
        "The group of notifications added in 5.0 release to support the
         hardware notifications on Nokia SROS series systems."
    ::= { tmnxChassisGroups 33 }

tmnxChassisNotificationV6v1Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible,
        tmnxCpmCardSyncFileNotPresent,
        tmnxEqMdaXplError,
        tmnxEqCardPChipError,
        tmnxEqCardSoftResetAlarm,
        tmnxEqCardPChipMemoryEvent,
        tmnxEqCardPChipCamEvent
    }
    STATUS      obsolete
    DESCRIPTION
        "The group of notifications supporting the management of chassis
         hardware for release 6.0 on Nokia SROS series systems."
    ::= { tmnxChassisGroups 34 }

tmnxChassisNotifyObjsV6v1Group   OBJECT-GROUP
    OBJECTS     {
        tmnxCardSoftResetState
    }
    STATUS      current
    DESCRIPTION
        "The group of objects added in 6.1 release to support chassis hardware
         notifications on Nokia SROS series systems."
    ::= { tmnxChassisGroups 35 }

tmnxChassisNotificationV7v0Group NOTIFICATION-GROUP
    NOTIFICATIONS {
        tmnxEnvTempTooHigh,
        tmnxEqPowerSupplyInserted,
        tmnxEqPowerSupplyRemoved,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible,
        tmnxCpmCardSyncFileNotPresent,
        tmnxEqMdaXplError,
        tmnxEqCardPChipError,
        tmnxEqCardSoftResetAlarm,
        tmnxEqMdaSyncENotCompatible,
        tmnxIPsecIsaGrpActiveIsaChgd,
        tmnxEqCardPChipMemoryEvent,
        tmnxIPsecIsaGrpUnableToSwitch,
        tmnxEqCardPChipCamEvent,
        tmnxEqHwEnhancedCapability
    }
    STATUS      current
    DESCRIPTION
        "The group of notifications supporting the management of chassis
         hardware for release 7.0 on Nokia SROS series systems."
    ::= { tmnxChassisGroups 36 }

tmnxChassisUserModV7v0Group      OBJECT-GROUP
    OBJECTS     {
        tmnxCpmCardConfigUserLastModified
    }
    STATUS      current
    DESCRIPTION
        "The group of objects added in 7.0 release on Nokia 7xx0 SR series
         systems to track user modifications."
    ::= { tmnxChassisGroups 37 }

tmnxCardPchipV5v0Group           OBJECT-GROUP
    OBJECTS     {
        tmnxCardCmplx1IngrFcsOccur,
        tmnxCardCmplx1IngrFcsOccurTime,
        tmnxCardCmplx1EgrFcsOccur,
        tmnxCardCmplx1EgrFcsOccurTime,
        tmnxCardCmplx2IngrFcsOccur,
        tmnxCardCmplx2IngrFcsOccurTime,
        tmnxCardCmplx2EgrFcsOccur,
        tmnxCardCmplx2EgrFcsOccurTime,
        tmnxCardCmplx1MemParityOccur,
        tmnxCardCmplx1MemParityOccurTime,
        tmnxCardCmplx2MemParityOccur,
        tmnxCardCmplx2MemParityOccurTime
    }
    STATUS      current
    DESCRIPTION
        "The group of objects added in 5.0 release to support IOM Card Pchip
         error indications on Nokia SROS series systems."
    ::= { tmnxChassisGroups 38 }

tmnxFPWredV7v0Group              OBJECT-GROUP
    OBJECTS     {
        tmnxFPWredBufAllocMin,
        tmnxFPWredBufAllocMax,
        tmnxFPWredResvCbsMin,
        tmnxFPWredResvCbsMax,
        tmnxFPWredSlopePolicy,
        tmnxFPWredAdminState
    }
    STATUS      current
    DESCRIPTION
        "The group of objects supporting management of WRED Queue Management
         feature for release 7.0 on Nokia SROS series systems."
    ::= { tmnxChassisGroups 39 }

tmnxChassisV7v0Group             OBJECT-GROUP
    OBJECTS     {
        tmnxChassisFanRevision
    }
    STATUS      current
    DESCRIPTION
        "The group of objects added in 7.0 release on Nokia 7x50 SR series
         systems to track Fan Tray revisions."
    ::= { tmnxChassisGroups 40 }

tmnxIPsecV7v0Group               OBJECT-GROUP
    OBJECTS     {
        tmnxIPsecIsaGrpTunnels,
        tmnxIPsecIsaGrpMaxTunnels
    }
    STATUS      current
    DESCRIPTION
        "The group of objects added in 7.0 release on Nokia 7x50 SR series
         systems related to IPsec feature."
    ::= { tmnxChassisGroups 41 }

tmnxIPsecNotifV7v0Group          NOTIFICATION-GROUP
    NOTIFICATIONS {
        tmnxIPsecIsaGrpTnlLowWMark,
        tmnxIPsecIsaGrpTnlHighWMark,
        tmnxIPsecIsaGrpTnlMax
    }
    STATUS      current
    DESCRIPTION
        "The group of objects added in 7.0 release to support IPsec
         notifications on Nokia SROS series systems."
    ::= { tmnxChassisGroups 42 }

tmnxSyncV6v0Group                OBJECT-GROUP
    OBJECTS     {
        tmnxSyncIfTimingRef1State,
        tmnxSyncIfTimingRef2State,
        tmnxSyncIfTimingBITSState
    }
    STATUS      current
    DESCRIPTION
        "The group of objects added in 6.0 release on Nokia 7xx0 SR series
         systems related to system timing."
    ::= { tmnxChassisGroups 43 }

tmnxSyncIfTimingV8v0Group        OBJECT-GROUP
    OBJECTS     {
        tmnxSyncIfTimingBITSOutAdmStatus,
        tmnxSyncIfTimingBITSOutLineLen,
        tmnxSyncIfTimingRef1CfgQltyLevel,
        tmnxSyncIfTimingRef1RxQltyLevel,
        tmnxSyncIfTimingRef2CfgQltyLevel,
        tmnxSyncIfTimingRef2RxQltyLevel,
        tmnxSyncIfTimingBITSCfgQltyLevel,
        tmnxSyncIfTimingBITSRxQltyLevel,
        tmnxSyncIfTimingBITS2InUse,
        tmnxSyncIfTimingBITS2Qualified,
        tmnxSyncIfTimingBITS2Alarm,
        tmnxSyncIfTimingBITS2RxQltyLevel,
        tmnxSyncIfTimingBITS2State,
        tmnxSyncIfTimingRef1NationalUse,
        tmnxSyncIfTimingRef2NationalUse,
        tmnxSyncIfTimingBITSNationalUse,
        tmnxSyncIfTimingQLSelection,
        tmnxSyncIfTimingOtherCPMInUse,
        tmnxSyncIfTimingOtherCPMQual,
        tmnxSyncIfTimingOtherCPMAlarm,
        tmnxSyncIfTimingOtherCPMState,
        tmnxSyncIfTimingBITSOutRefSel,
        tmnxSyncIfTimingBITSTxQltyLevel,
        tmnxSyncIfTimingBITS2AdminStatus,
        tmnxSyncIfTimingSystemQltyLevel,
        tSyncIfTimingAdmBITSOutAdmStatus,
        tSyncIfTimingAdmBITSOutLineLen,
        tSyncIfTimingAdmRef1CfgQltyLevel,
        tSyncIfTimingAdmRef2CfgQltyLevel,
        tSyncIfTimingAdmBITSCfgQltyLevel,
        tSyncIfTimingAdmRef1NationalUse,
        tSyncIfTimingAdmRef2NationalUse,
        tSyncIfTimingAdmBITSNationalUse,
        tSyncIfTimingAdmQLSelection
    }
    STATUS      current
    DESCRIPTION
        "The group of objects added in 8.0 release to support new
         Sync-if-timing features on Nokia SROS series systems."
    ::= { tmnxChassisGroups 44 }

tmnxSyncIfTimingNotifV8v0Group   NOTIFICATION-GROUP
    NOTIFICATIONS {
        tmnxEqSyncIfTimingRef1Quality,
        tmnxEqSyncIfTimingRef2Quality,
        tmnxEqSyncIfTimingBITSQuality,
        tmnxEqSyncIfTimingBITS2Quality,
        tmnxEqSyncIfTimingRefSwitch,
        tmnxEqSyncIfTimingBITS2Alarm,
        tmnxEqSyncIfTimingBITS2AlarmClr,
        tmnxEqSyncIfTimingBITSOutRefChg,
        tmnxEqSyncIfTimingSystemQuality
    }
    STATUS      current
    DESCRIPTION
        "The group of objects added in 8.0 release to support Sync-If-Timing
         notifications on Nokia SROS series systems."
    ::= { tmnxChassisGroups 45 }

tmnxChassisV8v0Group             OBJECT-GROUP
    OBJECTS     {
        tmnxHwEquippedPlatform,
        tmnxChassisRedForcedSingleSfm,
        tmnxCardCapability
    }
    STATUS      obsolete
    DESCRIPTION
        "The group of objects added in 8.0 release on Nokia SR series systems."
    ::= { tmnxChassisGroups 46 }

tmnxChassisMixedModeIomV8v0Group OBJECT-GROUP
    OBJECTS     {
        tmnxChassisMixedModeIomAdminMode,
        tmnxChassisMixedModeIomUpgrList
    }
    STATUS      obsolete
    DESCRIPTION
        "The group of objects added in 8.0 release on Nokia SR series systems
         to support the Mixed Mode IOM feature."
    ::= { tmnxChassisGroups 47 }

tmnxCardCamErrorV6v1Group        OBJECT-GROUP
    OBJECTS     {
        tmnxCardCmplx1CAMErrorOccur,
        tmnxCardCmplx1CAMErrorOccurTime,
        tmnxCardCmplx2CAMErrorOccur,
        tmnxCardCmplx2CAMErrorOccurTime,
        tmnxCpmCardCmplxCAMErrOccur,
        tmnxCpmCardCmplxCAMErrOccurTime
    }
    STATUS      current
    DESCRIPTION
        "The group of objects added in 6.1 release on Nokia 7xx0 SR series
         systems related to Card CAM Failures."
    ::= { tmnxChassisGroups 48 }

tmnxChassisV6v0Group             OBJECT-GROUP
    OBJECTS     {
        tmnxCardLastBootupReason
    }
    STATUS      obsolete
    DESCRIPTION
        "The group of objects added in 6.0 release on Nokia 7xx0 SR series
         systems."
    ::= { tmnxChassisGroups 49 }

tmnxCardV7v0Group                OBJECT-GROUP
    OBJECTS     {
        tmnxCardFailOnError
    }
    STATUS      current
    DESCRIPTION
        "The group of objects added in 7.0 release on Nokia 7xx0 SR series
         systems for card management."
    ::= { tmnxChassisGroups 50 }

tmnxAtmGroup                     OBJECT-GROUP
    OBJECTS     {
        tmnxMDAAtmMode
    }
    STATUS      obsolete
    DESCRIPTION
        "The group of objects on Nokia 7xx0 SR series systems for ATM
         management."
    ::= { tmnxChassisGroups 51 }

tmnxChassisHwV6v1Group           OBJECT-GROUP
    OBJECTS     {
        tmnxHwMfgAssemblyNumber
    }
    STATUS      current
    DESCRIPTION
        "The group of hardware related objects added in release 6.1 on Nokia
         7xx0 SR series systems."
    ::= { tmnxChassisGroups 52 }

tmnxChassisHwV9v0Group           OBJECT-GROUP
    OBJECTS     {
        tmnxCpmCardOscillatorType,
        tmnxHwFirmwareCodeVersion
    }
    STATUS      current
    DESCRIPTION
        "The group of hardware related objects added in release 9.0 on Nokia
         SROS series systems."
    ::= { tmnxChassisGroups 53 }

tmnxSyncIfTimingV9v0Group        OBJECT-GROUP
    OBJECTS     {
        tmnxSyncIfTimingRefOrder4,
        tmnxSyncIfTimingPTPAdminStatus,
        tmnxSyncIfTimingPTPInUse,
        tmnxSyncIfTimingPTPQualified,
        tmnxSyncIfTimingPTPAlarm,
        tmnxSyncIfTimingPTPCfgQltyLevel,
        tmnxSyncIfTimingPTPRxQltyLevel,
        tmnxSyncIfTimingPTPState,
        tmnxSyncIfTimingBITSOutSource,
        tSyncIfTimingAdmRefOrder4,
        tSyncIfTimingAdmPTPAdminStatus,
        tSyncIfTimingAdmPTPCfgQltyLevel,
        tSyncIfTimingAdmBITSOutSource
    }
    STATUS      current
    DESCRIPTION
        "The group of objects added in 9.0 release to support new
         Sync-if-timing features on Nokia SROS series systems."
    ::= { tmnxChassisGroups 54 }

tmnxSyncIfTimingNotifyV9v0Group  NOTIFICATION-GROUP
    NOTIFICATIONS {
        tmnxEqSyncIfTimingPTPQuality,
        tmnxEqSyncIfTimingPTPAlarm,
        tmnxEqSyncIfTimingPTPAlarmClear
    }
    STATUS      current
    DESCRIPTION
        "The group of notifications added in 9.0 release to support new
         Sync-if-timing features on Nokia SROS series systems."
    ::= { tmnxChassisGroups 55 }

tmnxChassisNotifyObjsV9v0Group   OBJECT-GROUP
    OBJECTS     {
        tmnxMdaNotifyType
    }
    STATUS      current
    DESCRIPTION
        "The group of notification objects extending chassis features for
         revision 9.0 on Nokia SROS series systems."
    ::= { tmnxChassisGroups 56 }

tmnxCardPchipV8v0Group           OBJECT-GROUP
    OBJECTS     {
        tmnxCardCmplx1EgrFcsSrcSlots,
        tmnxCardCmplx2EgrFcsSrcSlots
    }
    STATUS      current
    DESCRIPTION
        "The group of objects added in 8.0 release to enhance IOM Card Pchip
         error indications on Nokia SROS series systems."
    ::= { tmnxChassisGroups 58 }

tmnxChassisNotifyObjsV8v0Group   OBJECT-GROUP
    OBJECTS     {
        tmnxCardSrcSlotBitmap
    }
    STATUS      current
    DESCRIPTION
        "The group of objects added in 8.0 release to support chassis hardware
         notifications on Nokia SROS series systems."
    ::= { tmnxChassisGroups 59 }

tmnxFPQGrpGroup                  OBJECT-GROUP
    OBJECTS     {
        tmnxFPAccIngQGrpAcctgPolId,
        tmnxFPAccIngQGrpCollectStats,
        tmnxFPAccIngQGrpDescr,
        tmnxFPAccIngQGrpLastChgd,
        tmnxFPAccIngQGrpRowStatus,
        tmnxFPAccIngQGrpPolicerPol,
        tmnxFPAccIngQGrpTableLastChgd,
        tmnxFPNetIngQGrpAcctgPolId,
        tmnxFPNetIngQGrpCollectStats,
        tmnxFPNetIngQGrpDescr,
        tmnxFPNetIngQGrpLastChgd,
        tmnxFPNetIngQGrpRowStatus,
        tmnxFPNetIngQGrpPolicerPol,
        tmnxFPNetIngQGrpTableLastChgd,
        tmnxFPNetIngQGrpPStatMode,
        tmnxFPNetIngQgPStOffHPrioPkts,
        tmnxFPNetIngQgPStOffHPrioPktsL,
        tmnxFPNetIngQgPStOffHPrioPktsH,
        tmnxFPNetIngQgPStDrpHPrioPkts,
        tmnxFPNetIngQgPStDrpHPrioPktsL,
        tmnxFPNetIngQgPStDrpHPrioPktsH,
        tmnxFPNetIngQgPStOffLPrioPkts,
        tmnxFPNetIngQgPStOffLPrioPktsL,
        tmnxFPNetIngQgPStOffLPrioPktsH,
        tmnxFPNetIngQgPStDrpLPrioPkts,
        tmnxFPNetIngQgPStDrpLPrioPktsL,
        tmnxFPNetIngQgPStDrpLPrioPktsH,
        tmnxFPNetIngQgPStOffHPrioOcts,
        tmnxFPNetIngQgPStOffHPrioOctsL,
        tmnxFPNetIngQgPStOffHPrioOctsH,
        tmnxFPNetIngQgPStDrpHPrioOcts,
        tmnxFPNetIngQgPStDrpHPrioOctsL,
        tmnxFPNetIngQgPStDrpHPrioOctsH,
        tmnxFPNetIngQgPStOffLPrioOcts,
        tmnxFPNetIngQgPStOffLPrioOctsL,
        tmnxFPNetIngQgPStOffLPrioOctsH,
        tmnxFPNetIngQgPStDrpLPrioOcts,
        tmnxFPNetIngQgPStDrpLPrioOctsL,
        tmnxFPNetIngQgPStDrpLPrioOctsH,
        tmnxFPNetIngQgPStFwdInProfPkts,
        tmnxFPNetIngQgPStFwdInProfPktsL,
        tmnxFPNetIngQgPStFwdInProfPktsH,
        tmnxFPNetIngQgPStFwdOutProfPkts,
        tmnxFPNetIngQgPStFwdOutProfPktsL,
        tmnxFPNetIngQgPStFwdOutProfPktsH,
        tmnxFPNetIngQgPStFwdInProfOcts,
        tmnxFPNetIngQgPStFwdInProfOctsL,
        tmnxFPNetIngQgPStFwdInProfOctsH,
        tmnxFPNetIngQgPStFwdOutProfOcts,
        tmnxFPNetIngQgPStFwdOutProfOctsL,
        tmnxFPNetIngQgPStFwdOutProfOctsH,
        tmnxFPNetIngQgPStUncolPktsOff,
        tmnxFPNetIngQgPStUncolPktsOffL,
        tmnxFPNetIngQgPStUncolPktsOffH,
        tmnxFPNetIngQgPStUncolOctsOff,
        tmnxFPNetIngQgPStUncolOctsOffL,
        tmnxFPNetIngQgPStUncolOctsOffH,
        tmnxFPAccIngQGrpPStatMode,
        tmnxFPAccIngQgPStOffHPrioPkts,
        tmnxFPAccIngQgPStOffHPrioPktsL,
        tmnxFPAccIngQgPStOffHPrioPktsH,
        tmnxFPAccIngQgPStDrpHPrioPkts,
        tmnxFPAccIngQgPStDrpHPrioPktsL,
        tmnxFPAccIngQgPStDrpHPrioPktsH,
        tmnxFPAccIngQgPStOffLPrioPkts,
        tmnxFPAccIngQgPStOffLPrioPktsL,
        tmnxFPAccIngQgPStOffLPrioPktsH,
        tmnxFPAccIngQgPStDrpLPrioPkts,
        tmnxFPAccIngQgPStDrpLPrioPktsL,
        tmnxFPAccIngQgPStDrpLPrioPktsH,
        tmnxFPAccIngQgPStOffHPrioOcts,
        tmnxFPAccIngQgPStOffHPrioOctsL,
        tmnxFPAccIngQgPStOffHPrioOctsH,
        tmnxFPAccIngQgPStDrpHPrioOcts,
        tmnxFPAccIngQgPStDrpHPrioOctsL,
        tmnxFPAccIngQgPStDrpHPrioOctsH,
        tmnxFPAccIngQgPStOffLPrioOcts,
        tmnxFPAccIngQgPStOffLPrioOctsL,
        tmnxFPAccIngQgPStOffLPrioOctsH,
        tmnxFPAccIngQgPStDrpLPrioOcts,
        tmnxFPAccIngQgPStDrpLPrioOctsL,
        tmnxFPAccIngQgPStDrpLPrioOctsH,
        tmnxFPAccIngQgPStFwdInProfPkts,
        tmnxFPAccIngQgPStFwdInProfPktsL,
        tmnxFPAccIngQgPStFwdInProfPktsH,
        tmnxFPAccIngQgPStFwdOutProfPkts,
        tmnxFPAccIngQgPStFwdOutProfPktsL,
        tmnxFPAccIngQgPStFwdOutProfPktsH,
        tmnxFPAccIngQgPStFwdInProfOcts,
        tmnxFPAccIngQgPStFwdInProfOctsL,
        tmnxFPAccIngQgPStFwdInProfOctsH,
        tmnxFPAccIngQgPStFwdOutProfOcts,
        tmnxFPAccIngQgPStFwdOutProfOctsL,
        tmnxFPAccIngQgPStFwdOutProfOctsH,
        tmnxFPAccIngQgPStUncolPktsOff,
        tmnxFPAccIngQgPStUncolPktsOffL,
        tmnxFPAccIngQgPStUncolPktsOffH,
        tmnxFPAccIngQgPStUncolOctsOff,
        tmnxFPAccIngQgPStUncolOctsOffL,
        tmnxFPAccIngQgPStUncolOctsOffH,
        tFPNetIngQGrpArbitStatFwdPkts,
        tFPNetIngQGrpArbitStatFwdPktsL,
        tFPNetIngQGrpArbitStatFwdPktsH,
        tFPNetIngQGrpArbitStatFwdOcts,
        tFPNetIngQGrpArbitStatFwdOctsL,
        tFPNetIngQGrpArbitStatFwdOctsH,
        tFPAccIngQGrpArbitStatFwdPkts,
        tFPAccIngQGrpArbitStatFwdPktsL,
        tFPAccIngQGrpArbitStatFwdPktsH,
        tFPAccIngQGrpArbitStatFwdOcts,
        tFPAccIngQGrpArbitStatFwdOctsL,
        tFPAccIngQGrpArbitStatFwdOctsH
    }
    STATUS      current
    DESCRIPTION
        "The group of objects added in 10.0 release to support forwarding-plane
         queue-group objects on Nokia SROS series systems."
    ::= { tmnxChassisGroups 60 }

tmnxCardV10v0Group               OBJECT-GROUP
    OBJECTS     {
        tmnxCardHardResetUnsupMdas,
        tmnxCardRateCalcFastQueue,
        tmnxCardRateCalcSlowQueue,
        tmnxCardSchedRun,
        tmnxCardTaskScheduling,
        tmnxCardSlowQueueThresh
    }
    STATUS      current
    DESCRIPTION
        "The group of objects added in 10.0 release to enhance IOM Card
         features on Nokia SROS series systems."
    ::= { tmnxChassisGroups 61 }

tmnxIpsecV10v0Group              OBJECT-GROUP
    OBJECTS     {
        tmnxIPsecIsaGrpTunnelReassembly,
        tmnxIPsecIsaGrpOperFlags,
        tmnxIPsecIsaGrpIpTunnels,
        tmnxIPsecIsaGrpIpMaxTunnels
    }
    STATUS      current
    DESCRIPTION
        "The group of objects added in 10.0 release to ipsec features on Nokia
         SROS series systems."
    ::= { tmnxChassisGroups 62 }

tmnxChassisV10v0Group            OBJECT-GROUP
    OBJECTS     {
        tmnxFanTrayCompSpeed,
        tmnxFabricSupportedTypes,
        tmnxFabricReboot,
        tmnxFabricTypeName,
        tmnxFabricTypeDescription,
        tmnxFabricTypeStatus,
        tmnxHwResourceCurrentVoltage,
        tmnxHwResourcePeakVoltage,
        tmnxHwResourcePeakVoltageTime,
        tmnxHwResourceMinVoltage,
        tmnxHwResourceMinVoltageTime,
        tmnxHwResourceCurrentWattage,
        tmnxHwResourcePeakWattage,
        tmnxHwResourcePeakWattageTime,
        tmnxHwResourceMinWattage,
        tmnxHwResourceMinWattageTime,
        tmnxHwResourceCurrentAmperage,
        tmnxHwResourcePeakAmperage,
        tmnxHwResourcePeakAmperageTime,
        tmnxHwResourceMinAmperage,
        tmnxHwResourceMinAmperageTime,
        tmnxHwFirmwareRevisionStatus
    }
    STATUS      current
    DESCRIPTION
        "The group of objects added in 10.0 release to enhance hardware
         functionality on Nokia SROS series systems."
    ::= { tmnxChassisGroups 63 }

tmnxChassisNotificationV9v0Group NOTIFICATION-GROUP
    NOTIFICATIONS {
        tmnxPeFirmwareVersionWarning,
        tmnxEqCardQChipBufMemoryEvent,
        tmnxEqCardQChipStatsMemoryEvent,
        tmnxEqCardQChipIntMemoryEvent,
        tmnxEqCardChipIfDownEvent,
        tmnxEqCardChipIfCellEvent
    }
    STATUS      current
    DESCRIPTION
        "The group of notifications supporting the management of chassis
         hardware for release 9.0 on Nokia SROS series systems."
    ::= { tmnxChassisGroups 64 }

tmnxFPQGrpV10v0R4Group           OBJECT-GROUP
    OBJECTS     {
        tFPAccIngQGrpPlcrOvrTblLstChgd,
        tFPAccIngQGrpPlcrOvrRowStatus,
        tFPAccIngQGrpPlcrOvrLastChgd,
        tFPAccIngQGrpPlcrOvrAdminPIR,
        tFPAccIngQGrpPlcrOvrAdminCIR,
        tFPAccIngQGrpPlcrOvrStatMode,
        tFPAccIngQGrpPlcrOvrMBS,
        tFPAccIngQGrpPlcrOvrCBS,
        tFPAccIngQGrpPlcrOvrPktOffset
    }
    STATUS      current
    DESCRIPTION
        "The group of objects added in 10.0 release to support forwarding-plane
         queue-group policer override objects on Nokia SROS series systems."
    ::= { tmnxChassisGroups 65 }

tmnxMdaV10v0Group                OBJECT-GROUP
    OBJECTS     {
        tmnxMDAIsaTunnelGroup,
        tmnxIPsecIsaGrpIPsecRespondOnly,
        tmnxIPsecIsaGrpMultiActive,
        tmnxIPsecIsaGrpActiveMda,
        tmnxMDAIsaTunnelGroupInUse,
        tmnxMDAFailOnError,
        tmnxMDAEgrXplErrThreshold,
        tmnxMDAEgrXplErrWindow,
        tmnxMDAIngrXplErrThreshold,
        tmnxMDAIngrXplErrWindow
    }
    STATUS      obsolete
    DESCRIPTION
        "The group of objects added in 10.0 release to enhance IOM MDA features
         on Nokia SROS series systems."
    ::= { tmnxChassisGroups 66 }

tmnxChassisNotifyV10v0Group      NOTIFICATION-GROUP
    NOTIFICATIONS {
        tmnxMDAIsaTunnelGroupChange
    }
    STATUS      current
    DESCRIPTION
        "The group of notifications supporting the management of chassis
         hardware for release 10.0 on Nokia SROS series systems."
    ::= { tmnxChassisGroups 69 }

tmnxChassisV11v0Groups           OBJECT IDENTIFIER ::= { tmnxChassisGroups 71 }

tmnxFPDCpuProtV11v0R0Group       OBJECT-GROUP
    OBJECTS     {
        tmnxFPDCpuProtDynEnfrcPlcrPool,
        tmnxFpDcpDynPlcrHiWtrMrkHitCnt,
        tmnxFpDcpDynPlcrHiWtrMrkTime,
        tmnxFpDcpDynPlcrAllocFailCount,
        tmnxFpDcpDynPlcrInUse
    }
    STATUS      current
    DESCRIPTION
        "The group of objects added in 11.0 release to support forwarding-plane
         objects on Nokia SROS series systems."
    ::= { tmnxChassisV11v0Groups 1 }

tmnxFPDcpNotifyObjsV11v0Group    OBJECT-GROUP
    OBJECTS     {
        tmnxDcpTimeEventOccured,
        tmnxDcpMissingNotificationCount,
        tmnxChassisNotifyCardSlotNum
    }
    STATUS      current
    DESCRIPTION
        "The group of objects supporting management of Distributed CPU
         Protection feature for forwarding-plane on version 11.0 Nokia SROS
         series systems."
    ::= { tmnxChassisV11v0Groups 2 }

tmnxFPDcpNotifyV11v0Group        NOTIFICATION-GROUP
    NOTIFICATIONS {
        tmnxDcpCardFpEventOvrflw,
        tmnxDcpCardSapEventOvrflw,
        tmnxDcpCardVrtrIfEventOvrflw,
        tmnxDcpFpDynPoolUsageHiAlmRaise,
        tmnxDcpFpDynPoolUsageHiAlmClear,
        tmnxDcpCardFpEventOvrflwClr,
        tmnxDcpCardSapEventOvrflwClr,
        tmnxDcpCardVrtrIfEventOvrflwClr
    }
    STATUS      current
    DESCRIPTION
        "The group of notifications supporting management of Distributed CPU
         Protection feature for forwarding-plane on version 11.0 Nokia SROS
         series systems."
    ::= { tmnxChassisV11v0Groups 3 }

tmnxChassisObsoleteGroupV11v0    OBJECT-GROUP
    OBJECTS     {
        tmnxHwMfgString
    }
    STATUS      current
    DESCRIPTION
        "The group of objects obsoleted in 11.0 release on Nokia SROS series
         systems."
    ::= { tmnxChassisV11v0Groups 4 }

tmnxChassisV11v0Group            OBJECT-GROUP
    OBJECTS     {
        tmnxChassisTotalNumber,
        tmnxChassisLastChange,
        tmnxChassisRowStatus,
        tmnxChassisName,
        tmnxChassisType,
        tmnxChassisLocation,
        tmnxChassisCoordinates,
        tmnxChassisNumSlots,
        tmnxChassisNumPorts,
        tmnxChassisCriticalLEDState,
        tmnxChassisMajorLEDState,
        tmnxChassisMinorLEDState,
        tmnxChassisBaseMacAddress,
        tmnxChassisCLLICode,
        tmnxChassisReboot,
        tmnxChassisUpgrade,
        tmnxChassisAdminMode,
        tmnxChassisOperMode,
        tmnxChassisModeForce,
        tmnxChassisUpdateTimeLeft,
        tmnxChassisTypeName,
        tmnxChassisTypeDescription,
        tmnxChassisTypeStatus
    }
    STATUS      current
    DESCRIPTION
        "The group of objects supporting management of generic chassis
         capabilities on release 11.0 of Nokia SROS series systems."
    ::= { tmnxChassisV11v0Groups 5 }

tmnxChassisFanV11v0Group         OBJECT-GROUP
    OBJECTS     {
        tmnxChassisNumFanTrays,
        tmnxChassisNumFans,
        tmnxChassisFanOperStatus,
        tmnxChassisFanSpeed
    }
    STATUS      current
    DESCRIPTION
        "The group of objects supporting management of chassis Fan hardware
         capabilities on release 11.0 of Nokia SROS series systems."
    ::= { tmnxChassisV11v0Groups 6 }

tmnxChassisPowerV11v0Group       OBJECT-GROUP
    OBJECTS     {
        tmnxChassisNumPwrSupplies,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType
    }
    STATUS      current
    DESCRIPTION
        "The group of objects supporting management of chassis power supply
         hardware capabilities on release 11.0 of Nokia SROS series systems."
    ::= { tmnxChassisV11v0Groups 7 }

tmnxChassisHwV11v0Group          OBJECT-GROUP
    OBJECTS     {
        tmnxHwLastChange,
        tmnxHwID,
        tmnxHwMfgBoardNumber,
        tmnxHwSerialNumber,
        tmnxHwManufactureDate,
        tmnxHwClass,
        tmnxHwName,
        tmnxHwAlias,
        tmnxHwAssetID,
        tmnxHwCLEI,
        tmnxHwIsFRU,
        tmnxHwContainedIn,
        tmnxHwParentRelPos,
        tmnxHwAdminState,
        tmnxHwOperState,
        tmnxHwTempSensor,
        tmnxHwTemperature,
        tmnxHwTempThreshold,
        tmnxHwBootCodeVersion,
        tmnxHwSoftwareCodeVersion,
        tmnxHwSwLastBoot,
        tmnxHwAlarmState,
        tmnxHwSwImageSource,
        tmnxHwMfgDeviations,
        tmnxHwBaseMacAddress,
        tmnxHwFailureReason,
        tmnxHwContainedIndex
    }
    STATUS      current
    DESCRIPTION
        "The group of objects supporting management of chassis hardware
         capabilities on release 11.0 of Nokia SROS series systems."
    ::= { tmnxChassisV11v0Groups 8 }

tmnxChassisQGrpOvrGroup          OBJECT-GROUP
    OBJECTS     {
        tFPNetIngQGrpPlcrOvrTblLstChgd,
        tFPNetIngQGrpPlcrOvrRowStatus,
        tFPNetIngQGrpPlcrOvrLastChgd,
        tFPNetIngQGrpPlcrOvrAdminPIR,
        tFPNetIngQGrpPlcrOvrAdminCIR,
        tFPNetIngQGrpPlcrOvrStatMode,
        tFPNetIngQGrpPlcrOvrMBS,
        tFPNetIngQGrpPlcrOvrCBS,
        tFPNetIngQGrpPlcrOvrPktOffset,
        tFPAccIngQGrpPCPOvrLastChgd,
        tFPAccIngQGrpPCPOvrLvlLastChgd,
        tFPAccIngQGrpPCPOvrLvlMBS,
        tFPAccIngQGrpPCPOvrLvlTblLstChgd,
        tFPAccIngQGrpPCPOvrMaxRate,
        tFPAccIngQGrpPCPOvrMinMBSSep,
        tFPAccIngQGrpPCPOvrRowStatus,
        tFPAccIngQGrpPCPOvrTblLastChgd,
        tFPNetIngQGrpPCPOvrLastChgd,
        tFPNetIngQGrpPCPOvrLvlLastChgd,
        tFPNetIngQGrpPCPOvrLvlMBS,
        tFPNetIngQGrpPCPOvrLvlTblLstChgd,
        tFPNetIngQGrpPCPOvrMaxRate,
        tFPNetIngQGrpPCPOvrMinMBSSep,
        tFPNetIngQGrpPCPOvrRowStatus,
        tFPNetIngQGrpPCPOvrTblLastChgd
    }
    STATUS      current
    DESCRIPTION
        "The group of objects supporting management of policer control policies
         capabilities on release 11.0 of Nokia SROS series systems."
    ::= { tmnxChassisV11v0Groups 9 }

tmnxFPPoolSizingV11v0Group       OBJECT-GROUP
    OBJECTS     {
        tmnxFPStablePoolSizing
    }
    STATUS      current
    DESCRIPTION
        "The group of objects supporting management of policer control policies
         capabilities on release 11.0 of Nokia SROS series systems."
    ::= { tmnxChassisV11v0Groups 10 }

tmnxChassisPowerMgmtGroup        OBJECT-GROUP
    OBJECTS     {
        tmnxChassisPEQTableLastChg,
        tmnxChassisPEQLastChangedTime,
        tmnxChassisPowerMgmtTableLastChg,
        tmnxChassisPwrMgmtChangedTime,
        tmnxChassisPEQAssignedType,
        tmnxChassisPEQAvailableWattage,
        tmnxChassisPEQEquippedType,
        tmnxChassisPEQSupportedTypes,
        tmnxPEQTypeDescription,
        tmnxPEQTypeName,
        tmnxChassisPwrMgmtMode,
        tmnxChassisPwrMgmtSafetyLevel,
        tmnxChassisPwrMgmtSafetyAlert,
        tmnxMDAHwPowerPriority,
        tmnxHwResourceMaxRequiredWattage,
        tmnxHwPowerZone
    }
    STATUS      current
    DESCRIPTION
        "The group of objects supporting the management of power utilization
         capabilities on release 11.0 of Nokia SROS series systems."
    ::= { tmnxChassisV11v0Groups 11 }

tmnxChassisPowerMgmtNotifyObjs   OBJECT-GROUP
    OBJECTS     {
        tmnxChassisNotifyPowerZone,
        tmnxChassisNotifyPowerCapacity
    }
    STATUS      current
    DESCRIPTION
        "The group of notification-objects supporting the management of power
         utilization capabilities on release 11.0 of Nokia SROS series systems."
    ::= { tmnxChassisV11v0Groups 12 }

tmnxChassisPowerMgmtNotifyGroup  NOTIFICATION-GROUP
    NOTIFICATIONS {
        tmnxEqPowerCapacityExceeded,
        tmnxEqPowerCapacityExceededClear,
        tmnxEqPowerLostCapacity,
        tmnxEqPowerLostCapacityClear,
        tmnxEqPowerOverloadState,
        tmnxEqPowerOverloadStateClear,
        tmnxEqPowerSafetyAlertThreshold,
        tmnxEqPowerSafetyAlertClear,
        tmnxEqPowerSafetyLevelThreshold,
        tmnxEqPowerSafetyLevelClear,
        tmnxEqProvPowerCapacityAlm,
        tmnxEqProvPowerCapacityAlmClr
    }
    STATUS      current
    DESCRIPTION
        "The group of notifications supporting the management of power
         utilization capabilities on release 11.0 of Nokia SROS series systems."
    ::= { tmnxChassisV11v0Groups 13 }

tmnxChassisSmartPeqV11v0Group    OBJECT-GROUP
    OBJECTS     {
        tmnxChassisPowerSupplyInFeedDown
    }
    STATUS      current
    DESCRIPTION
        "The group of objects supporting the management of smart PEQ
         capabilities on release 11.0 of Nokia SROS series systems."
    ::= { tmnxChassisV11v0Groups 14 }

tmnxChassisSmartPeqNtfyV11v0Grp  NOTIFICATION-GROUP
    NOTIFICATIONS {
        tmnxEqPowerSupplyInputFeedAlm,
        tmnxEqPowerSupplyInputFeedAlmClr
    }
    STATUS      obsolete
    DESCRIPTION
        "The group of notifications supporting the management of smart PEQ
         capabilities on release 11.0 of Nokia SROS series systems."
    ::= { tmnxChassisV11v0Groups 15 }

tmnxChassisFabricV11v0Group      OBJECT-GROUP
    OBJECTS     {
        tmnxChassisFabricSpeed
    }
    STATUS      current
    DESCRIPTION
        "The group of objects supporting the management of the system fabric
         speed on release 11.0 of Nokia SROS series systems."
    ::= { tmnxChassisV11v0Groups 16 }

tmnxChassisSwitchFabNtfyV11v0Grp NOTIFICATION-GROUP
    NOTIFICATIONS {
        tmnxEqLowSwitchFabricCap,
        tmnxEqLowSwitchFabricCapClear
    }
    STATUS      current
    DESCRIPTION
        "The group of notifications supporting chassis switch fabric management
         on release 11.0 of Nokia SROS series systems."
    ::= { tmnxChassisV11v0Groups 17 }

tmnxCpmCardRebootHoldV11v0Group  OBJECT-GROUP
    OBJECTS     {
        tmnxCpmCardRebootHold
    }
    STATUS      current
    DESCRIPTION
        "The group of additional objects supporting CPM standby reboot hold in
         release 11.0 of Nokia SROS series systems."
    ::= { tmnxChassisV11v0Groups 18 }

tmnxChassisV9v0Groups            OBJECT IDENTIFIER ::= { tmnxChassisGroups 72 }

tmnxCpmCardCmplxMemErrV9v0Group  OBJECT-GROUP
    OBJECTS     {
        tmnxCpmCardCmplxMemErrOccur,
        tmnxCpmCardCmplxMemErrOccurTime
    }
    STATUS      current
    DESCRIPTION
        "The group of objects supporting management of CPM complex memory
         errors on release 9.0 of Nokia SROS series systems."
    ::= { tmnxChassisV9v0Groups 1 }

tmnxCardCmplQChipMemErrV9v0Group OBJECT-GROUP
    OBJECTS     {
        tmnxCardCmpl1BufMemErrOccur,
        tmnxCardCmpl1BufMemErrOccurTime,
        tmnxCardCmpl2BufMemErrOccur,
        tmnxCardCmpl2BufMemErrOccurTime,
        tmnxCardCmpl1StatMemErrOccur,
        tmnxCardCmpl1StatMemErrOccurTime,
        tmnxCardCmpl2StatMemErrOccur,
        tmnxCardCmpl2StatMemErrOccurTime,
        tmnxCardCmpl1IntMemErrOccur,
        tmnxCardCmpl1IntMemErrOccurTime,
        tmnxCardCmpl2IntMemErrOccur,
        tmnxCardCmpl2IntMemErrOccurTime,
        tmnxCpmCardCmplBufMemErrOcc,
        tmnxCpmCardCmplBufMemErrOccTime,
        tmnxCpmCardCmplStatMemErrOcc,
        tmnxCpmCardCmplStatMemErrOccTime,
        tmnxCpmCardCmplIntMemErrOcc,
        tmnxCpmCardCmplIntMemErrOccTime
    }
    STATUS      current
    DESCRIPTION
        "The group of objects supporting management of card complex Q-chip
         memory errors on release 9.0 of Nokia SROS series systems."
    ::= { tmnxChassisV9v0Groups 2 }

tmnxCardCmplChipIfErrV9v0Group   OBJECT-GROUP
    OBJECTS     {
        tmnxCardCmpl1ChipIfDownOcc,
        tmnxCardCmpl1ChipIfDownOccTime,
        tmnxCardCmpl2ChipIfDownOcc,
        tmnxCardCmpl2ChipIfDownOccTime,
        tmnxCardCmpl1ChipIfCellOcc,
        tmnxCardCmpl1ChipIfCellOccTime,
        tmnxCardCmpl2ChipIfCellOcc,
        tmnxCardCmpl2ChipIfCellOccTime,
        tmnxCpmCardCmplChipIfDownOcc,
        tmnxCpmCardCmplChipIfDownOccTime,
        tmnxCpmCardCmplChipIfCellOcc,
        tmnxCpmCardCmplChipIfCellOccTime
    }
    STATUS      current
    DESCRIPTION
        "The group of objects supporting management of card complex chip
         interface errors on release 9.0 of Nokia SROS series systems."
    ::= { tmnxChassisV9v0Groups 3 }

tmnxChassisHwEventGroup          OBJECT-GROUP
    OBJECTS     {
        tmnxCardHwEventNumOccurrences,
        tmnxCardHwEventLastOccurTime
    }
    STATUS      current
    DESCRIPTION
        "The group of additional objects supporting Hardware event detection
         and reporting in release 9.0 of Nokia SROS series systems."
    ::= { tmnxChassisV9v0Groups 4 }

tmnxChassisHwEventNotifyGroup    NOTIFICATION-GROUP
    NOTIFICATIONS {
        tmnxEqCardTChipParityEvent
    }
    STATUS      current
    DESCRIPTION
        "The group of additional notification-types supporting Hardware event
         detection and reporting in release 9.0 of Nokia SROS series systems."
    ::= { tmnxChassisV9v0Groups 5 }

tmnxChassisPowerSupplyV9v0Grp    OBJECT-GROUP
    OBJECTS     {
        tmnxChassisPowerSupplyPemACRect
    }
    STATUS      current
    DESCRIPTION
        "The group of additional objects supporting chassis power supplies in
         release 9.0 of Nokia SROS series systems."
    ::= { tmnxChassisV9v0Groups 6 }

tmnxChassisV12v0Groups           OBJECT IDENTIFIER ::= { tmnxChassisGroups 73 }

tmnxChassisResourceV12v0Group    OBJECT-GROUP
    OBJECTS     {
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResQosIntSchedsTotal,
        tCardResQosIntSchedsAlloc,
        tCardResSubSPIQosOvrTotal,
        tCardResSubSPIQosOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResIntArbiterTotal,
        tFPResIntArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResResRvplsFdbRecTotal,
        tFPResResRvplsFdbRecAlloc,
        tFPResDynQ2NamedPoolTotal,
        tFPResDynQ2NamedPoolAlloc,
        tFPResDynQ2NamedPoolIUBI,
        tFPResDynQ2NamedPoolIUBE,
        tFPResIngQ1NamedPoolTotal,
        tFPResIngQ1NamedPoolAlloc,
        tFPResEgrQ1NamedPoolTotal,
        tFPResEgrQ1NamedPoolAlloc,
        tFPResDynQ2WredPoolTotal,
        tFPResDynQ2WredPoolAlloc
    }
    STATUS      obsolete
    DESCRIPTION
        "The group of objects supporting management of System Resource
         Information on release 12.0 of Nokia SROS series systems."
    ::= { tmnxChassisV12v0Groups 1 }

tmnxFPBufAllocV12v0Group         OBJECT-GROUP
    OBJECTS     {
        tmnxFPIngressBufferAllocation
    }
    STATUS      current
    DESCRIPTION
        "The group of objects supporting management of buffer allocation for
         named pools on release 12.0 of Nokia SROS series systems."
    ::= { tmnxChassisV12v0Groups 2 }

tmnxFPPlcyAcctV12v0Group         OBJECT-GROUP
    OBJECTS     {
        tmnxFPPlcyAcctStatsPool,
        tmnxFPPlcyAcctStatsInUse
    }
    STATUS      current
    DESCRIPTION
        "The group of objects supporting management of stats pool for policy
         accounting on release 12.0 of Nokia SROS series systems."
    ::= { tmnxChassisV12v0Groups 3 }

tmnxPhysChassisGroup             OBJECT-GROUP
    OBJECTS     {
        tmnxPhysChassisRole,
        tmnxPhysChassisState,
        tmnxPhysChassisHwIndex,
        tmnxPhysChassisNumPwrSupplies,
        tmnxPhysChassisNumFanTrays,
        tmnxPhysChassisNumFans,
        tmnxPhysChassisName
    }
    STATUS      current
    DESCRIPTION
        "The group of objects supporting management of physical chassis on
         release 12.0 of Nokia SROS series systems."
    ::= { tmnxChassisV12v0Groups 4 }

tmnxChassisNotifV12v0Group       NOTIFICATION-GROUP
    NOTIFICATIONS {
        tmnxEqDataPathFailureProtImpact,
        tmnxExtStandbyCpmReboot,
        tmnxExtStandbyCpmRebootFail
    }
    STATUS      current
    DESCRIPTION
        "The group of notifications supporting chassis management on release
         12.0 of Nokia SROS series systems."
    ::= { tmnxChassisV12v0Groups 5 }

tmnxCpmCardRebootHoldV12v0Group  OBJECT-GROUP
    OBJECTS     {
        tmnxCpmCardRebootHold
    }
    STATUS      obsolete
    DESCRIPTION
        "The group of additional objects supporting CPM standby reboot hold in
         release 12.0 of Nokia SROS series systems."
    ::= { tmnxChassisV12v0Groups 6 }

tmnxChassisPlcyAcctNtfyV12v0Grp  NOTIFICATION-GROUP
    NOTIFICATIONS {
        tmnxPlcyAcctStatsPoolExcResource,
        tmnxPlcyAcctStatsPoolLowResource,
        tmnxPlcyAcctStatsEventOvrflw,
        tmnxPlcyAcctStatsEventOvrflwClr
    }
    STATUS      current
    DESCRIPTION
        "The group of notifications supporting the management of policy
         accounting on release 12.0 of Nokia SROS series systems."
    ::= { tmnxChassisV12v0Groups 7 }

tmnxChassisV12v0Group            OBJECT-GROUP
    OBJECTS     {
        tmnxChassisOperNumSlots,
        tmnxChassisOperTopology
    }
    STATUS      current
    DESCRIPTION
        "The group of objects supporting management of generic chassis
         capabilities on release 12.0 of Nokia SROS series systems."
    ::= { tmnxChassisV12v0Groups 8 }

tmnxChassisObsoleteV12v0Group    OBJECT-GROUP
    OBJECTS     {
        tmnxChassisAdminLastSetTimer,
        tmnxChassisAdminLastSetTimeout
    }
    STATUS      current
    DESCRIPTION
        "The group of objects obsoleted in 12.0 release on Nokia SROS series
         systems."
    ::= { tmnxChassisV12v0Groups 9 }

tmnxChassPANotifyObjsV12v0Grp    OBJECT-GROUP
    OBJECTS     {
        tmnxPlcyAcctMissingNotifCount,
        tmnxPlcyAcctTimeEventOccured
    }
    STATUS      current
    DESCRIPTION
        "The group of objects supporting the management of policy accounting on
         release 12.0 of Nokia SROS series systems."
    ::= { tmnxChassisV12v0Groups 10 }

tmnxChassisNotifyObjsV12v0Group  OBJECT-GROUP
    OBJECTS     {
        tmnxChassisNotifyCpmCardSlotNum,
        tmnxChassisNotifyFabricSlotNum
    }
    STATUS      current
    DESCRIPTION
        "The group of notification-objects supporting management of generic
         chassis capabilities on release 12.0 of Nokia SROS series systems."
    ::= { tmnxChassisV12v0Groups 11 }

tmnxIomResrcNotifyObjsV12v0Grp   OBJECT-GROUP
    OBJECTS     {
        tmnxIomResourceType,
        tmnxIomResourceLimitPct,
        tmnxIomResLimMissingNotifCount,
        tmnxIomResLimitTimeEventOccured,
        tmnxChassisNotifyFpNum
    }
    STATUS      current
    DESCRIPTION
        "The group of objects supporting the management of IOM resources on
         release 12.0 of Nokia SROS series systems."
    ::= { tmnxChassisV12v0Groups 12 }

tmnxIomResrcNotifyV12v0Group     NOTIFICATION-GROUP
    NOTIFICATIONS {
        tmnxIomResHighLimitReached,
        tmnxIomResExhausted,
        tmnxIomResStateClr,
        tmnxIomEventOverflow,
        tmnxIomEventOverflowClr
    }
    STATUS      current
    DESCRIPTION
        "The group of notifications supporting the management of IOM resources
         on release 12.0 of Nokia SROS series systems."
    ::= { tmnxChassisV12v0Groups 13 }

tmnxChassisFabricV12v0Group      OBJECT-GROUP
    OBJECTS     {
        tmnxChassisFabricSpeed
    }
    STATUS      obsolete
    DESCRIPTION
        "The group of objects supporting the management of the system fabric
         speed on release 12.0 of Nokia SROS series systems."
    ::= { tmnxChassisV12v0Groups 14 }

tmnxChassisPowerV12v0Group       OBJECT-GROUP
    OBJECTS     {
        tmnxChassisPowerSupplyFanDir
    }
    STATUS      current
    DESCRIPTION
        "The group of objects supporting the management of power supply
         hardware capabilities on release 12.0 of Nokia SROS series systems."
    ::= { tmnxChassisV12v0Groups 15 }

tmnxChassisPowerNotifV12v0Group  NOTIFICATION-GROUP
    NOTIFICATIONS {
        tmnxPowerSupplyWrongFanDir,
        tmnxPowerSupplyWrongFanDirClear
    }
    STATUS      obsolete
    DESCRIPTION
        "The group of notifications supporting the management of power supply
         hardware capabilities on release 12.0 of Nokia SROS series systems."
    ::= { tmnxChassisV12v0Groups 16 }

tmnxMDAResetOnRecoverErGrp       OBJECT-GROUP
    OBJECTS     {
        tmnxMDAResetOnRecoverableError
    }
    STATUS      current
    DESCRIPTION
        "The tmnxMDAResetOnRecoverErGrp contains objects for the MDA reset on
         recoverable error capability on Nokia SROS series systems for release
         12.0."
    ::= { tmnxChassisV12v0Groups 17 }

tmnxCardResetOnRecoverErGrp      OBJECT-GROUP
    OBJECTS     {
        tmnxCardResetOnRecoverableError
    }
    STATUS      current
    DESCRIPTION
        "The tmnxCardResetOnRecoverErGrp contains objects for the card reset on
         recoverable error capability on Nokia SROS series systems for release
         12.0."
    ::= { tmnxChassisV12v0Groups 18 }

tmnxCpmMemSizeNotifGroupV12v0    NOTIFICATION-GROUP
    NOTIFICATIONS {
        tmnxCpmMemSizeMismatch,
        tmnxCpmMemSizeMismatchClear
    }
    STATUS      current
    DESCRIPTION
        "The group of notifications supporting CPM memory size mismatch in
         release 12.0 on Nokia SROS series systems."
    ::= { tmnxChassisV12v0Groups 19 }

tmnxCpmPChipFcsObjGroupV12v0     OBJECT-GROUP
    OBJECTS     {
        tmnxCpmCardCmplxIngrFcsOccur,
        tmnxCpmCardCmplxIngrFcsOccurTime,
        tmnxCpmCardCmplxEgrFcsOccur,
        tmnxCpmCardCmplxEgrFcsOccurTime,
        tmnxCpmCardCmplxEgrFcsSrcSlots
    }
    STATUS      current
    DESCRIPTION
        "The group of objects supporting CPM PChip management in release 12.0
         on Nokia SROS series systems."
    ::= { tmnxChassisV12v0Groups 20 }

tmnxChassisV13v0Groups           OBJECT IDENTIFIER ::= { tmnxChassisGroups 74 }

tmnxChassisResourceV13v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResIntArbiterTotal,
        tFPResIntArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResResRvplsFdbRecTotal,
        tFPResResRvplsFdbRecAlloc,
        tFPResDynQ2NamedPoolTotal,
        tFPResDynQ2NamedPoolAlloc,
        tFPResDynQ2NamedPoolIUBI,
        tFPResDynQ2NamedPoolIUBE,
        tFPResIngQ1NamedPoolTotal,
        tFPResIngQ1NamedPoolAlloc,
        tFPResEgrQ1NamedPoolTotal,
        tFPResEgrQ1NamedPoolAlloc,
        tFPResDynQ2WredPoolTotal,
        tFPResDynQ2WredPoolAlloc,
        tFPResIngIPv6AclFilterTotal,
        tFPResIngIPv6AclFilterAlloc,
        tFPResEgrIPv6AclFilterTotal,
        tFPResEgrIPv6AclFilterAlloc
    }
    STATUS      obsolete
    DESCRIPTION
        "The group of objects supporting management of System Resource
         Information on release 13.0 of Nokia SROS series systems."
    ::= { tmnxChassisV13v0Groups 1 }

tmnxCardVirtualSchAdjV13v0Group  OBJECT-GROUP
    OBJECTS     {
        tmnxCardInternalSchedWghtMode
    }
    STATUS      current
    DESCRIPTION
        "The group of objects supporting management of enhancing IOM Card
         features on release 13.0 of Nokia SROS series systems."
    ::= { tmnxChassisV13v0Groups 2 }

tmnxPhysChassisV13v0Group        OBJECT-GROUP
    OBJECTS     {
        tmnxPhysChassisDescription
    }
    STATUS      current
    DESCRIPTION
        "The group of objects supporting management of physical chassis on
         release 13.0 of Nokia SROS series systems."
    ::= { tmnxChassisV13v0Groups 3 }

tChassisResObsoletedV13v0Group   OBJECT-GROUP
    OBJECTS     {
        tCardResQosIntSchedsTotal,
        tCardResQosIntSchedsAlloc
    }
    STATUS      current
    DESCRIPTION
        "The group of objects obsoleted in release 13.0 of Nokia SROS series
         systems."
    ::= { tmnxChassisV13v0Groups 4 }

tmnxChassisV13v0Group            OBJECT-GROUP
    OBJECTS     {
        tmnxChassisPortIdScheme
    }
    STATUS      current
    DESCRIPTION
        "The group of additional objects supporting the management of chassis
         capabilities on release 13.0 of Nokia SROS series systems."
    ::= { tmnxChassisV13v0Groups 5 }

tmnxChassisMgmtEthRedNtfV13v0Grp NOTIFICATION-GROUP
    NOTIFICATIONS {
        tmnxEqMgmtEthRedStandbyRaise,
        tmnxEqMgmtEthRedStandbyClear
    }
    STATUS      current
    DESCRIPTION
        "The group of notifications supporting management Ethernet redundancy
         in release 13.0 of Nokia SROS series systems."
    ::= { tmnxChassisV13v0Groups 6 }

tmnxChassisMgmtEthRedV13v0Grp    OBJECT-GROUP
    OBJECTS     {
        tmnxChassisMgmtEthRed,
        tmnxChassisMgmtEthRedRevertTime,
        tmnxChassisMgmtEthRedStandby
    }
    STATUS      current
    DESCRIPTION
        "The group of objects supporting management Ethernet redundancy in
         release 13.0 of Nokia SROS series systems."
    ::= { tmnxChassisV13v0Groups 7 }

tmnxChassisPowerMgmtGroupV13v0   OBJECT-GROUP
    OBJECTS     {
        tmnxChassisPEQInputPowerMode,
        tmnxPEQTypeNumInputFeed
    }
    STATUS      current
    DESCRIPTION
        "The group of additional objects supporting the management of power
         utilization capabilities on release 13.0 of Nokia SROS series systems."
    ::= { tmnxChassisV13v0Groups 8 }

tmnxChassisNotifV13v0Group       NOTIFICATION-GROUP
    NOTIFICATIONS {
        tmnxSyncIfTimBITS2048khzUnsup,
        tmnxSyncIfTimBITS2048khzUnsupClr,
        tmnxEqBpEpromFail,
        tmnxEqBpEpromFailClear,
        tmnxEqBpEpromWarning,
        tmnxEqBpEpromWarningClear
    }
    STATUS      current
    DESCRIPTION
        "The group of additional notifications supporting chassis management in
         release 13.0 on Nokia SROS series systems."
    ::= { tmnxChassisV13v0Groups 9 }

tmnxChassisNotifyObjsV13v0Grp    OBJECT-GROUP
    OBJECTS     {
        tmnxChassisNotifyDiskFullReason,
        tmnxChassisNotifyMgmtEthRedPort
    }
    STATUS      current
    DESCRIPTION
        "The group of accessible-for-notify objects supporting chassis
         management in release 13.0 of Nokia SROS series systems."
    ::= { tmnxChassisV13v0Groups 10 }

tmnxChassisFpResourceV13v0Group  OBJECT-GROUP
    OBJECTS     {
        tFPResEgrQosBypassTotal,
        tFPResEgrQosBypassAlloc
    }
    STATUS      current
    DESCRIPTION
        "The group of objects supporting management of System Resource
         Information on release 13.0 of Nokia SROS series systems."
    ::= { tmnxChassisV13v0Groups 11 }

tmnxFPV13v0Group                 OBJECT-GROUP
    OBJECTS     {
        tmnxFPInitExtractDropPrioMode
    }
    STATUS      current
    DESCRIPTION
        "The group of additional objects supporting management of the
         forwarding plane on release 13.0 of Nokia SROS series systems."
    ::= { tmnxChassisV13v0Groups 12 }

tmnxCpmCardV13v0Group            OBJECT-GROUP
    OBJECTS     {
        tmnxCpmCardUuid
    }
    STATUS      current
    DESCRIPTION
        "The group of additional objects supporting management of CPM cards on
         release 13.0 of Nokia SROS series systems."
    ::= { tmnxChassisV13v0Groups 13 }

tmnxChassisV10v0Groups           OBJECT IDENTIFIER ::= { tmnxChassisGroups 75 }

tmnxChassisHwEventGroupV10v0     OBJECT-GROUP
    OBJECTS     {
        tmnxMdaHwEventNumOccurrences,
        tmnxMdaHwEventLastOccurTime
    }
    STATUS      current
    DESCRIPTION
        "The group of additional objects supporting Hardware event detection
         and reporting in release 10.0 of Nokia SROS series systems."
    ::= { tmnxChassisV10v0Groups 1 }

tmnxChassisHwEventNotifyGrpV10v0 NOTIFICATION-GROUP
    NOTIFICATIONS {
        tmnxEqMdaIngrXplError
    }
    STATUS      current
    DESCRIPTION
        "The group of additional notification-types supporting Hardware event
         detection and reporting in release 10.0 of Nokia SROS series systems."
    ::= { tmnxChassisV10v0Groups 2 }

tmnxChassisV14v0Groups           OBJECT IDENTIFIER ::= { tmnxChassisGroups 76 }

tmnxSyncIfTimingV14v0Group       OBJECT-GROUP
    OBJECTS     {
        tmnxSyncIfTimingBITSOutQlMin,
        tSyncIfTimingAdmBITSOutQlMin,
        tmnxSyncIfTimingBITSOutSquelch,
        tSyncIfTimingAdmBITSOutSquelch,
        tmnxSyncIfTimingQlMin,
        tSyncIfTimingAdmQlMin,
        tmnxSyncIfTimingWaitToRestorTime,
        tSyncIfTimingAdmWaitToRestorTime,
        tSyncIfTimingAdmChangedMask
    }
    STATUS      current
    DESCRIPTION
        "The group of additional objects supporting the management of
         synchronous interface timing capabilities in release 14.0 of Nokia
         SROS series systems."
    ::= { tmnxChassisV14v0Groups 1 }

tmnxChassisResourceV14v0Group    OBJECT-GROUP
    OBJECTS     {
        tCardResQosUserSchedOvrsTotal,
        tCardResQosUserSchedOvrsAlloc,
        tCardResCategoryEntriesTotal,
        tCardResCategoryEntriesAlloc,
        tChassisResSapTotal,
        tChassisResSapAlloc,
        tFPResSapInstanceTotal,
        tFPResSapInstanceAlloc,
        tMDAResSapInstanceTotal,
        tMDAResSapInstanceAlloc
    }
    STATUS      current
    DESCRIPTION
        "The group of objects supporting management of System Resource
         Information on release 14.0 of Nokia SROS series systems."
    ::= { tmnxChassisV14v0Groups 2 }

tmnxCpmFlashV14v0Group           OBJECT-GROUP
    OBJECTS     {
        tmnxCpmFlashPercentageUsed
    }
    STATUS      current
    DESCRIPTION
        "The group of additional objects supporting the management of compact
         flash in release 14.0 of Nokia SROS series systems."
    ::= { tmnxChassisV14v0Groups 3 }

tmnxPhysChassisGroupV14v0        OBJECT-GROUP
    OBJECTS     {
        tmnxPhysChassisFanOperStatus,
        tmnxPhysChassisFanSpeed,
        tmnxPhysChassisFanRevision,
        tmnxPhysChassPowerSupACStatus,
        tmnxPhysChassPowerSupDCStatus,
        tmnxPhysChassPowerSupTempStatus,
        tmnxPhysChassPowerSupTempThrshld,
        tmnxPhysChassPowerSup1Status,
        tmnxPhysChassPowerSup2Status,
        tmnxPhysChassPowerSupAssignType,
        tmnxPhysChassPowerSupInputStatus,
        tmnxPhysChassPowerSupOutptStatus,
        tmnxPhysChassPowerSupPemType,
        tmnxPhysChassPowerSupPemACRect,
        tmnxPhysChassPowerSupInFeedDown,
        tmnxPhysChassPowerSupFanDir
    }
    STATUS      current
    DESCRIPTION
        "The group of objects supporting management of physical chassis in
         release 14.0 of Nokia SROS series systems."
    ::= { tmnxChassisV14v0Groups 4 }

tFPFwdEngStatsGroup              OBJECT-GROUP
    OBJECTS     {
        tFwdEngDREgrEncapExceeded,
        tFwdEngDREgrPortMtuExceeded
    }
    STATUS      current
    DESCRIPTION
        "The group of objects supporting management of forward engine drop
         statistics on forwarding plane for release 14.0 on Nokia SROS series
         systems."
    ::= { tmnxChassisV14v0Groups 5 }

tmnxPhysChassisNotifGroupV14v0   NOTIFICATION-GROUP
    NOTIFICATIONS {
        tmnxEqPhysChassPowerSupOvrTmp,
        tmnxEqPhysChassPowerSupOvrTmpClr,
        tmnxEqPhysChassPowerSupAcFail,
        tmnxEqPhysChassPowerSupAcFailClr,
        tmnxEqPhysChassPowerSupDcFail,
        tmnxEqPhysChassPowerSupDcFailClr,
        tmnxEqPhysChassPowerSupInFail,
        tmnxEqPhysChassPowerSupInFailClr,
        tmnxEqPhysChassPowerSupOutFail,
        tmnxEqPhysChassPowerSupOutFailCl,
        tmnxEqPhysChassisFanFailure,
        tmnxEqPhysChassisFanFailureClear
    }
    STATUS      current
    DESCRIPTION
        "The group of notifications supporting physical chassis management in
         release 14.0 on Nokia SROS series systems."
    ::= { tmnxChassisV14v0Groups 6 }

tmnxIsaMemWMarkNotifGroupV14v0   NOTIFICATION-GROUP
    NOTIFICATIONS {
        tIPsecIsaMemLowWatermark,
        tIPsecIsaMemHighWatermark,
        tIPsecIsaMemMax
    }
    STATUS      current
    DESCRIPTION
        "The group of notifications supporting ISA card memory watermarks in
         release 14.0 on Nokia SROS series systems."
    ::= { tmnxChassisV14v0Groups 7 }

tmnxIsaGrpIsaScaleModeGroupV14v0 OBJECT-GROUP
    OBJECTS     {
        tmnxIPsecIsaGrpIsaScaleMode
    }
    STATUS      current
    DESCRIPTION
        "The group of objects supporting ISA scale mode in release 14.0 on
         Nokia SROS series systems."
    ::= { tmnxChassisV14v0Groups 9 }

tmnxCardVirtualGroupV14v0        OBJECT-GROUP
    OBJECTS     {
        tmnxCardVFpCpuCount,
        tmnxCardVFpAvgUtilization,
        tmnxCardVFpMaxUtilization,
        tmnxCardVCpuSchedHealth,
        tmnxCardVCpuSchedLastClearedTime
    }
    STATUS      current
    DESCRIPTION
        "The group of objects supporting management of virtual card statistics
         for release 14.0 on Nokia SROS series systems."
    ::= { tmnxChassisV14v0Groups 10 }

tmnxChassisV15v0Groups           OBJECT IDENTIFIER ::= { tmnxChassisGroups 77 }

tmnxCardFPEgrHsGroup             OBJECT-GROUP
    OBJECTS     {
        tmnxFPEgrHsPoolPolicy,
        tFPResEgrHsQGrpTotal,
        tFPResEgrHsQGrpAlloc,
        tFPResEgrHsPrimaryShapersTotal,
        tFPResEgrHsPrimaryShapersAlloc,
        tFPResEgrHsPrimaryShapersIUBES,
        tFPResEgrHsPrimaryShapersIUBMS,
        tFPResEgrHsSecondaryShapersTotal,
        tFPResEgrHsSecondaryShapersAlloc,
        tmnxFPEgrHsFixedHighThreshDelta,
        tFPResEgrHsTurboQGrpTotal,
        tFPResEgrHsTurboQGrpAlloc
    }
    STATUS      current
    DESCRIPTION
        "The group of objects supporting egress High Scale related objects on
         Nokia SROS series system."
    ::= { tmnxChassisV15v0Groups 1 }

tmnxChassisObsoletedV15v0Group   OBJECT-GROUP
    OBJECTS     {
        tmnxMDAHiBwMcastSource,
        tmnxMDAHiBwMcastAlarm,
        tmnxMDAHiBwMcastTapCount,
        tmnxMDAHiBwMcastGroup,
        tmnxMDAMcPathMgmtBwPlcyName,
        tmnxMDAMcPathMgmtPriPathLimit,
        tmnxMDAMcPathMgmtSecPathLimit,
        tmnxMDAMcPathMgmtAncPathLimit,
        tmnxMDAMcPathMgmtAdminState,
        tmnxMDAMcPathMgmtPriInUseBw,
        tmnxMDAMcPathMgmtSecInUseBw,
        tmnxMDAMcPathMgmtAncInUseBw,
        tmnxMDAMcPathMgmtBlkHoleInUseBw,
        tmnxPhysChassisFanSpeed,
        tmnxChassisFanOperStatus,
        tmnxChassisFanSpeed,
        tmnxChassisFanRevision,
        tmnxChassisFanSpeedPercent,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType,
        tmnxChassisPowerSupplyInputStatus,
        tmnxChassisPowerSupplyOutputStatus,
        tmnxChassisPowerSupplyPemType,
        tmnxChassisPowerSupplyPemACRect,
        tmnxChassisPowerSupplyInFeedDown,
        tmnxChassisPowerSupplyFanDir,
        tmnxChassisPEQTableLastChg,
        tmnxChassisPEQLastChangedTime,
        tmnxChassisPEQAssignedType,
        tmnxChassisPEQEquippedType,
        tmnxChassisPEQSupportedTypes,
        tmnxChassisPEQAvailableWattage,
        tmnxChassisPEQInputPowerMode
    }
    STATUS      current
    DESCRIPTION
        "The group of chassis objects obsoleted in release 15.0 of Nokia SROS
         series systems."
    ::= { tmnxChassisV15v0Groups 2 }

tmnxChassisFanV15v0Group         OBJECT-GROUP
    OBJECTS     {
        tmnxChassisFanSpeedPercent,
        tmnxPhysChassisFanSpeedPercent
    }
    STATUS      current
    DESCRIPTION
        "The group of objects supporting fans in release 15.0 of Nokia SROS
         series systems."
    ::= { tmnxChassisV15v0Groups 3 }

tmnxPhysChassisGroupV15v0        OBJECT-GROUP
    OBJECTS     {
        tmnxPhysChassisPEQTableLastChg,
        tmnxPhysChassisPEQLastChangeTime,
        tmnxPhysChassisPEQAssignedType,
        tmnxPhysChassisPEQEquippedType,
        tmnxPhysChassisPEQSupportedTypes,
        tmnxPhysChassisPEQAvailableWatt,
        tmnxPhysChassisPEQInputPowerMode
    }
    STATUS      current
    DESCRIPTION
        "The group of objects supporting management of physical chassis in
         release 15.0 of Nokia SROS series systems."
    ::= { tmnxChassisV15v0Groups 4 }

tmnxPhysChassisNotifGroupV15v0   NOTIFICATION-GROUP
    NOTIFICATIONS {
        tmnxPhysChassPwrSupWrgFanDir,
        tmnxPhysChassPwrSupWrgFanDirClr,
        tmnxPhysChassPwrSupPemACRect,
        tmnxPhysChassPwrSupPemACRectClr,
        tmnxPhysChassPwrSupInputFeed,
        tmnxPhysChassPwrSupInputFeedClr
    }
    STATUS      current
    DESCRIPTION
        "The group of additional notifications supporting management of
         physical chassis in release 15.0 of Nokia SROS series systems."
    ::= { tmnxChassisV15v0Groups 5 }

tmnxIcmpMtuExceededStatGroup     OBJECT-GROUP
    OBJECTS     {
        tFwdEngDREgrMtuExceeded
    }
    STATUS      current
    DESCRIPTION
        "The group of objects supporting management of physical chassis in
         release 15.0 of Nokia SROS series systems."
    ::= { tmnxChassisV15v0Groups 6 }

tmnxChassisGroupV15v0            OBJECT-GROUP
    OBJECTS     {
        tmnxChassisVsrCongestionMgmt,
        tmnxChassisAlarmLEDState
    }
    STATUS      current
    DESCRIPTION
        "The group of objects supporting management of chassis in release 15.0
         of Nokia SROS series systems."
    ::= { tmnxChassisV15v0Groups 7 }

tmnxChassNotifsObsoletedGrpV15v0 NOTIFICATION-GROUP
    NOTIFICATIONS {
        tmnxEqFanFailure,
        tmnxEqPowerSupplyFailure,
        tmnxEqPowerSupplyInputFeedAlm,
        tmnxEqPowerSupplyInputFeedAlmClr,
        tmnxEqPowerSupplyPemACRectAlm,
        tmnxEqPowerSupplyPemACRectAlmClr,
        tmnxPowerSupplyWrongFanDir,
        tmnxPowerSupplyWrongFanDirClear
    }
    STATUS      current
    DESCRIPTION
        "The group of notifications supporting the management of chassis
         hardware made obsolete in release 15.0 on Nokia SROS series systems."
    ::= { tmnxChassisV15v0Groups 8 }

tmnxCardResMacFdbUsgNotifGroup   NOTIFICATION-GROUP
    NOTIFICATIONS {
        tmnxCardResMacFdbHighUsgSet,
        tmnxCardResMacFdbHighUsgClr
    }
    STATUS      current
    DESCRIPTION
        "The group notifications supporting  MAC scale feature on Nokia SROS
         series systems release 15.0."
    ::= { tmnxChassisV15v0Groups 9 }

tmnxMacScaleNotifyObjsV15v0Grp   OBJECT-GROUP
    OBJECTS     {
        tmnxMacScaleCardSlotNum
    }
    STATUS      current
    DESCRIPTION
        "The group of accessible-for-notify objects supporting MAC scale
         feature in release 15.0 of Nokia SROS series systems."
    ::= { tmnxChassisV15v0Groups 10 }

tmnxMDAV15v0Group                OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMdaTypeName,
        tmnxMdaTypeDescription,
        tmnxMdaTypeStatus,
        tmnxMDAReboot,
        tmnxMDASynchronousEthernet,
        tmnxMDAIsaTunnelGroup,
        tmnxIPsecIsaGrpIPsecRespondOnly,
        tmnxIPsecIsaGrpMultiActive,
        tmnxIPsecIsaGrpActiveMda,
        tmnxMDAIsaTunnelGroupInUse,
        tmnxMDAFailOnError,
        tmnxMDAEgrXplErrThreshold,
        tmnxMDAEgrXplErrWindow,
        tmnxMDAIngrXplErrThreshold,
        tmnxMDAIngrXplErrWindow
    }
    STATUS      obsolete
    DESCRIPTION
        "The group of objects supporting management of MDAs for release 15.0 on
         Nokia SROS series systems."
    ::= { tmnxChassisV15v0Groups 11 }

tmnxFPMcPathMgmtV15v0Group       OBJECT-GROUP
    OBJECTS     {
        tmnxFPMcPathMgmtPriInUseBw,
        tmnxFPMcPathMgmtSecInUseBw,
        tmnxFPMcPathMgmtBlkHoleInUseBw
    }
    STATUS      current
    DESCRIPTION
        "The group of additional objects supporting management of the
         forwarding plane on release 15.0 of Nokia SROS series systems."
    ::= { tmnxChassisV15v0Groups 12 }

tmnxChassisResourceV15v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResIntArbiterTotal,
        tFPResIntArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResDynQ2NamedPoolTotal,
        tFPResDynQ2NamedPoolAlloc,
        tFPResDynQ2NamedPoolIUBI,
        tFPResDynQ2NamedPoolIUBE,
        tFPResIngQ1NamedPoolTotal,
        tFPResIngQ1NamedPoolAlloc,
        tFPResEgrQ1NamedPoolTotal,
        tFPResEgrQ1NamedPoolAlloc,
        tFPResDynQ2WredPoolTotal,
        tFPResDynQ2WredPoolAlloc,
        tFPResIngIPv6AclFilterTotal,
        tFPResIngIPv6AclFilterAlloc,
        tFPResEgrIPv6AclFilterTotal,
        tFPResEgrIPv6AclFilterAlloc
    }
    STATUS      obsolete
    DESCRIPTION
        "The group of objects supporting management of System Resource
         Information on release 15.0 of Nokia SROS series systems."
    ::= { tmnxChassisV15v0Groups 13 }

tmnxChassisResrcObsoletedGroup   OBJECT-GROUP
    OBJECTS     {
        tFPResResRvplsFdbRecTotal,
        tFPResResRvplsFdbRecAlloc
    }
    STATUS      current
    DESCRIPTION
        "The group of obsoleted objects supporting management of System
         Resource Information on release 15.0 of Nokia SROS series systems."
    ::= { tmnxChassisV15v0Groups 14 }

tmnxCardFPResIngV15v0QGroup      OBJECT-GROUP
    OBJECTS     {
        tFPResIngQGrpRedirTotal,
        tFPResIngQGrpRedirAlloc
    }
    STATUS      current
    DESCRIPTION
        "The group of objects supporting ingress queue group related objects on
         Nokia SROS series system."
    ::= { tmnxChassisV15v0Groups 15 }

tmnxCardFPResEgrV15v0QGroup      OBJECT-GROUP
    OBJECTS     {
        tFPResSapInstEgrQGrpRedirTotal,
        tFPResSapInstEgrQGrpRedirAlloc
    }
    STATUS      current
    DESCRIPTION
        "The group of objects supporting egress queue group related objects on
         Nokia SROS series system."
    ::= { tmnxChassisV15v0Groups 16 }

tmnxIPsecIsaGrpV15v0Group        OBJECT-GROUP
    OBJECTS     {
        tmnxIPsecIsaGrpDpCpuUsageCollEn,
        tmnxIPsecIsaGrpTrafficFwdCollEn
    }
    STATUS      current
    DESCRIPTION
        "The group of objects supporting ISA tunnel group related objects on
         Nokia SROS series systems for release 15.0."
    ::= { tmnxChassisV15v0Groups 17 }

tmnxPhysChassisPCMGroupV15v0     OBJECT-GROUP
    OBJECTS     {
        tmnxPhysChassisFanType,
        tmnxPhysChassisPCMTableLastChg,
        tmnxPhysChassisPCMEntryLastChg,
        tmnxPhysChassisPCMEquippedType,
        tmnxPhysChassisPCMAssignedType,
        tmnxPhysChassisPCMInFeedDown
    }
    STATUS      current
    DESCRIPTION
        "The group of objects supporting management of Power Connection Modules
         in release 15.0 of Nokia SROS series systems."
    ::= { tmnxChassisV15v0Groups 18 }

tmnxMinFpGenerationGroupV15v0    OBJECT-GROUP
    OBJECTS     {
        tmnxFPGeneration,
        tmnxChassisFPGenerationFP2,
        tmnxChassisFPGenerationFP3,
        tmnxChassisFPGenerationFP4,
        tmnxChassisFPGenerationVFP
    }
    STATUS      current
    DESCRIPTION
        "The group of objects supporting minimum Forwarding Plane (FP) network
         processor generation requirements in release 15.0 on Nokia SROS series
         systems."
    ::= { tmnxChassisV15v0Groups 19 }

tmnxPhysChassPCMNotifGroupV15v0  NOTIFICATION-GROUP
    NOTIFICATIONS {
        tmnxPhysChassisPCMInputFeed,
        tmnxPhysChassisPCMInputFeedClr
    }
    STATUS      current
    DESCRIPTION
        "The group of additional notifications supporting management of PCM in
         release 15.0 of Nokia SROS series systems."
    ::= { tmnxChassisV15v0Groups 20 }

tmnxChassisV16v0Groups           OBJECT IDENTIFIER ::= { tmnxChassisGroups 78 }

tmnxCardV16v0Group               OBJECT-GROUP
    OBJECTS     {
        tmnxVmCardHypervisor,
        tmnxVmCardCpu,
        tmnxVmCardNumCores,
        tmnxVmCpmCardHypervisor,
        tmnxVmCpmCardCpu,
        tmnxVmCpmCardNumCores,
        tmnxCardFilterScaleProfile
    }
    STATUS      current
    DESCRIPTION
        "The group of objects supporting management of hardware cards that were
         added in the release 16 of the Nokia SROS series systems."
    ::= { tmnxChassisV16v0Groups 1 }

tmnxCardComplexGroupV16v0        OBJECT-GROUP
    OBJECTS     {
        tmnxCardComplexIngFcsError,
        tmnxCardComplexIngFcsErrTime,
        tmnxCardComplexEgrFcsError,
        tmnxCardComplexEgrFcsErrTime,
        tmnxCardComplexMemParError,
        tmnxCardComplexMemParErrTime,
        tmnxCardComplexCamError,
        tmnxCardComplexCamErrTime,
        tmnxCardComplexBufMemError,
        tmnxCardComplexBufMemErrTime,
        tmnxCardComplexStatsMemError,
        tmnxCardComplexStatsMemErrTime,
        tmnxCardComplexIntMemError,
        tmnxCardComplexIntMemErrTime,
        tmnxCardComplexIntDatapathError,
        tmnxCardComplexIntDatapthErrTime,
        tmnxCardComplexIntDpCellError,
        tmnxCardComplexIntDpCellErrTime,
        tmnxCardComplexSrcSlotsEgFcsErr
    }
    STATUS      current
    DESCRIPTION
        "The group of objects supporting management of card complex statistics
         on Nokia SROS series systems for release 16.0."
    ::= { tmnxChassisV16v0Groups 2 }

tmnxChassisGroupV16v0            OBJECT-GROUP
    OBJECTS     {
        tmnxChassisNumPhysicalPorts
    }
    STATUS      current
    DESCRIPTION
        "The group of objects supporting management of chassis objects on Nokia
         SROS series systems for release 16.0."
    ::= { tmnxChassisV16v0Groups 3 }

tmnxChassisResourceV16v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tCardResIntArbiterOvrsTotal,
        tCardResIntArbiterOvrsAlloc,
        tCardResSLAProfileInstanceTotal,
        tCardResSLAProfileInstanceAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResDynQ2NamedPoolTotal,
        tFPResDynQ2NamedPoolAlloc,
        tFPResDynQ2NamedPoolIUBI,
        tFPResDynQ2NamedPoolIUBE,
        tFPResDynQ2WredPoolTotal,
        tFPResDynQ2WredPoolAlloc,
        tFPResIngIPv6AclFilterTotal,
        tFPResIngIPv6AclFilterAlloc,
        tFPResEgrIPv6AclFilterTotal,
        tFPResEgrIPv6AclFilterAlloc,
        tFPResSLAProfileInstanceTotal,
        tFPResSLAProfileInstanceAlloc
    }
    STATUS      obsolete
    DESCRIPTION
        "The group of objects supporting management of System Resource
         Information on release 16.0 of Nokia SROS series systems."
    ::= { tmnxChassisV16v0Groups 4 }

tmnxChassisResV16v0ObsoleteGroup OBJECT-GROUP
    OBJECTS     {
        tFPResIngQ1NamedPoolTotal,
        tFPResIngQ1NamedPoolAlloc,
        tFPResEgrQ1NamedPoolTotal,
        tFPResEgrQ1NamedPoolAlloc,
        tFPResIntArbiterTotal,
        tFPResIntArbiterAlloc
    }
    STATUS      current
    DESCRIPTION
        "The group of obsoleted objects supporting management of System
         Resource Information on release 16.0 of Nokia SROS series systems."
    ::= { tmnxChassisV16v0Groups 5 }

tmnxChassisFanObsoleteGroupV16v0 OBJECT-GROUP
    OBJECTS     {
        tmnxPhysChassisNumFans,
        tmnxFanTrayCompSpeed
    }
    STATUS      current
    DESCRIPTION
        "The group of obsoleted objects supporting management of fan
         information on Nokia SROS series systems for release 16.0."
    ::= { tmnxChassisV16v0Groups 6 }

tmnxPhysChassisPMGroupV16v0      OBJECT-GROUP
    OBJECTS     {
        tmnxPhysChassisPMTypeName,
        tmnxPhysChassisPMTypeDescription,
        tmnxPhysChassisPMTypeNumInFeed,
        tmnxPhysChassisPMTableLastChange,
        tmnxPhysChassisPMEntryLastChange,
        tmnxPhysChassisPMAssignedType,
        tmnxPhysChassisPMEquippedType,
        tmnxPhysChassisPMSupportedTypes,
        tmnxPhysChassisPMAvailableWatt,
        tmnxPhysChassisPMOutputStatus,
        tmnxPhysChassisPMInputFeedDown,
        tmnxPhysChassisMonitorFilterDoor,
        tmnxPhysChassisFilterDoorState
    }
    STATUS      current
    DESCRIPTION
        "The group of objects supporting management of Power Module
         capabilities on Nokia SROS series systems for release 16.0."
    ::= { tmnxChassisV16v0Groups 7 }

tmnxChassisGnssGroup             OBJECT-GROUP
    OBJECTS     {
        tmnxGnssTableLastChange,
        tmnxGnssCfgLastChanged,
        tmnxGnssAdminState,
        tmnxGnssConstellation,
        tmnxGnssNmeaAdminState,
        tmnxGnssNmeaSentenceTypes,
        tmnxGnssNmeaSentenceInterval,
        tmnxGnssOperState,
        tmnxGnssPositionValid,
        tmnxGnssDateTime,
        tmnxGnssLatitude,
        tmnxGnssLongitude,
        tmnxGnssAltitude,
        tmnxGnssHeading,
        tmnxGnssSpeed,
        tmnxGnssSatelliteType,
        tmnxGnssSatelliteElevation,
        tmnxGnssSatelliteAzimuth,
        tmnxGnssSatelliteSnr
    }
    STATUS      current
    DESCRIPTION
        "The group of objects supporting the GNSS receiver management."
    ::= { tmnxChassisV16v0Groups 9 }

tmnxMdaFlexGroupV16v0            OBJECT-GROUP
    OBJECTS     {
        tmnxMdaFlexGroupTableLastChanged,
        tmnxMdaFlexMemberTableLastChngd,
        tmnxMdaFlexClientTableLastChngd,
        tmnxMdaFlexGroupRowStatus,
        tmnxMdaFlexGroupEntryLastChanged,
        tmnxMdaFlexGroupAdminState,
        tmnxMdaFlexGroupOperState,
        tmnxMdaFlexGroupDescription,
        tmnxMdaFlexMemberRowStatus,
        tmnxMdaFlexMemberEntryLastChngd,
        tmnxMdaFlexMemberPhyNumber,
        tmnxMdaFlexClientRowStatus,
        tmnxMdaFlexClientEntryLastChngd,
        tmnxMdaFlexGroupMaxBandwidth
    }
    STATUS      current
    DESCRIPTION
        "The group of objects supporting the management of Flex for MDAs."
    ::= { tmnxChassisV16v0Groups 10 }

tmnxChassisGnssNotifGroup        NOTIFICATION-GROUP
    NOTIFICATIONS {
        tmnxGnssAcquiringFix,
        tmnxGnssAcquiredFix
    }
    STATUS      current
    DESCRIPTION
        "The group of notifications supporting management of GNSS in Nokia SROS
         series systems."
    ::= { tmnxChassisV16v0Groups 11 }

tmnxPhysChassisPMNotifGroupV16v0 NOTIFICATION-GROUP
    NOTIFICATIONS {
        tmnxPhysChassisPMInputFeed,
        tmnxPhysChassisPMInputFeedClr,
        tmnxPhysChassisPMOutFail,
        tmnxPhysChassisPMOutFailClr,
        tmnxPhysChassisFilterDoorOpen,
        tmnxPhysChassisFilterDoorClosed,
        tmnxPhysChassisPMOverTemp,
        tmnxPhysChassisPMOverTempClr
    }
    STATUS      current
    DESCRIPTION
        "The group of notifications supporting management of Power Module
         capabilities on Nokia SROS series systems for release 16.0."
    ::= { tmnxChassisV16v0Groups 12 }

tmnxNearFullNotifGroupV16v0      NOTIFICATION-GROUP
    NOTIFICATIONS {
        tmnxIPMacFilterIngNearFull,
        tmnxIPMacFilterIngNearFullClear,
        tmnxIPMacFilterEgrNearFull,
        tmnxIPMacFilterEgrNearFullClear,
        tmnxIPv6FilterIngNearFull,
        tmnxIPv6FilterIngNearFullClear,
        tmnxIPv6FilterEgrNearFull,
        tmnxIPv6FilterEgrNearFullClear
    }
    STATUS      current
    DESCRIPTION
        "The group of additional notifications supporting management of QoS
         Criteria, ACL Filter, and CPM Filter router complex overload in
         release 16.0 of Nokia SROS series systems."
    ::= { tmnxChassisV16v0Groups 13 }

tmnxCardV16v0ObsoleteGroup       OBJECT-GROUP
    OBJECTS     {
        tmnxCardVmHypervisor,
        tmnxCardVmCpu,
        tmnxCardVmNumCores,
        tmnxCpmCardVmHypervisor,
        tmnxCpmCardVmCpu,
        tmnxCpmCardVmNumCores,
        tmnxCardCmplx1IngrFcsOccur,
        tmnxCardCmplx1IngrFcsOccurTime,
        tmnxCardCmplx1EgrFcsOccur,
        tmnxCardCmplx1EgrFcsOccurTime,
        tmnxCardCmplx2IngrFcsOccur,
        tmnxCardCmplx2IngrFcsOccurTime,
        tmnxCardCmplx2EgrFcsOccur,
        tmnxCardCmplx2EgrFcsOccurTime,
        tmnxCardCmplx1MemParityOccur,
        tmnxCardCmplx1MemParityOccurTime,
        tmnxCardCmplx2MemParityOccur,
        tmnxCardCmplx2MemParityOccurTime,
        tmnxCardCmplx1CAMErrorOccur,
        tmnxCardCmplx1CAMErrorOccurTime,
        tmnxCardCmplx2CAMErrorOccur,
        tmnxCardCmplx2CAMErrorOccurTime,
        tmnxCardCmplx1EgrFcsSrcSlots,
        tmnxCardCmplx2EgrFcsSrcSlots,
        tmnxCardCmpl1BufMemErrOccur,
        tmnxCardCmpl1BufMemErrOccurTime,
        tmnxCardCmpl2BufMemErrOccur,
        tmnxCardCmpl2BufMemErrOccurTime,
        tmnxCardCmpl1StatMemErrOccur,
        tmnxCardCmpl1StatMemErrOccurTime,
        tmnxCardCmpl2StatMemErrOccur,
        tmnxCardCmpl2StatMemErrOccurTime,
        tmnxCardCmpl1IntMemErrOccur,
        tmnxCardCmpl1IntMemErrOccurTime,
        tmnxCardCmpl2IntMemErrOccur,
        tmnxCardCmpl2IntMemErrOccurTime,
        tmnxCardCmpl1ChipIfDownOcc,
        tmnxCardCmpl1ChipIfDownOccTime,
        tmnxCardCmpl2ChipIfDownOcc,
        tmnxCardCmpl2ChipIfDownOccTime,
        tmnxCardCmpl1ChipIfCellOcc,
        tmnxCardCmpl1ChipIfCellOccTime,
        tmnxCardCmpl2ChipIfCellOcc,
        tmnxCardCmpl2ChipIfCellOccTime
    }
    STATUS      current
    DESCRIPTION
        "The group of objects obsoleted in release 16 of the Nokia SROS series
         systems."
    ::= { tmnxChassisV16v0Groups 14 }

tmnxCardV16v0FpgaSoftErrNotifGrp NOTIFICATION-GROUP
    NOTIFICATIONS {
        tmnxEqFpgaSoftError
    }
    STATUS      current
    DESCRIPTION
        "The group of notifications supporting management of Fpga soft errors
         in release 16.0 of Nokia SROS series systems."
    ::= { tmnxChassisV16v0Groups 15 }

tmnxCardEncapGrpV16v5Group       OBJECT-GROUP
    OBJECTS     {
        tCardResEncapGrpMemberTotal,
        tCardResEncapGrpMemberAlloc
    }
    STATUS      current
    DESCRIPTION
        "The group of objects supporting management of hardware cards that were
         added in the release 16R5 of the Nokia SROS series systems."
    ::= { tmnxChassisV16v0Groups 16 }

tmnxMDAIsaTnlStatsV16v0Group     OBJECT-GROUP
    OBJECTS     {
        tmnxMDAIsaTnlStatsCryptoAcc
    }
    STATUS      current
    DESCRIPTION
        "The group of objects supporting management of MDA that were added in
         the release 16.0 of the Nokia SROS series systems."
    ::= { tmnxChassisV16v0Groups 17 }

tmnxCardPowerSaveGroupV16v0      OBJECT-GROUP
    OBJECTS     {
        tmnxCardPowerSave
    }
    STATUS      current
    DESCRIPTION
        "The group of objects supporting card power-save that were added in the
         release 16.0 of the Nokia SROS series systems."
    ::= { tmnxChassisV16v0Groups 18 }

tmnxChassPSStateGroupV22v0       OBJECT-GROUP
    OBJECTS     {
        tmnxPhysChassisPMFeedAInVolt,
        tmnxPhysChassisPMFeedBInVolt,
        tmnxPhysChassPSFeedAInVolt,
        tmnxPhysChassPSFeedBInVolt
    }
    STATUS      current
    DESCRIPTION
        "The group of objects supporting management of input voltage for
         power-supply and power-module elements added in release 22.0 of the
         Nokia SROS series systems."
    ::= { tmnxChassisV16v0Groups 19 }

tmnxCpmSecureBootGroupV22v0      OBJECT-GROUP
    OBJECTS     {
        tmnxCpmSecureBootEnabled,
        tmnxCpmSBUefiVarsStatus
    }
    STATUS      current
    DESCRIPTION
        "The group of objects supporting management of secure boot settings for
         CPM elements added in release 22.0 of the Nokia SROS series systems."
    ::= { tmnxChassisV16v0Groups 20 }

tmnxChassisV15v1Groups           OBJECT IDENTIFIER ::= { tmnxChassisGroups 79 }

tmnxBluetoothGroupV15v1          OBJECT-GROUP
    OBJECTS     {
        tmnxBluetoothTableLastChange,
        tmnxBluetoothPasskey,
        tmnxBluetoothAdvertisingTimeout,
        tmnxBluetoothPowerState,
        tmnxBluetoothPairingButton,
        tmnxBluetoothDeviceTableLastChg,
        tmnxBluetoothDeviceRowStatus,
        tmnxBluetoothDeviceEntryLastChg,
        tmnxBluetoothDeviceDescription,
        tmnxBluetoothModuleTableLastChg,
        tmnxBluetoothModuleEntryLastChg,
        tmnxBluetoothModuleCfgIdentifier,
        tmnxBluetoothModuleIdentifier,
        tmnxBluetoothModuleConnected,
        tmnxBluetoothModuleConnectedMac
    }
    STATUS      obsolete
    DESCRIPTION
        "The group of objects supporting management of Bluetooth capabilities
         on Nokia SROS series systems for release 15.1."
    ::= { tmnxChassisV15v1Groups 1 }

tmnxOverloadNotifGroupV15v1      NOTIFICATION-GROUP
    NOTIFICATIONS {
        tmnxIPMacQosIngOverload,
        tmnxIPMacQosIngOverloadClear,
        tmnxIPQosEgrOverload,
        tmnxIPQosEgrOverloadClear,
        tmnxIPv6QosIngOverload,
        tmnxIPv6QosIngOverloadClear,
        tmnxIPv6QosEgrOverload,
        tmnxIPv6QosEgrOverloadClear,
        tmnxIPMacFilterIngOverload,
        tmnxIPMacFilterIngOverloadClear,
        tmnxIPMacFilterEgrOverload,
        tmnxIPMacFilterEgrOverloadClear,
        tmnxIPv6FilterIngOverload,
        tmnxIPv6FilterIngOverloadClear,
        tmnxIPv6FilterEgrOverload,
        tmnxIPv6FilterEgrOverloadClear,
        tmnxIPMacCpmFilterOverload,
        tmnxIPMacCpmFilterOverloadClear,
        tmnxIPv6CpmFilterOverload,
        tmnxIPv6CpmFilterOverloadClear
    }
    STATUS      current
    DESCRIPTION
        "The group of additional notifications supporting management of QoS
         Criteria, ACL Filter, and CPM Filter router complex overload in
         release 15.1 of Nokia SROS series systems."
    ::= { tmnxChassisV15v1Groups 2 }

tmnxChassisSystemProfGroupV15v1  OBJECT-GROUP
    OBJECTS     {
        tmnxChassisSystemProfile
    }
    STATUS      current
    DESCRIPTION
        "The group of objects supporting system profiles in release 15.1 on
         Nokia SROS series systems."
    ::= { tmnxChassisV15v1Groups 3 }

tmnxCardResourceV15v1Group       OBJECT-GROUP
    OBJECTS     {
        tCardResIntArbiterTotal,
        tCardResIntArbiterAlloc
    }
    STATUS      current
    DESCRIPTION
        "The group of objects supporting management of card system resource
         information on release 15.1 of Nokia SROS series systems."
    ::= { tmnxChassisV15v1Groups 4 }

tmnxBluetoothNotifGroupV15v1     NOTIFICATION-GROUP
    NOTIFICATIONS {
        tmnxBluetoothModuleConnectionChg
    }
    STATUS      obsolete
    DESCRIPTION
        "The group of additional notifications supporting management of
         Bluetooth in release 15.1 of Nokia SROS series systems."
    ::= { tmnxChassisV15v1Groups 5 }

tmnxChassisCardLevelGroupV15v1   OBJECT-GROUP
    OBJECTS     {
        tmnxCardAssignedLevel,
        tmnxCardEquippedLevel,
        tmnxCardLicensedLevel,
        tmnxCardLicensedBandwidth,
        tmnxCardLevelName,
        tmnxCardLevelId,
        tmnxCardLevelDescription,
        tmnxCardLevelStatus,
        tmnxCardLevelUpgradeName,
        tmnxCardUpgradeLevelId,
        tmnxCardUpgradeRequiresReboot,
        tmnxCardLevelUpgradeRowStatus,
        tmnxCardAssignedLevelUpgradeId
    }
    STATUS      current
    DESCRIPTION
        "The group of objects supporting the management of licensing for cards
         with licensed variants."
    ::= { tmnxChassisV15v1Groups 6 }

tmnxChassisMdaLevelGroupV15v1    OBJECT-GROUP
    OBJECTS     {
        tmnxMDAAssignedLevel,
        tmnxMDAEquippedLevel,
        tmnxMDALicensedLevel,
        tmnxMDALicensedBandwidth,
        tmnxMdaLevelName,
        tmnxMdaLevelId,
        tmnxMdaLevelDescription,
        tmnxMdaLevelStatus,
        tmnxMDALevelUpgradeName,
        tmnxMDAUpgradeLevelId,
        tmnxMDAUpgradeRequiresReboot,
        tmnxMDALevelUpgradeRowStatus,
        tmnxMDAAssignedLevelUpgradeId
    }
    STATUS      current
    DESCRIPTION
        "The group of objects supporting the management of licensing for MDAs
         with licensed variants."
    ::= { tmnxChassisV15v1Groups 7 }

tmnxFPResourceV15v1Group         OBJECT-GROUP
    OBJECTS     {
        tFPResEgrUserQueueTotal,
        tFPResEgrUserQueueAlloc,
        tFPResEgrUserPolicerTotal,
        tFPResEgrUserPolicerAlloc
    }
    STATUS      current
    DESCRIPTION
        "The group of objects supporting management of FP system resource
         information on release 15.1 of Nokia SROS series systems."
    ::= { tmnxChassisV15v1Groups 8 }

tmnxChassisV19Groups             OBJECT IDENTIFIER ::= { tmnxChassisGroups 81 }

tmnxEsaGroup                     OBJECT-GROUP
    OBJECTS     {
        tmnxEsaLastChanged,
        tmnxEsaRowStatus,
        tmnxEsaAdminState,
        tmnxEsaDescription,
        tmnxEsaHwIndex,
        tmnxEsaReboot,
        tmnxEsaColdReboot,
        tmnxEsaHostPortRowStatus,
        tmnxEsaVmRowStatus,
        tmnxEsaVmLastChanged,
        tmnxEsaVmAdminState,
        tmnxEsaVmDescription,
        tmnxEsaVmType,
        tmnxEsaVmHostPortId,
        tmnxEsaVmCoreNumber,
        tmnxEsaVmMemorySize,
        tmnxEsaVmReboot,
        tmnxEsaStatsOperState,
        tmnxEsaStatsCoresAvailable,
        tmnxEsaStatsCoresAllocated,
        tmnxEsaStatsMemoryAvailable,
        tmnxEsaStatsMemoryAllocated,
        tmnxEsaStatsSoftwareVersion,
        tmnxEsaVmStatsOperState,
        tmnxEsaStatsOperFlags,
        tmnxEsaStatsTimeOfBoot,
        tmnxEsaVmStatsOperFlags,
        tmnxEsaVmStatsTimeOfBoot,
        tmnxEsaVmStatsSoftwareVersion,
        tmnxEsaVmStatsUtilLastChanged,
        tmnxEsaStatsSystemManufacturer,
        tmnxEsaStatsSystemProductName,
        tmnxEsaStatsSystemSerialNumber,
        tmnxEsaStatsPerformanceEnabled,
        tmnxEsaStatsExportRestricted,
        tmnxEsaVmVirtualCoreRoleName,
        tmnxEsaVmVirtCoreCurUtilization,
        tmnxEsaVmVirtCoreAvgUtilization,
        tmnxEsaVmVirtCorePeakUtilization
    }
    STATUS      current
    DESCRIPTION
        "The group of objects for ESA support on Nokia systems."
    ::= { tmnxChassisV19Groups 1 }

tmnxFPNetworkIngressGroupV19v5   OBJECT-GROUP
    OBJECTS     {
        tmnxFPIngNetQueuePolicy
    }
    STATUS      current
    DESCRIPTION
        "The group of objects supporting Forwarding Plane (FP) network ingress
         pool requirements in release 19.5 on Nokia SROS series systems."
    ::= { tmnxChassisV19Groups 2 }

tmnxCardV19v5Group               OBJECT-GROUP
    OBJECTS     {
        tmnxCardHashSeedShift
    }
    STATUS      current
    DESCRIPTION
        "The group of objects added for IOM card management in 19.5 on  Nokia
         SROS series systems."
    ::= { tmnxChassisV19Groups 3 }

tmnxSyncIfTimingV19v0Group       OBJECT-GROUP
    OBJECTS     {
        tSyncIfTimingAdmSyncECfgQltyLevl,
        tSyncIfTimingAdmSyncEAdminStatus,
        tmnxSyncIfTimingSyncEAdminStatus,
        tmnxSyncIfTimingSyncEInUse,
        tmnxSyncIfTimingSyncEQualified,
        tmnxSyncIfTimingSyncEAlarm,
        tmnxSyncIfTimingSyncECfgQltyLevl,
        tmnxSyncIfTimingSyncERxQltyLevel,
        tmnxSyncIfTimingSyncEState,
        tmnxSyncIfTimingSyncE2AdmnStatus,
        tmnxSyncIfTimingSyncE2InUse,
        tmnxSyncIfTimingSyncE2Qualified,
        tmnxSyncIfTimingSyncE2Alarm,
        tmnxSyncIfTimingSyncE2RxQltyLevl,
        tmnxSyncIfTimingSyncE2State,
        tSyncIfTimingAdmRefOrder5,
        tmnxSyncIfTimingRefOrder5
    }
    STATUS      current
    DESCRIPTION
        "The group on objects supporting the SyncE timing reference in 19.7 on
         Nokia SROS series systems."
    ::= { tmnxChassisV19Groups 4 }

tmnxChassisV19v0Group            OBJECT-GROUP
    OBJECTS     {
        tmnxHwEquippedPlatform,
        tmnxChassisRedForcedSingleSfm
    }
    STATUS      current
    DESCRIPTION
        "The group of objects supporting chassis in 19.0 release on Nokia SR
         series systems."
    ::= { tmnxChassisV19Groups 5 }

tmnxChassisV19v0ObsoleteGroup    OBJECT-GROUP
    OBJECTS     {
        tmnxChassisMixedModeIomAdminMode,
        tmnxChassisMixedModeIomUpgrList,
        tmnxCardCapability,
        tmnxMDANetworkIngQueues
    }
    STATUS      current
    DESCRIPTION
        "The group of objects supporting the Mixed Mode IOM feature obsoleted
         in 19.0 release on Nokia SR series systems."
    ::= { tmnxChassisV19Groups 6 }

tmnxMDAV19v0Group                OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDACapabilities,
        tmnxMDAMinChannelization,
        tmnxMDAMaxChannelization,
        tmnxMDAMaxChannels,
        tmnxMDAChannelsInUse,
        tmnxMdaTypeName,
        tmnxMdaTypeDescription,
        tmnxMdaTypeStatus,
        tmnxMDAReboot,
        tmnxMDASynchronousEthernet,
        tmnxMDAIsaTunnelGroup,
        tmnxIPsecIsaGrpIPsecRespondOnly,
        tmnxIPsecIsaGrpMultiActive,
        tmnxIPsecIsaGrpActiveMda,
        tmnxMDAIsaTunnelGroupInUse,
        tmnxMDAFailOnError,
        tmnxMDAEgrXplErrThreshold,
        tmnxMDAEgrXplErrWindow,
        tmnxMDAIngrXplErrThreshold,
        tmnxMDAIngrXplErrWindow
    }
    STATUS      obsolete
    DESCRIPTION
        "The group of objects supporting management of MDAs for release 19.0 on
         Nokia SROS series systems."
    ::= { tmnxChassisV19Groups 7 }

tmnxTunnelGrpEsaVmGroupV19v0     OBJECT-GROUP
    OBJECTS     {
        tmnxTunnelGrpEsaVmRowStatus,
        tmnxTunnelGrpEsaVmLastChgd,
        tmnxTunnelGrpEsaVmGroupAssoc,
        tmnxTunnelGrpEsaVmActive
    }
    STATUS      current
    DESCRIPTION
        "The group of objects supporting IPsec tunnel group ESA virtual machine
         members in release 19.10 on Nokia SROS series systems."
    ::= { tmnxChassisV19Groups 8 }

tmnxChassisResEgrV19v0Group      OBJECT-GROUP
    OBJECTS     {
        tChassisResEgrStatVlanVoQTotal,
        tChassisResEgrStatVlanVoQAlloc,
        tChassisResEgrNoStatVlanVoQTotal,
        tChassisResEgrNoStatVlanVoQAlloc
    }
    STATUS      current
    DESCRIPTION
        "The group of objects supporting management of Chassis Resource
         Information on release 19.5 of Nokia SROS series systems."
    ::= { tmnxChassisV19Groups 9 }

tmnxChassisResEgrRmrkV19v0Group  OBJECT-GROUP
    OBJECTS     {
        tChassisResEgrRemarkQosPolTotal,
        tChassisResEgrRemarkQosPolAlloc,
        tFPResEgrRemarkMapTotal,
        tFPResEgrRemarkMapAlloc,
        tFPResEgrExpRemarkMapTotal,
        tFPResEgrExpRemarkMapAlloc
    }
    STATUS      current
    DESCRIPTION
        "The group of objects supporting management of Resource Information
         related to Egress remark policy. This is for release 19.5 of Nokia IXR
         systems."
    ::= { tmnxChassisV19Groups 10 }

tmnxChassisResIngClassV19v0Group OBJECT-GROUP
    OBJECTS     {
        tChassisResIngClassQosPolTotal,
        tChassisResIngClassQosPolAlloc,
        tFPResIngClassMapTotal,
        tFPResIngClassMapAlloc,
        tFPResIngL2ClassMapTotal,
        tFPResIngL2ClassMapAlloc
    }
    STATUS      current
    DESCRIPTION
        "The group of objects supporting management of Resource Information
         related to Ingress Classification policy. This is for release 19.5 of
         Nokia IXR systems."
    ::= { tmnxChassisV19Groups 11 }

tmnxChassisResDynCAMV19v0Group   OBJECT-GROUP
    OBJECTS     {
        tFPResCamBanksTotal,
        tFPResCamBanksAlloc
    }
    STATUS      current
    DESCRIPTION
        "The group of objects supporting management of dynamic CAM bank
         allocation on the FP. This if for release 19.5 of Nokia IXR systems."
    ::= { tmnxChassisV19Groups 12 }

tmnxChassisResIpMacCAMV19v0Group OBJECT-GROUP
    OBJECTS     {
        tFPResIngIPv4QosEntryTotal,
        tFPResIngIPv4QosEntryAlloc,
        tFPResIngMacQosEntryTotal,
        tFPResIngMacQosEntryAlloc,
        tFPResIngIPv4AclEntryTotal,
        tFPResIngIPv4AclEntryAlloc,
        tFPResIngMacAclEntryTotal,
        tFPResIngMacAclEntryAlloc,
        tFPResEgrIPv4AclEntryTotal,
        tFPResEgrIPv4AclEntryAlloc,
        tFPResEgrMacAclEntryTotal,
        tFPResEgrMacAclEntryAlloc
    }
    STATUS      current
    DESCRIPTION
        "The group of objects supporting management of information about IPV4
         and MAC entry resource allocation. This is for release 19.5 of Nokia
         IXR systems."
    ::= { tmnxChassisV19Groups 13 }

tmnxChassisCoreResV19v0Group     OBJECT-GROUP
    OBJECTS     {
        tCoreResVlanVoqTotal,
        tCoreResVlanVoqAlloc
    }
    STATUS      current
    DESCRIPTION
        "The group of objects supporting management of Resource Information on
         a core. This is for release 19.5 of Nokia IXR systems."
    ::= { tmnxChassisV19Groups 14 }

tmnxSyncIfTimingV19v0NotifGroup  NOTIFICATION-GROUP
    NOTIFICATIONS {
        tmnxEqSyncIfTimingSyncEQuality,
        tmnxEqSyncIfTimingSyncE2Quality,
        tmnxEqSyncIfTimingSyncEAlarm,
        tmnxEqSyncIfTimingSyncEAlarmClr,
        tmnxEqSyncIfTimingSyncE2Alarm,
        tmnxEqSyncIfTimingSyncE2AlarmClr
    }
    STATUS      current
    DESCRIPTION
        "The group of additional notifications supporting management of
         sync-if-timing in release 19.7 of Nokia SROS series systems."
    ::= { tmnxChassisV19Groups 15 }

tmnxHwEventGroupV19v0            OBJECT-GROUP
    OBJECTS     {
        tmnxHwEventRowStatus,
        tmnxHwEventAction,
        tmnxHwEventNumOccurrences,
        tmnxHwEventLastOccurTime
    }
    STATUS      current
    DESCRIPTION
        "The group of objects supporting Hardware event detection and reporting
         in release 19.0 of Nokia SROS series systems."
    ::= { tmnxChassisV19Groups 16 }

tmnxHwEventNotifyObjsGrpV19v0    OBJECT-GROUP
    OBJECTS     {
        tmnxEqNotifyHwEventType,
        tmnxEqNotifyHwEventDetail,
        tmnxEqNotifyHwEventAction
    }
    STATUS      current
    DESCRIPTION
        "The group of objects supporting Hardware event detection and reporting
         in release 19.0 of Nokia SROS series systems."
    ::= { tmnxChassisV19Groups 17 }

tmnxHwEventNotifGroupV19v0       NOTIFICATION-GROUP
    NOTIFICATIONS {
        tmnxEqHwEventDetected
    }
    STATUS      current
    DESCRIPTION
        "The group of additional notifications supporting management of
         hardware events in release 19.0 of Nokia SROS series systems."
    ::= { tmnxChassisV19Groups 18 }

tmnxTunnelGrpEsaVmNotifGrpV19v0  NOTIFICATION-GROUP
    NOTIFICATIONS {
        tmnxTunnelGrpEsaVmActivity
    }
    STATUS      current
    DESCRIPTION
        "The group of notifications supporting management of tunnel group ESA
         virtual machine members in release 19.0 of Nokia SROS series systems."
    ::= { tmnxChassisV19Groups 19 }

tmnxEsaNotificationObjectGroup   OBJECT-GROUP
    OBJECTS     {
        tmnxEsaNotifyId,
        tmnxEsaVmNotifyId,
        tmnxEsaPortNotifyPortId,
        tmnxEsaHostPortNotifCrcAlrmValue,
        tmnxEsaHostPortNotifCrcMltiplier,
        tmnxEsaHostPortNotifCrcThreshold
    }
    STATUS      current
    DESCRIPTION
        "The group of objects supporting ESA notifications on Nokia systems."
    ::= { tmnxChassisV19Groups 20 }

tmnxEsaNotificationGroup         NOTIFICATION-GROUP
    NOTIFICATIONS {
        tmnxEsaDiscovered,
        tmnxEsaConnected,
        tmnxEsaDisconnected,
        tmnxEsaFailure,
        tmnxEsaCleared,
        tmnxEsaVmCreated,
        tmnxEsaVmBooted,
        tmnxEsaVmRemoved,
        tmnxEsaVmCleared,
        tmnxEsaVmFailure,
        tIPsecEsaVmMemLowWatermark,
        tIPsecEsaVmMemHighWatermark,
        tmnxEsaFirmwareUpgradeStarted,
        tmnxEsaColdRebooted
    }
    STATUS      current
    DESCRIPTION
        "The group of notifications for ESA on Nokia systems."
    ::= { tmnxChassisV19Groups 21 }

tmnxCardSapInstV19v0Group        OBJECT-GROUP
    OBJECTS     {
        tCardResSapInstanceTotal,
        tCardResSapInstanceAlloc,
        tCardResNonEpipeSapInstanceTotal,
        tCardResNonEpipeSapInstanceAlloc
    }
    STATUS      current
    DESCRIPTION
        "The group of objects supporting management of hardware cards that were
         added in the release 19R10 of the Nokia SROS series systems."
    ::= { tmnxChassisV19Groups 22 }

tmnxChassisResQMgmtV19v0Group    OBJECT-GROUP
    OBJECTS     {
        tChassisResQueueMgmtQosPolTotal,
        tChassisResQueueMgmtQosPolAlloc
    }
    STATUS      current
    DESCRIPTION
        "The group of objects supporting management of Resource Information
         related to Queue Management policy. This is for release 19.10 of Nokia
         IXR systems."
    ::= { tmnxChassisV19Groups 23 }

tmnxXiomGroupV20v0               OBJECT-GROUP
    OBJECTS     {
        tmnxXiomConfigTableLastChanged,
        tmnxXiomConfigEntryLastChanged,
        tmnxXiomAssignedType,
        tmnxXiomAssignedLevel,
        tmnxXiomReboot,
        tmnxXiomFailOnError,
        tmnxXiomResetOnRecoverableError,
        tmnxXiomEquippedType,
        tmnxXiomEquippedLevel,
        tmnxXiomLicensedLevel,
        tmnxXiomAvailableMdaSlots,
        tmnxXiomNumEquippedMdas,
        tmnxXiomHwIndex,
        tmnxXiomTypeName,
        tmnxXiomTypeDescription,
        tmnxXiomTypeStatus,
        tmnxXiomLevelName,
        tmnxXiomLevelId,
        tmnxXiomLevelDescription,
        tmnxXiomLevelStatus,
        tmnxXiomLvlUpgrdTableLastChanged,
        tmnxXiomLevelUpgradeRowStatus,
        tmnxXiomAssignedLevelUpgradeType,
        tmnxXiomLevelUpgradeName,
        tmnxXiomUpgradeLevelId,
        tmnxXiomUpgradeRequiresReboot,
        tmnxCardNumEquippedXioms
    }
    STATUS      current
    DESCRIPTION
        "The group of objects supporting management of XIOM in release 20 on
         Nokia SROS series systems."
    ::= { tmnxChassisV19Groups 24 }

tmnxSapResourceUsageV19v0Group   OBJECT-GROUP
    OBJECTS     {
        tChassisResApipeSapTotal,
        tChassisResApipeSapAlloc,
        tChassisResCpipeSapTotal,
        tChassisResCpipeSapAlloc,
        tChassisResEpipeSapTotal,
        tChassisResEpipeSapAlloc,
        tChassisResFpipeSapTotal,
        tChassisResFpipeSapAlloc,
        tChassisResIpipeSapTotal,
        tChassisResIpipeSapAlloc,
        tChassisResIesSapTotal,
        tChassisResIesSapAlloc,
        tChassisResMirrorSapTotal,
        tChassisResMirrorSapAlloc,
        tChassisResVplsSapTotal,
        tChassisResVplsSapAlloc,
        tChassisResVprnSapTotal,
        tChassisResVprnSapAlloc,
        tCardResApipeSapInstanceTotal,
        tCardResApipeSapInstanceAlloc,
        tCardResCpipeSapInstanceTotal,
        tCardResCpipeSapInstanceAlloc,
        tCardResEpipeSapInstanceTotal,
        tCardResEpipeSapInstanceAlloc,
        tCardResFpipeSapInstanceTotal,
        tCardResFpipeSapInstanceAlloc,
        tCardResIpipeSapInstanceTotal,
        tCardResIpipeSapInstanceAlloc,
        tCardResIesSapInstanceTotal,
        tCardResIesSapInstanceAlloc,
        tCardResMirrorSapInstanceTotal,
        tCardResMirrorSapInstanceAlloc,
        tCardResVplsSapInstanceTotal,
        tCardResVplsSapInstanceAlloc,
        tCardResVprnSapInstanceTotal,
        tCardResVprnSapInstanceAlloc
    }
    STATUS      obsolete
    DESCRIPTION
        "The group of objects supporting management of Saps that were added in
         the release 19R10 of the Nokia SROS series systems."
    ::= { tmnxChassisV19Groups 25 }

tmnxIPv6MCastCamV19v0Group       OBJECT-GROUP
    OBJECTS     {
        tFPResIPv6McastEntryTotal,
        tFPResIPv6McastEntryAlloc
    }
    STATUS      current
    DESCRIPTION
        "The group of objects supporting management of IPv6 multicast cam entry
         allocation."
    ::= { tmnxChassisV19Groups 26 }

tmnxSyncIfTimingV20v0NotifGroup  NOTIFICATION-GROUP
    NOTIFICATIONS {
        tmnxEqSyncIfTimingGnssQuality,
        tmnxEqSyncIfTimingGnss2Quality,
        tmnxEqSyncIfTimingGnssAlarm,
        tmnxEqSyncIfTimingGnssAlarmClr,
        tmnxEqSyncIfTimingGnss2Alarm,
        tmnxEqSyncIfTimingGnss2AlarmClr
    }
    STATUS      current
    DESCRIPTION
        "The group of additional notifications supporting management of
         sync-if-timing in release 20.0 of Nokia SROS series systems."
    ::= { tmnxChassisV19Groups 27 }

tmnxChassisCoreResPlcrV19v0Group OBJECT-GROUP
    OBJECTS     {
        tCoreResIngFloatPolicerTotal,
        tCoreResIngFloatPolicerAlloc,
        tCoreResIngFloatPolicerStatTotal,
        tCoreResIngFloatPolicerStatAlloc,
        tCoreResIngDdctdPolicerTotal,
        tCoreResIngDdctdPolicerAlloc,
        tCoreResIngDdctdPolicerStatTotal,
        tCoreResIngDdctdPolicerStatAlloc
    }
    STATUS      current
    DESCRIPTION
        "The group of objects supporting management of Resource Information on
         a core. This is for release 19.5 of Nokia IXR systems."
    ::= { tmnxChassisV19Groups 28 }

tmnxChassisV20Groups             OBJECT IDENTIFIER ::= { tmnxChassisGroups 82 }

tmnxChassisV20v0ObsoleteGroup    OBJECT-GROUP
    OBJECTS     {
        tmnxMcmSupportedTypes,
        tmnxMcmAssignedType,
        tmnxMcmEquippedType,
        tmnxMcmHwIndex,
        tmnxMcmTypeName,
        tmnxMcmTypeDescription,
        tmnxMcmTypeStatus,
        tmnxMDAIngNamedPoolPolicy,
        tmnxMDAEgrNamedPoolPolicy,
        tmnxCardNamedPoolAdminMode,
        tmnxCardNamedPoolOperMode,
        tFPResDynQ2NamedPoolTotal,
        tFPResDynQ2NamedPoolAlloc,
        tFPResDynQ2NamedPoolIUBI,
        tFPResDynQ2NamedPoolIUBE
    }
    STATUS      current
    DESCRIPTION
        "The group of chassis objects that were obsoleted in release 20.2 on
         Nokia SR series systems."
    ::= { tmnxChassisV20Groups 2 }

tmnxChassisNotifGroupV20v0       NOTIFICATION-GROUP
    NOTIFICATIONS {
        tmnxPeKernelVersionMismatch,
        tmnxFPResourcePolicyModified,
        tmnxFPResourcePolicyModifiedClr,
        tChassisAirflowDirMismatch,
        tChassisAirflowDirMismatchClr,
        tChassisPowerSupplyMismatch,
        tChassisPowerSupplyMismatchClr
    }
    STATUS      current
    DESCRIPTION
        "The group of additional notifications supporting chassis management in
         release 20 of Nokia SROS series systems."
    ::= { tmnxChassisV20Groups 3 }

tmnx77x0CESMDAV20v0Group         OBJECT-GROUP
    OBJECTS     {
        tmnxMDAClockMode,
        tmnxMDADiffTimestampFreq
    }
    STATUS      obsolete
    DESCRIPTION
        "The group of objects supporting management of CES MDAs for release
         20.0 on Nokia 77x0 SR series systems."
    ::= { tmnxChassisV20Groups 4 }

tmnxChassisResourceV20v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tCardResIntArbiterOvrsTotal,
        tCardResIntArbiterOvrsAlloc,
        tCardResSLAProfileInstanceTotal,
        tCardResSLAProfileInstanceAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResDynQ2WredPoolTotal,
        tFPResDynQ2WredPoolAlloc,
        tFPResIngIPv6AclFilterTotal,
        tFPResIngIPv6AclFilterAlloc,
        tFPResEgrIPv6AclFilterTotal,
        tFPResEgrIPv6AclFilterAlloc,
        tFPResSLAProfileInstanceTotal,
        tFPResSLAProfileInstanceAlloc
    }
    STATUS      obsolete
    DESCRIPTION
        "The group of objects supporting management of System Resource
         Information on release 20.0 of Nokia SROS series systems."
    ::= { tmnxChassisV20Groups 5 }

tmnxCardFPQosPolicyV20v0Group    OBJECT-GROUP
    OBJECTS     {
        tmnxFPQosFPResourcePolicy
    }
    STATUS      current
    DESCRIPTION
        "The group of objects supporting management of Qos Forwarding Plane
         (FP) resource policy in release 20.0 on Nokia SROS series systems."
    ::= { tmnxChassisV20Groups 6 }

tmnxSyncIfTimingV20v0ObsoleteGrp OBJECT-GROUP
    OBJECTS     {
        tmnxSyncIfTimingRef1SrcHw,
        tmnxSyncIfTimingRef1BITSIfType,
        tmnxSyncIfTimingRef2SrcHw,
        tmnxSyncIfTimingRef2BITSIfType,
        tSyncIfTimingAdmRef1SrcHw,
        tSyncIfTimingAdmRef1BITSIfType,
        tSyncIfTimingAdmRef2SrcHw,
        tSyncIfTimingAdmRef2BITSIfType,
        tmnxSyncIfTimingRef1NationalUse,
        tmnxSyncIfTimingRef2NationalUse,
        tSyncIfTimingAdmRef1NationalUse,
        tSyncIfTimingAdmRef2NationalUse
    }
    STATUS      current
    DESCRIPTION
        "The group of objects supporting Sync-if-timing features obsoleted in
         20.0 release on Nokia SROS series systems."
    ::= { tmnxChassisV20Groups 7 }

tmnxSyncIfTimingGnssV20v0Group   OBJECT-GROUP
    OBJECTS     {
        tSyncIfTimingAdmGnssCfgQltyLevel,
        tSyncIfTimingAdmGnssAdminStatus,
        tmnxSyncIfTimingGnssAdminStatus,
        tmnxSyncIfTimingGnssInUse,
        tmnxSyncIfTimingGnssQualified,
        tmnxSyncIfTimingGnssAlarm,
        tmnxSyncIfTimingGnssCfgQltyLevel,
        tmnxSyncIfTimingGnssRxQltyLevel,
        tmnxSyncIfTimingGnssState,
        tmnxSyncIfTimingGnss2AdminStatus,
        tmnxSyncIfTimingGnss2InUse,
        tmnxSyncIfTimingGnss2Qualified,
        tmnxSyncIfTimingGnss2Alarm,
        tmnxSyncIfTimingGnss2RxQltyLevel,
        tmnxSyncIfTimingGnss2State
    }
    STATUS      current
    DESCRIPTION
        "The group on objects supporting the GNSS (Global Navigation Satellite
         System) timing reference in 20.0 on Nokia SROS series systems."
    ::= { tmnxChassisV20Groups 8 }

tmnxChassisResEgrRmrkV20v0Group  OBJECT-GROUP
    OBJECTS     {
        tFPResEgrDot1pDscpRemarkMapTotal,
        tFPResEgrDot1pDscpRemarkMapAlloc
    }
    STATUS      current
    DESCRIPTION
        "The group of objects supporting management of Resource Information
         related to Egress remark policy. This is for release 20.0 of Nokia IXR
         systems."
    ::= { tmnxChassisV20Groups 9 }

tmnxChassisDot1xHostV20v0Group   OBJECT-GROUP
    OBJECTS     {
        tFPResDot1xHostTotal,
        tFPResDot1xHostAlloc
    }
    STATUS      current
    DESCRIPTION
        "The group of objects supporting management of Resource Information
         related to dot1X authenticated hosts. This is for release 20.10 of
         Nokia SROS series systems."
    ::= { tmnxChassisV20Groups 10 }

tmnxChassisResDepthMQV20v0Group  OBJECT-GROUP
    OBJECTS     {
        tChassisResFastDepthMQueuesTotal,
        tChassisResFastDepthMQueuesAlloc,
        tFPResFastDepthMQueuesTotal,
        tFPResFastDepthMQueuesAlloc
    }
    STATUS      current
    DESCRIPTION
        "The group of objects supporting management of Resource Information
         related to fast polled queue depth monitored queue. This is for
         release 20.10 of Nokia SROS series systems."
    ::= { tmnxChassisV20Groups 11 }

tmnxChassisFPQppbPolV20v0Group   OBJECT-GROUP
    OBJECTS     {
        tmnxFPPlcyAcctPolicerLimit,
        tmnxFPPlcyAcctPolicerInUse
    }
    STATUS      current
    DESCRIPTION
        "The group of objects supporting management of FP policy-accounting
         resources on forwarding plane. This is for release 20.10 of Nokia SROS
         series systems."
    ::= { tmnxChassisV20Groups 12 }

tmnxChassisCoreResV20v0Group     OBJECT-GROUP
    OBJECTS     {
        tCoreResSapTotal,
        tCoreResSapAlloc
    }
    STATUS      current
    DESCRIPTION
        "The group of objects supporting management of Resource Information on
         a core. This is for release 20.10 of Nokia IXR systems."
    ::= { tmnxChassisV20Groups 14 }

tmnxFPNotificationV20Group       NOTIFICATION-GROUP
    NOTIFICATIONS {
        tmnxPlcyAcctPlcrPoolExcResource,
        tmnxPlcyAcctPlcrPoolLowResource
    }
    STATUS      current
    DESCRIPTION
        "The group of notifications for FP on Nokia systems."
    ::= { tmnxChassisV20Groups 15 }

tmnxChassisIxrXFanV20v0Group     OBJECT-GROUP
    OBJECTS     {
        tmnxPhysChassisFanDirection
    }
    STATUS      current
    DESCRIPTION
        "The group of objects supporting management of IXR-x chassis fans in
         release 20.10 of Nokia IXR systems."
    ::= { tmnxChassisV20Groups 16 }

tmnxChassisV21Groups             OBJECT IDENTIFIER ::= { tmnxChassisGroups 83 }

tmnxIpsecV21Group                OBJECT-GROUP
    OBJECTS     {
        tmnxIPsecIsaMemberPoolName,
        tmnxIPsecIsaMemberPoolRowStatus,
        tmnxIPsecIsaMemberPoolLastChgd,
        tmnxIPsecIsaMemberPoolDesc,
        tmnxIPsecIsaMemberPoolTblLstChgd,
        tmnxMDAIsaMemberPoolAssoc,
        tmnxMDAIsaTunnelActiveInGrp,
        tmnxTunnelGrpEsaVmPoolAssoc,
        tmnxTunnelGrpEsaVmActiveInGrp,
        tmnxIPsecIsaGrpMemberPool
    }
    STATUS      current
    DESCRIPTION
        "The group of objects for N:M multi-chassis support on Nokia systems."
    ::= { tmnxChassisV21Groups 1 }

tmnxMdaXConnectGroupV21          OBJECT-GROUP
    OBJECTS     {
        tmnxMdaXConMacTableLastChanged,
        tmnxMdaXConMacRowStatus,
        tmnxMdaXConMacLastChanged,
        tmnxMdaXConMacDescription,
        tmnxMdaXConLpbkTableLastChanged,
        tmnxMdaXConLpbkRowStatus,
        tmnxMdaXConLpbkLastChanged,
        tmnxMdaXConLpbkDescription,
        tmnxMdaXConLpbkBandwidth
    }
    STATUS      current
    DESCRIPTION
        "The group of objects supporting management of MDA Cross-Connect
         capabilities in release 21.0 on Nokia SROS series systems."
    ::= { tmnxChassisV21Groups 2 }

tmnxCoreDdctdPolicerResGroupV21  OBJECT-GROUP
    OBJECTS     {
        tCoreDdctdPolicersTotal,
        tCoreDdctdPolicersAlloc
    }
    STATUS      current
    DESCRIPTION
        "The group of objects supporting management of entries for
         direct-mapped policer resource information on a core capabilities in
         release 21.0 on Nokia SROS series systems."
    ::= { tmnxChassisV21Groups 3 }

tmnxFPToFPStatGroupV21           OBJECT-GROUP
    OBJECTS     {
        tmnxBestEffortFptoFpPkts,
        tmnxBestEffortFptoFpOcts,
        tmnxExpeditedFptoFpPkts,
        tmnxExpeditedFptoFpOcts
    }
    STATUS      current
    DESCRIPTION
        "The group of objects supporting the packet and octet counters for
         unicast traffic sent by source to destination forwarding engine in
         release 21.0 on Nokia SROS series systems."
    ::= { tmnxChassisV21Groups 4 }

tmnxCcagObsoleteGroupV21         OBJECT-GROUP
    OBJECTS     {
        tmnxMDACcagId,
        tmnxCcagRowStatus,
        tmnxCcagDescription,
        tmnxCcagAdminStatus,
        tmnxCcagOperStatus,
        tmnxCcagCcaRate,
        tmnxCcagLastChanged,
        tmnxCcagAccessAdaptQos,
        tmnxCcagPathLastChanged,
        tmnxCcagPathRate,
        tmnxCcagPathRateOption,
        tmnxCcagPathWeight,
        tmnxCcagPathCcLastChanged,
        tmnxCcagPathCcEgrPoolResvCbs,
        tmnxCcagPathCcEgrPoolSlpPlcy,
        tmnxCcagPathCcIngPoolResvCbs,
        tmnxCcagPathCcIngPoolSlpPlcy,
        tmnxCcagPathCcAcctPolicyId,
        tmnxCcagPathCcCollectStats,
        tmnxCcagPathCcQueuePlcy,
        tmnxCcagPathCcMac,
        tmnxCcagPathCcMtu,
        tmnxCcagPathCcHwMac,
        tmnxCcagPathCcUserAssignedMac
    }
    STATUS      current
    DESCRIPTION
        "The group of objects supporting CCAG capabilities made obsolete in
         release 21.0 on Nokia SROS series systems."
    ::= { tmnxChassisV21Groups 5 }

tmnxMDAV21v0Group                OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDACapabilities,
        tmnxMDAMinChannelization,
        tmnxMDAMaxChannelization,
        tmnxMDAMaxChannels,
        tmnxMDAChannelsInUse,
        tmnxMdaTypeName,
        tmnxMdaTypeDescription,
        tmnxMdaTypeStatus,
        tmnxMDAReboot,
        tmnxMDASynchronousEthernet,
        tmnxMDAIsaTunnelGroup,
        tmnxIPsecIsaGrpIPsecRespondOnly,
        tmnxIPsecIsaGrpMultiActive,
        tmnxIPsecIsaGrpActiveMda,
        tmnxMDAIsaTunnelGroupInUse,
        tmnxMDAFailOnError,
        tmnxMDAEgrXplErrThreshold,
        tmnxMDAEgrXplErrWindow,
        tmnxMDAIngrXplErrThreshold,
        tmnxMDAIngrXplErrWindow
    }
    STATUS      current
    DESCRIPTION
        "The group of objects supporting management of MDAs for release 19.0 on
         Nokia SROS series systems."
    ::= { tmnxChassisV21Groups 6 }

tmnxChassisResourceV21v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tCardResIntArbiterOvrsTotal,
        tCardResIntArbiterOvrsAlloc,
        tCardResSLAProfileInstanceTotal,
        tCardResSLAProfileInstanceAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResDynQ2WredPoolTotal,
        tFPResDynQ2WredPoolAlloc,
        tFPResIngIPv6AclFilterTotal,
        tFPResIngIPv6AclFilterAlloc,
        tFPResEgrIPv6AclFilterTotal,
        tFPResEgrIPv6AclFilterAlloc,
        tFPResSLAProfileInstanceTotal,
        tFPResSLAProfileInstanceAlloc,
        tFPResMepsWithIntMegTotal,
        tFPResMepsWithIntMegAlloc,
        tFPResMepsWithIccMegTotal,
        tFPResMepsWithIccMegAlloc,
        tFPResMepsWithOtherMegTotal,
        tFPResMepsWithOtherMegAlloc,
        tFPResUniqueIccsForMepsTotal,
        tFPResUniqueIccsForMepsAlloc,
        tFPResPrefixesOfMepMacsTotal,
        tFPResPrefixesOfMepMacsAlloc,
        tFPResIngAclStatTotal,
        tFPResIngAclStatAlloc,
        tFPResEgrAclStatTotal,
        tFPResEgrAclStatAlloc,
        tFPResOamSathTrafGenBandwAlloc,
        tFPResOamSathTrafGenBandwTotal,
        tFPResOamSathTrafGenSvcStrmAlloc,
        tFPResOamSathTrafGenSvcStrmTotal
    }
    STATUS      obsolete
    DESCRIPTION
        "The group of objects supporting management of System Resource
         Information on release 21.0 of Nokia SROS series systems."
    ::= { tmnxChassisV21Groups 8 }

tFPResEgrHwAggShaperV21v0Group   OBJECT-GROUP
    OBJECTS     {
        tFPResEgrHwAssignNonShaperQTotal,
        tFPResEgrHwAssignNonShaperQAlloc,
        tFPResEgrHwAggShapQSetSize8Total,
        tFPResEgrHwAggShapQSetSize8Alloc,
        tFPResEgrHwAggShapersTotal,
        tFPResEgrHwAggShapersAlloc,
        tFPResEgrHwAggShaperSchedsTotal,
        tFPResEgrHwAggShaperSchedsAlloc
    }
    STATUS      current
    DESCRIPTION
        "The group of objects supporting management of FP Resource Information
         on release 21.0 of Nokia SROS series systems."
    ::= { tmnxChassisV21Groups 10 }

tmnxHwObsoleteV21v0Group         OBJECT-GROUP
    OBJECTS     {
        tmnxHwLastAlarmEvent,
        tmnxHwClearAlarms
    }
    STATUS      current
    DESCRIPTION
        "The group of objects supporting management of hardware capabilities
         that were obsoleted in release 21.0 of Nokia SROS series systems."
    ::= { tmnxChassisV21Groups 11 }

tmnxIssuObsoleteV21v0Group       OBJECT-GROUP
    OBJECTS     {
        tmnxChassisUpdateTimeLeft
    }
    STATUS      current
    DESCRIPTION
        "The group of objects supporting management of fields used by ISSU
         which have been obsoleted in release 21.0 of Nokia SROS series
         systems."
    ::= { tmnxChassisV21Groups 12 }

tCardResTLSMcastV21v0Group       OBJECT-GROUP
    OBJECTS     {
        tCardResTLSMcastEntriesAlloc,
        tCardResTLSMcastEntriesTotal
    }
    STATUS      current
    DESCRIPTION
        "The group of objects supporting management of TLS Mcast Entry resource
         usage on release 21.0 of Nokia SROS series systems."
    ::= { tmnxChassisV21Groups 13 }

tmnxChassisNotifGroupV21v0       NOTIFICATION-GROUP
    NOTIFICATIONS {
        tChassisPowerSupplyUnsup
    }
    STATUS      current
    DESCRIPTION
        "The group of additional notifications supporting chassis management in
         release 21 of Nokia SROS series systems."
    ::= { tmnxChassisV21Groups 14 }

tmnxChassisResIngClassV21v0Group OBJECT-GROUP
    OBJECTS     {
        tFPResIngClassProfileTotal,
        tFPResIngClassProfileAlloc,
        tFPResIngClassNonEpipeProfTotal,
        tFPResIngClassNonEpipeProfAlloc
    }
    STATUS      current
    DESCRIPTION
        "The group of objects supporting management of Resource Information
         related to Ingress Classification policy. This is for release 21 of
         Nokia IXR systems."
    ::= { tmnxChassisV21Groups 15 }

tmnxChassisResEgrRmrkV21v0Group  OBJECT-GROUP
    OBJECTS     {
        tFPResEgrRemarkProfileTotal,
        tFPResEgrRemarkProfileAlloc
    }
    STATUS      current
    DESCRIPTION
        "The group of objects supporting management of Resource Information
         related to Egress remark policy. This is for release 21 of Nokia IXR
         systems."
    ::= { tmnxChassisV21Groups 16 }

tmnxChassisResIngrMapsV21v0Group OBJECT-GROUP
    OBJECTS     {
        tChassisResDot1pFCMapTotal,
        tChassisResDot1pFCMapAlloc,
        tChassisResDscpFCMapTotal,
        tChassisResDscpFCMapAlloc,
        tChassisResLspExpFCMapTotal,
        tChassisResLspExpFCMapAlloc,
        tFPResDot1pFCMapIUBI,
        tFPResDscpFCMapIUBI,
        tFPResLspExpFCMapIUBI
    }
    STATUS      current
    DESCRIPTION
        "The group of objects supporting management of Resource Information
         related to Ingress classification maps. This is for release 21.7 of
         Nokia SROS series systems."
    ::= { tmnxChassisV21Groups 17 }

tmnxChassisResEgrMapsV21v0Group  OBJECT-GROUP
    OBJECTS     {
        tChassisResFCDot1pMapTotal,
        tChassisResFCDot1pMapAlloc,
        tChassisResFCDscpMapTotal,
        tChassisResFCDscpMapAlloc,
        tChassisResFCLspExpMapTotal,
        tChassisResFCLspExpMapAlloc,
        tFPResFCDot1pMapIUBE,
        tFPResFCDscpMapIUBE,
        tFPResFCLspExpMapIUBE
    }
    STATUS      current
    DESCRIPTION
        "The group of objects supporting management of Resource Information
         related to Egress remark maps. This is for release 21.7 of Nokia SROS
         series systems."
    ::= { tmnxChassisV21Groups 18 }

tmnxChassisResLagBundl1V21v0Grp  OBJECT-GROUP
    OBJECTS     {
        tChassisResPool1LagBundleIdTotal,
        tChassisResPool1LagBundleIdAlloc
    }
    STATUS      current
    DESCRIPTION
        "The group of objects supporting management of Resource Information
         related to pool 1 lag bundles. This is for release 21.7 of Nokia SROS
         series systems."
    ::= { tmnxChassisV21Groups 19 }

tmnxChassisResSysBundleV21v0Grp  OBJECT-GROUP
    OBJECTS     {
        tChassisResSystemBundleNumTotal,
        tChassisResSystemBundleNumAlloc
    }
    STATUS      current
    DESCRIPTION
        "The group of objects supporting management of Resource Information
         related to system bundles. This is for release 21.7 of Nokia SROS
         series systems."
    ::= { tmnxChassisV21Groups 20 }

tmnxChassisResLagBundl2V21v0Grp  OBJECT-GROUP
    OBJECTS     {
        tChassisResPool2LagBundleIdTotal,
        tChassisResPool2LagBundleIdAlloc
    }
    STATUS      current
    DESCRIPTION
        "The group of objects supporting management of Resource Information
         related to pool 2 lag bundles. This is for release 21.10 of Nokia SROS
         series systems."
    ::= { tmnxChassisV21Groups 21 }

tmnxIomRsrcNotifyObjsV21v0Grp    OBJECT-GROUP
    OBJECTS     {
        tmnxIomRsrcResourceType,
        tmnxIomRsrcUserType,
        tmnxIomRsrcTimeEventOccured,
        tmnxIomRsrcUsagePercent,
        tmnxIomRsrcMissingNotifCount
    }
    STATUS      obsolete
    DESCRIPTION
        "The group of objects supporting the management of IOM resources on
         release 21 of Nokia SROS series systems."
    ::= { tmnxChassisV21Groups 22 }

tmnxIomRsrcNotifyV21v0Grp        NOTIFICATION-GROUP
    NOTIFICATIONS {
        tmnxIomRsrcUsageHighLimitReached,
        tmnxIomRsrcUsageExhausted,
        tmnxIomRsrcUsageRecovered,
        tmnxIomRsrcUserOversubscribed,
        tmnxIomRsrcUserOversubscribedClr,
        tmnxIomRsrcEventOverflow,
        tmnxIomRsrcEventOverflowClr
    }
    STATUS      obsolete
    DESCRIPTION
        "The group of notifications supporting the management of IOM resources
         on release 21 of Nokia SROS series systems."
    ::= { tmnxChassisV21Groups 23 }

tmnxChassisResPerHostAutV21v0Grp OBJECT-GROUP
    OBJECTS     {
        tFPResCamBanksIUBDot1xHostAuth
    }
    STATUS      current
    DESCRIPTION
        "The group of objects supporting management of Resource Information
         related to dot1x per host authentication. This is for release 21.10 of
         Nokia SROS series systems."
    ::= { tmnxChassisV21Groups 24 }

tmnxChassisDrpCntrJ1V21v0Group   OBJECT-GROUP
    OBJECTS     {
        tCoreResIngFloatPlcrStatIUBACL
    }
    STATUS      current
    DESCRIPTION
        "The group of objects supporting management of Resource Information on
         a core. This is for release 21.10 of Nokia IXR systems."
    ::= { tmnxChassisV21Groups 25 }

tmnxChassisPwrMgmtV21v0Group     OBJECT-GROUP
    OBJECTS     {
        tmnxChassisPwrMgmtPeakPower,
        tmnxChassisPwrMgmtReservedPower,
        tmnxChassisPwrMgmtRqdRestPower,
        tmnxChassisPwrMgmtUtilRestPower,
        tmnxChassisPwrMgmtOperSafetyLvl,
        tmnxChassisPwrMgmtOperSafetyAlrt,
        tmnxChassisPwrMgmtActiveConds
    }
    STATUS      current
    DESCRIPTION
        "The group of objects supporting management of Power Management
         statistics in release 21.0 of Nokia SROS series systems."
    ::= { tmnxChassisV21Groups 26 }

tmnxChassisResMacCamBnkV21v0Grp  OBJECT-GROUP
    OBJECTS     {
        tFPResMacIPv4CamBanksTotal,
        tFPResMacIPv4CamBanksAlloc,
        tFPResIPv6CamBanksTotal,
        tFPResIPv6CamBanksAlloc
    }
    STATUS      current
    DESCRIPTION
        "The group of objects supporting management of Resource Information
         related to Cam banks. This is for release 21.10 of Nokia SROS series
         systems."
    ::= { tmnxChassisV21Groups 27 }

tmnxChassisV22v0Groups           OBJECT IDENTIFIER ::= { tmnxChassisGroups 84 }

tmnxMinFpGenerationV22v0Group    OBJECT-GROUP
    OBJECTS     {
        tmnxChassisFPGenerationFP5
    }
    STATUS      current
    DESCRIPTION
        "The group of objects added in release 22 supporting minimum Forwarding
         Plane (FP) network processor generation on Nokia SROS series systems."
    ::= { tmnxChassisV22v0Groups 1 }

tmnxHwAggShpNotifyObjsV22v0Grp   OBJECT-GROUP
    OBJECTS     {
        tmnxHwAggShpTimeEventOccured,
        tmnxHwAggShpMissingNotifCount
    }
    STATUS      current
    DESCRIPTION
        "The group of objects supporting the management of hw agg shaper traps
         on release 22 of Nokia SROS series systems."
    ::= { tmnxChassisV22v0Groups 2 }

tmnxHwAggShpNotifGroupV22v0      NOTIFICATION-GROUP
    NOTIFICATIONS {
        tmnxHwAggShpSchedEventOvrflw,
        tmnxHwAggShpSchedEventOvrflwClr
    }
    STATUS      current
    DESCRIPTION
        "The group of additional notifications supporting chassis management in
         release 22 of Nokia SROS series systems."
    ::= { tmnxChassisV22v0Groups 3 }

tmnxEsa400gGroupV22v0            OBJECT-GROUP
    OBJECTS     {
        tmnxEsaCellTopoSocket,
        tmnxEsaCellTopoCoresAvailable,
        tmnxEsaCellTopoCoresAllocated,
        tmnxEsaCellTopoMemoryAvailable,
        tmnxEsaCellTopoMemoryAllocated,
        tmnxEsaHostPortSocketId,
        tmnxEsaHostPortNicIfName
    }
    STATUS      current
    DESCRIPTION
        "The group of additional objects for ESA 400g support in release 22.x
         on Nokia systems."
    ::= { tmnxChassisV22v0Groups 4 }

tmnxEsaHwStatusMonGroupV22v0     OBJECT-GROUP
    OBJECTS     {
        tmnxEsaStatsHardwareStatus,
        tmnxEsaStatsPowerSupply1Status,
        tmnxEsaStatsPowerSupply2Status,
        tmnxEsaStatsPowerSupply1Temp,
        tmnxEsaStatsPowerSupply2Temp,
        tmnxEsaStatsFanRedundancy,
        tmnxEsaStatsFanStatus,
        tmnxEsaStatsPwrSupMismatchStatus,
        tmnxEsaStatsPwrSupRedundancy,
        tmnxEsaStatsTemperatureStatus,
        tmnxEsaStatsCpu1Temperature,
        tmnxEsaStatsCpu2Temperature
    }
    STATUS      current
    DESCRIPTION
        "The group of objects for ESA HW status monitor in release 22.x on
         Nokia systems."
    ::= { tmnxChassisV22v0Groups 5 }

tmnxChassisGnssGroupV22v0        OBJECT-GROUP
    OBJECTS     {
        tmnxGnssSyncSysTime
    }
    STATUS      current
    DESCRIPTION
        "The group of objects supporting the GNSS receiver management in
         release 22 on Nokia SROS series systems."
    ::= { tmnxChassisV22v0Groups 6 }

tmnxChassisResPortFwdIdGrpV22v0  OBJECT-GROUP
    OBJECTS     {
        tFPResPortForwardingIdTotal,
        tFPResPortForwardingIdAlloc,
        tMDAResPortForwardingIdTotal,
        tMDAResPortForwardingIdAlloc,
        tFPResIngIPv4AclEntryIUBAcl,
        tFPResIngIPv4AclEntryIUBDcpu
    }
    STATUS      current
    DESCRIPTION
        "The group of objects supporting internal port forwarding IDs resources
         used by satellite and virtual ports in release 22.x on Nokia systems."
    ::= { tmnxChassisV22v0Groups 7 }

tmnxChassisResShardPlcrGrpV22v0  OBJECT-GROUP
    OBJECTS     {
        tCoreResSharedPolicerAlloc,
        tCoreResSharedPolicerTotal
    }
    STATUS      current
    DESCRIPTION
        "The group of objects supporting shared policers in release 22.x on
         Nokia systems."
    ::= { tmnxChassisV22v0Groups 8 }

tmnxFPCoreResUsgStatsGroupV22v0  OBJECT-GROUP
    OBJECTS     {
        tmnxFPCoreFreeDramBdb,
        tmnxFPCoreMinFreeDramBdb,
        tmnxFPCoreLowFreeDramBdb,
        tmnxFPCoreTotalDramBdb,
        tmnxFPCoreFreeSramBuf,
        tmnxFPCoreMinFreeSramBuf,
        tmnxFPCoreLowFreeSramBuf,
        tmnxFPCoreTotalSramBuf,
        tmnxFPCoreFreeSramPdb,
        tmnxFPCoreMinFreeSramPdb,
        tmnxFPCoreLowFreeSramPdb,
        tmnxFPCoreTotalSramPdb,
        tmnxFPCoreDramBwMaxCnscPollBlk,
        tmnxFPCoreDramBwPktRejLastPoll,
        tmnxFPCoreDramBwTotalPktRejects,
        tmnxFPCorePcsPipeNifPrdDrpLstPol,
        tmnxFPCorePcsPipeTotNifPrdDrops,
        tmnxFPCorePcsPipeMxCnvPlNifPrdDp,
        tmnxFPCoreMeshFabBwAsrtCngstFP1,
        tmnxFPCoreMeshFabBwAsrtCngstFP2,
        tmnxFPCoreMeshFabBwAsrtCngstFP3
    }
    STATUS      current
    DESCRIPTION
        "The group of objects supporting FP core resource usage stats in
         release 22.x on Nokia SROS series systems."
    ::= { tmnxChassisV22v0Groups 9 }

tmnxHwTempGroupV22v0             OBJECT-GROUP
    OBJECTS     {
        tmnxHwOverTempStatus
    }
    STATUS      current
    DESCRIPTION
        "The group of objects supporting hardware temperature objects in
         release 22.x on Nokia SROS series systems."
    ::= { tmnxChassisV22v0Groups 10 }

tmnxCamOverloadGroupV22v0        OBJECT-GROUP
    OBJECTS     {
        tFPResIngIPv4MacCamOverLoad,
        tFPResIngIPv6CamOverLoad,
        tFPResEgrIPv4MacCamOverLoad,
        tFPResEgrIPv6CamOverLoad
    }
    STATUS      current
    DESCRIPTION
        "The group of objects supporting CAM overloading state in release 22.x
         on Nokia SROS series systems."
    ::= { tmnxChassisV22v0Groups 11 }

tmnxSyncIfTimingGroupV22v0       OBJECT-GROUP
    OBJECTS     {
        tSyncIfTimingAdmRefOrder6,
        tmnxSyncIfTimingRefOrder6
    }
    STATUS      current
    DESCRIPTION
        "The group of objects supporting the GNSS receiver management timing
         reference in release 22 on Nokia SROS series systems."
    ::= { tmnxChassisV22v0Groups 12 }

tChassisResShardPlcrStatGrpV22v0 OBJECT-GROUP
    OBJECTS     {
        tCoreResIngFloatPlcrStatIUBSP
    }
    STATUS      current
    DESCRIPTION
        "The group of objects supporting shared policers stats in release 22.x
         on Nokia systems."
    ::= { tmnxChassisV22v0Groups 13 }

tmnxIomRsrcNotifyObjsV22v0Grp    OBJECT-GROUP
    OBJECTS     {
        tmnxIomRsrcOwnerType
    }
    STATUS      current
    DESCRIPTION
        "The group of objects supporting the management of IOM resources on
         release 22 of Nokia SROS series systems."
    ::= { tmnxChassisV22v0Groups 15 }

tmnxIomRsrcNotifyV22v0Grp        NOTIFICATION-GROUP
    NOTIFICATIONS {
        tmnxIomRsrcOwnerOversubscribed,
        tmnxIomRsrcOwnerOversubscrbdClr
    }
    STATUS      current
    DESCRIPTION
        "The group of notifications supporting the management of IOM resources
         on release 22 of Nokia SROS series systems."
    ::= { tmnxChassisV22v0Groups 16 }

tmnxIsaGrpESPSeqNumGroupV22v0    OBJECT-GROUP
    OBJECTS     {
        tmnxIPsecIsaGrpESPSeqNumOrder
    }
    STATUS      current
    DESCRIPTION
        "The group of objects supporting the management of strict ESP Sequence
         number ordering on release 22 of Nokia SROS series systems."
    ::= { tmnxChassisV22v0Groups 17 }

tFPResOversubGroupV22v0          OBJECT-GROUP
    OBJECTS     {
        tFPResOversub,
        tmnxFPResOversubDetected
    }
    STATUS      current
    DESCRIPTION
        "The group of objects supporting the management of FP resource
         oversubscription capabilities on release 22 of Nokia SROS series
         systems."
    ::= { tmnxChassisV22v0Groups 18 }

tmnxFPResOversubNotifGroupV22v0  NOTIFICATION-GROUP
    NOTIFICATIONS {
        tmnxFPResOversubscribed,
        tmnxFPResOversubscribedCleared
    }
    STATUS      current
    DESCRIPTION
        "The group of notifications supporting the management of FP resource
         oversubscription capabilities on release 22 of Nokia SROS series
         systems."
    ::= { tmnxChassisV22v0Groups 19 }

tmnxEsaHwStatusMonNotifGrpV22v0  NOTIFICATION-GROUP
    NOTIFICATIONS {
        tmnxEsaHwStatusDegraded,
        tmnxEsaHwStatusDegradedClr,
        tmnxEsaHwStatusCritical,
        tmnxEsaHwStatusCriticalClr,
        tmnxEsaHwPwrSup1Degraded,
        tmnxEsaHwPwrSup1DegradedClr,
        tmnxEsaHwPwrSup1Failed,
        tmnxEsaHwPwrSup1FailedClr,
        tmnxEsaHwPwrSup2Degraded,
        tmnxEsaHwPwrSup2DegradedClr,
        tmnxEsaHwPwrSup2Failed,
        tmnxEsaHwPwrSup2FailedClr,
        tmnxEsaHwFanBankNonRedun,
        tmnxEsaHwFanBankNonRedunClr,
        tmnxEsaHwFanBankFailRedun,
        tmnxEsaHwFanBankFailRedunClr,
        tmnxEsaHwFanStatusDegraded,
        tmnxEsaHwFanStatusDegradedClr,
        tmnxEsaHwFanStatusFailed,
        tmnxEsaHwFanStatusFailedClr,
        tmnxEsaHwPwrSupMismatch,
        tmnxEsaHwPwrSupMismatchClr,
        tmnxEsaHwPwrSupBankNonRedun,
        tmnxEsaHwPwrSupBankNonRedunClr,
        tmnxEsaHwPwrSupBankFailRedun,
        tmnxEsaHwPwrSupBankFailRedunClr,
        tmnxEsaHwTemperatureDegraded,
        tmnxEsaHwTemperatureDegradedClr,
        tmnxEsaHwTemperatureFailed,
        tmnxEsaHwTemperatureFailedClr
    }
    STATUS      current
    DESCRIPTION
        "The group of notifications supporting the management of ESA hardware
         monitoring capabilities on release 22 of Nokia SROS series systems."
    ::= { tmnxChassisV22v0Groups 20 }

tFPResEgrHwAggShaperV22v0Group   OBJECT-GROUP
    OBJECTS     {
        tFPResEgrHwAggShapQSetSizeTotal,
        tFPResEgrHwAggShapQSetSizeAlloc,
        tFPResEgrHwAggShpDefSapQSetSz,
        tFPResEgrHwAggShpDefSubQSetSz,
        tFPResEgrHwAggShpDefQGrpQSetSz
    }
    STATUS      obsolete
    DESCRIPTION
        "The group of objects supporting management of FP Resource Information
         on release 22.0 of Nokia SROS series systems."
    ::= { tmnxChassisV22v0Groups 21 }

tmnxIsaGrpESPSeqNumGroupV23v0    OBJECT-GROUP
    OBJECTS     {
        tmnxIPsecIsaGrpESPSeqNumOrderOpr
    }
    STATUS      current
    DESCRIPTION
        "The group of objects supporting the management of strict ESP Sequence
         number ordering on release 23 of Nokia SROS series systems."
    ::= { tmnxChassisV22v0Groups 22 }

tmnxIsaMemberPoolV23v0Group      OBJECT-GROUP
    OBJECTS     {
        tmnxIPsecIsaMemberPoolHighAvail
    }
    STATUS      current
    DESCRIPTION
        "The group of objects supporting ISA tunnel member pools on release
         23.0 of Nokia SROS series systems."
    ::= { tmnxChassisV22v0Groups 23 }

tmnxEsaStallNotifV22v0Grp        NOTIFICATION-GROUP
    NOTIFICATIONS {
        tmnxEsaStolenTimeDetected
    }
    STATUS      current
    DESCRIPTION
        "The group of notifications for ESA stall events in release 22.x of
         Nokia systems."
    ::= { tmnxChassisV22v0Groups 24 }

tmnxChassisV23v0Groups           OBJECT IDENTIFIER ::= { tmnxChassisGroups 85 }

tmnxXiomGroupV23v0               OBJECT-GROUP
    OBJECTS     {
        tmnxXiomSupportedTypes
    }
    STATUS      current
    DESCRIPTION
        "The group of additional objects supporting management of XIOM
         capabilities in release 23 on Nokia SROS series systems."
    ::= { tmnxChassisV23v0Groups 1 }

tmnxCoreDdctdPolicerResGroupV23  OBJECT-GROUP
    OBJECTS     {
        tCoreDdctdPolicerStatsTotal,
        tCoreDdctdPolicerStatsAlloc
    }
    STATUS      current
    DESCRIPTION
        "The group of objects supporting management of entries for
         direct-mapped policer resource information on a core capabilities in
         release 23.0 on Nokia SROS series systems."
    ::= { tmnxChassisV23v0Groups 2 }

tmnxChassisRebootReqdGroupV23v0  OBJECT-GROUP
    OBJECTS     {
        tmnxChassisRebootReqd,
        tmnxChassisRebootReqdReason
    }
    STATUS      current
    DESCRIPTION
        "The group of objects introduced to support reboot requirement start in
         in SROS release 23.3."
    ::= { tmnxChassisV23v0Groups 3 }

tmnxChassisAtmObsoleteGroupV23v0 OBJECT-GROUP
    OBJECTS     {
        tmnxMDAAtmMode
    }
    STATUS      current
    DESCRIPTION
        "The group of obsoleted objects on Nokia 7xx0 SR series systems for ATM
         management."
    ::= { tmnxChassisV23v0Groups 4 }

tmnxChassisIxrResourceGroup      OBJECT-GROUP
    OBJECTS     {
        tChassisIxrResCommonLifTotal,
        tChassisIxrResCommonLifAlloc,
        tChassisIxrResCommonLifFree,
        tChassisIxrResArpLifTotal,
        tChassisIxrResArpLifAlloc,
        tChassisIxrResArpLifFree,
        tChassisIxrResMplsLifTotal,
        tChassisIxrResMplsLifAlloc,
        tChassisIxrResMplsLifFree,
        tChassisIxrResL3VsiRifTotal,
        tChassisIxrResL3VsiRifAlloc,
        tChassisIxrResL3VsiRifFree,
        tChassisIxrResFecUnpairedTotal,
        tChassisIxrResFecUnpairedAlloc,
        tChassisIxrResFecUnpairedFree,
        tChassisIxrResFecPairedTotal,
        tChassisIxrResFecPairedAlloc,
        tChassisIxrResFecPairedFree,
        tChassisIxrResOamLmCtrTotal,
        tChassisIxrResOamLmCtrAlloc,
        tChassisIxrResOamLmCtrFree,
        tChassisIxrResOwnCommonLifTotal,
        tChassisIxrResOwnCommonLifAlloc,
        tChassisIxrResOwnCommonLifFree,
        tChassisIxrResOwnArpLifAlloc,
        tChassisIxrResOwnMplsLifAlloc,
        tChassisIxrResOwnL3VsiRifAlloc,
        tChassisIxrResOwnFecUnpairAlloc,
        tChassisIxrResOwnFecPairedAlloc,
        tChassisIxrResOwnOamLmCtrAlloc,
        tCardIxrResMplsEcmpGroupsTotal,
        tCardIxrResMplsEcmpGroupsAlloc,
        tCardIxrResMplsEcmpGroupsFree,
        tCardIxrResIpEcmpGroupsTotal,
        tCardIxrResIpEcmpGroupsAlloc,
        tCardIxrResIpEcmpGroupsFree,
        tCardIxrResFecBanksTotal,
        tCardIxrResFecBanksAlloc,
        tCardIxrResFecBanksFree,
        tCardIxrResFecLevel1BanksAlloc,
        tCardIxrResFecLevel2BanksAlloc,
        tCardIxrResFecsTotal,
        tCardIxrResFecsAlloc,
        tCardIxrResFecsFree,
        tCardIxrResFecLevel1Total,
        tCardIxrResFecLevel1Alloc,
        tCardIxrResFecLevel1Free,
        tCardIxrResFecLevel2Total,
        tCardIxrResFecLevel2Alloc,
        tCardIxrResFecLevel2Free,
        tCardIxrResOwnFecLevel1Alloc,
        tCardIxrResOwnFecLevel2Alloc,
        tFpIxrResEgrGlobalLifMapTotal,
        tFpIxrResEgrGlobalLifMapAlloc,
        tFpIxrResEgrGlobalLifMapFree,
        tFpIxrResIngTerminationATotal,
        tFpIxrResIngTerminationAAlloc,
        tFpIxrResIngTerminationAFree,
        tFpIxrResIngTerminationBTotal,
        tFpIxrResIngTerminationBAlloc,
        tFpIxrResIngTerminationBFree,
        tFpIxrResIngEndpoint1Total,
        tFpIxrResIngEndpoint1Alloc,
        tFpIxrResIngEndpoint1Free,
        tFpIxrResIngEndpoint2Total,
        tFpIxrResIngEndpoint2Alloc,
        tFpIxrResIngEndpoint2Free,
        tFpIxrResIngEndpoint3Total,
        tFpIxrResIngEndpoint3Alloc,
        tFpIxrResIngEndpoint3Free,
        tFpIxrResEgrEncapEntriesTotal,
        tFpIxrResEgrEncapEntriesAlloc,
        tFpIxrResEgrEncapEntriesFree,
        tFpIxrResEgrEncapBanksTotal,
        tFpIxrResEgrEncapBanksAlloc,
        tFpIxrResEgrEncapBanksFree,
        tFpIxrResEgrRoutedTotal,
        tFpIxrResEgrRoutedAlloc,
        tFpIxrResEgrRoutedFree,
        tFpIxrResEgrRoutedBanks,
        tFpIxrResEgrTdmTotal,
        tFpIxrResEgrTdmAlloc,
        tFpIxrResEgrTdmFree,
        tFpIxrResEgrTdmBanks,
        tFpIxrResEgrPortVlanXlatTotal,
        tFpIxrResEgrPortVlanXlatAlloc,
        tFpIxrResEgrPortVlanXlatFree,
        tFpIxrResEgrPortVlanXlatBanks,
        tFpIxrResEgrArpTotal,
        tFpIxrResEgrArpAlloc,
        tFpIxrResEgrArpFree,
        tFpIxrResEgrArpBanks,
        tFpIxrResEgrLabelPushTotal,
        tFpIxrResEgrLabelPushAlloc,
        tFpIxrResEgrLabelPushFree,
        tFpIxrResEgrLabelPushBanks,
        tFpIxrResEgrLabelSwapPushTotal,
        tFpIxrResEgrLabelSwapPushAlloc,
        tFpIxrResEgrLabelSwapPushFree,
        tFpIxrResEgrLabelSwapPushBanks,
        tFpIxrResEgrPortVlanXltExtTotal,
        tFpIxrResEgrPortVlanXltExtAlloc,
        tFpIxrResEgrPortVlanXltExtFree,
        tFpIxrResEgrPortVlanXltExtBanks,
        tFpIxrResEgrArpExtTotal,
        tFpIxrResEgrArpExtAlloc,
        tFpIxrResEgrArpExtFree,
        tFpIxrResEgrArpExtBanks,
        tFpIxrResEgrLabelPushExtTotal,
        tFpIxrResEgrLabelPushExtAlloc,
        tFpIxrResEgrLabelPushExtFree,
        tFpIxrResEgrLabelPushExtBanks,
        tFpIxrResEgrLabelSwapPshExTotal,
        tFpIxrResEgrLabelSwapPshExAlloc,
        tFpIxrResEgrLabelSwapPshExFree,
        tFpIxrResEgrLabelSwapPshExBanks,
        tFpIxrResEgrEncapExtEntriesTotal,
        tFpIxrResEgrEncapExtEntriesAlloc,
        tFpIxrResEgrEncapExtEntriesFree,
        tFpIxrResEgrEncapExtBanksTotal,
        tFpIxrResEgrEncapExtBanksAlloc,
        tFpIxrResEgrEncapExtBanksFree,
        tFpIxrResEgrExPortVlanXlatTotal,
        tFpIxrResEgrExPortVlanXlatAlloc,
        tFpIxrResEgrExPortVlanXlatFree,
        tFpIxrResEgrExPortVlanXlatBanks,
        tFpIxrResEgrExArpTotal,
        tFpIxrResEgrExArpAlloc,
        tFpIxrResEgrExArpFree,
        tFpIxrResEgrExArpBanks,
        tFpIxrResEgrExLabelPushTotal,
        tFpIxrResEgrExLabelPushAlloc,
        tFpIxrResEgrExLabelPushFree,
        tFpIxrResEgrExLabelPushBanks,
        tFpIxrResEgrExLabelSwapPshTotal,
        tFpIxrResEgrExLabelSwapPshAlloc,
        tFpIxrResEgrExLabelSwapPshFree,
        tFpIxrResEgrExLabelSwapPshBanks
    }
    STATUS      obsolete
    DESCRIPTION
        "The group of objects supporting IXR resource index  on Nokia SROS
         series systems"
    ::= { tmnxChassisV23v0Groups 5 }

tmnxIomRsrcObjObsoleteGrpV23v0   OBJECT-GROUP
    OBJECTS     {
        tmnxIomRsrcUserType
    }
    STATUS      current
    DESCRIPTION
        "The group of obsoleted objects supporting management of IOM resources
         in release 23 on Nokia SROS series systems."
    ::= { tmnxChassisV23v0Groups 6 }

tmnxIomRsrcNotifyObjsV23v0Grp    OBJECT-GROUP
    OBJECTS     {
        tmnxIomRsrcResourceType,
        tmnxIomRsrcTimeEventOccured,
        tmnxIomRsrcUsagePercent,
        tmnxIomRsrcMissingNotifCount
    }
    STATUS      current
    DESCRIPTION
        "The group of objects supporting the management of IOM resources on
         release 21 of Nokia SROS series systems."
    ::= { tmnxChassisV23v0Groups 7 }

tmnxIomRsrcNotifyV23v0Grp        NOTIFICATION-GROUP
    NOTIFICATIONS {
        tmnxIomRsrcUsageHighLimitReached,
        tmnxIomRsrcUsageExhausted,
        tmnxIomRsrcUsageRecovered,
        tmnxIomRsrcEventOverflow,
        tmnxIomRsrcEventOverflowClr
    }
    STATUS      current
    DESCRIPTION
        "The group of notifications supporting the management of IOM resources
         on release 21 of Nokia SROS series systems."
    ::= { tmnxChassisV23v0Groups 8 }

tmnxSapResourceUsageV23v0Group   OBJECT-GROUP
    OBJECTS     {
        tChassisResCpipeSapTotal,
        tChassisResCpipeSapAlloc,
        tChassisResEpipeSapTotal,
        tChassisResEpipeSapAlloc,
        tChassisResIpipeSapTotal,
        tChassisResIpipeSapAlloc,
        tChassisResIesSapTotal,
        tChassisResIesSapAlloc,
        tChassisResMirrorSapTotal,
        tChassisResMirrorSapAlloc,
        tChassisResVplsSapTotal,
        tChassisResVplsSapAlloc,
        tChassisResVprnSapTotal,
        tChassisResVprnSapAlloc,
        tCardResApipeSapInstanceTotal,
        tCardResApipeSapInstanceAlloc,
        tCardResCpipeSapInstanceTotal,
        tCardResCpipeSapInstanceAlloc,
        tCardResEpipeSapInstanceTotal,
        tCardResEpipeSapInstanceAlloc,
        tCardResFpipeSapInstanceTotal,
        tCardResFpipeSapInstanceAlloc,
        tCardResIpipeSapInstanceTotal,
        tCardResIpipeSapInstanceAlloc,
        tCardResIesSapInstanceTotal,
        tCardResIesSapInstanceAlloc,
        tCardResMirrorSapInstanceTotal,
        tCardResMirrorSapInstanceAlloc,
        tCardResVplsSapInstanceTotal,
        tCardResVplsSapInstanceAlloc,
        tCardResVprnSapInstanceTotal,
        tCardResVprnSapInstanceAlloc
    }
    STATUS      current
    DESCRIPTION
        "The group of objects supporting management of Saps that were added in
         the release 19R10 of the Nokia SROS series systems."
    ::= { tmnxChassisV23v0Groups 9 }

tmnxSapResUsageObsoletedGroup    OBJECT-GROUP
    OBJECTS     {
        tChassisResApipeSapTotal,
        tChassisResApipeSapAlloc,
        tChassisResFpipeSapTotal,
        tChassisResFpipeSapAlloc
    }
    STATUS      current
    DESCRIPTION
        "The group of objects supporting management of Saps that were added in
         the release 19R10 and are obsoleted in release 23R of the Nokia SROS
         series systems."
    ::= { tmnxChassisV23v0Groups 10 }

tmnxFPCoreResUsgStatsGroupV23v0  OBJECT-GROUP
    OBJECTS     {
        tmnxFPCoreL0PolicerProfilesInUse,
        tmnxFPCoreL1PolicerProfilesInUse
    }
    STATUS      current
    DESCRIPTION
        "The group of objects supporting FP core resource usage stats in
         release 23.x on Nokia SROS series systems."
    ::= { tmnxChassisV23v0Groups 11 }

tmnxEsa100g2GroupV23v0           OBJECT-GROUP
    OBJECTS     {
        tmnxEsaStatsSystemPartNumber
    }
    STATUS      current
    DESCRIPTION
        "The group of objects for ESA 100G-2 in release 23.x on Nokia SROS
         series systems."
    ::= { tmnxChassisV23v0Groups 12 }

tmnxChassisResIOCapacityV23v0Grp OBJECT-GROUP
    OBJECTS     {
        tChassisResIOCapacityTotal,
        tChassisResIOCapacityAlloc
    }
    STATUS      current
    DESCRIPTION
        "The group of objects supporting management of Resource Information
         related to faceplate IO capacity."
    ::= { tmnxChassisV23v0Groups 13 }

tFPResSharedPolicersV23v0Group   OBJECT-GROUP
    OBJECTS     {
        tFPResCamBanksIUBSharedPlcrs,
        tFPResSharedPlcrCamBanksTotal,
        tFPResSharedPlcrCamBanksAlloc,
        tFPResSharedPlcrCamEntryTotal,
        tFPResSharedPlcrCamEntryAlloc
    }
    STATUS      current
    DESCRIPTION
        "The group of objects supporting management of FP Resource Information
         on release 23.0 of Nokia SROS series systems."
    ::= { tmnxChassisV23v0Groups 14 }

tmnxChassisResourceV23v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tCardResIntArbiterOvrsTotal,
        tCardResIntArbiterOvrsAlloc,
        tCardResSLAProfileInstanceTotal,
        tCardResSLAProfileInstanceAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResDynQ2WredPoolTotal,
        tFPResDynQ2WredPoolAlloc,
        tFPResIngIPv6AclFilterTotal,
        tFPResIngIPv6AclFilterAlloc,
        tFPResEgrIPv6AclFilterTotal,
        tFPResEgrIPv6AclFilterAlloc,
        tFPResSLAProfileInstanceTotal,
        tFPResSLAProfileInstanceAlloc,
        tFPResMepsWithIntMegTotal,
        tFPResMepsWithIntMegAlloc,
        tFPResMepsWithIccMegTotal,
        tFPResMepsWithIccMegAlloc,
        tFPResMepsWithOtherMegTotal,
        tFPResMepsWithOtherMegAlloc,
        tFPResUniqueIccsForMepsTotal,
        tFPResUniqueIccsForMepsAlloc,
        tFPResPrefixesOfMepMacsTotal,
        tFPResPrefixesOfMepMacsAlloc,
        tFPResIngAclStatTotal,
        tFPResIngAclStatAlloc,
        tFPResEgrAclStatTotal,
        tFPResEgrAclStatAlloc,
        tFPResOamSathTrafGenBandwAlloc,
        tFPResOamSathTrafGenBandwTotal,
        tFPResOamSathTrafGenSvcStrmAlloc,
        tFPResOamSathTrafGenSvcStrmTotal
    }
    STATUS      current
    DESCRIPTION
        "The group of objects supporting management of System Resource
         Information on release 23.0 of Nokia SROS series systems."
    ::= { tmnxChassisV23v0Groups 15 }

tmnxChassisResObsoletedGroup     OBJECT-GROUP
    OBJECTS     {
        tFPResIngAclQosEntryTotal,
        tFPResIngAclQosEntryAlloc,
        tFPResEgrAclQosEntryTotal,
        tFPResEgrAclQosEntryAlloc
    }
    STATUS      current
    DESCRIPTION
        "The group of objects supporting management of System system resource
         information that are obsoleted in release 23R of the Nokia SROS series
         systems."
    ::= { tmnxChassisV23v0Groups 16 }

tmnxChassisPwrMgmtV23v0Group     OBJECT-GROUP
    OBJECTS     {
        tmnxPhysChassPSFanOperStatus
    }
    STATUS      current
    DESCRIPTION
        "The group of objects supporting management of Power Management
         statistics in release 23.0 of Nokia SROS series systems."
    ::= { tmnxChassisV23v0Groups 17 }

tmnxChassisPwrMgmtNotifsV23v0Grp NOTIFICATION-GROUP
    NOTIFICATIONS {
        tmnxPowerSupplyFanFailed,
        tmnxPowerSupplyFanFailedClear
    }
    STATUS      current
    DESCRIPTION
        "The group of objects supporting management of Power Management
         notifications in release 23.0 of Nokia SROS series systems."
    ::= { tmnxChassisV23v0Groups 18 }

tmnxIxrRsrcNotifyObjsGroup       OBJECT-GROUP
    OBJECTS     {
        tmnxNotifIxrResourceOwner,
        tmnxNotifIxrResource,
        tmnxNotifIxrRsrcUtilPercentage
    }
    STATUS      current
    DESCRIPTION
        "The group of objects supporting the IXR resource notifications on
         Nokia SROS series systems."
    ::= { tmnxChassisV23v0Groups 19 }

tmnxIxrRsrcNotifsGroup           NOTIFICATION-GROUP
    NOTIFICATIONS {
        tmnxIxrResourceHighUsage,
        tmnxIxrResourceHighUsageByOwner,
        tmnxIxrResourceExhausted,
        tmnxIxrResourceExhaustedByOwner,
        tmnxIxrResourceRecovered,
        tmnxIxrResourceRecoveredByOwner
    }
    STATUS      current
    DESCRIPTION
        "The group of notification objects supporting the IXR resource on Nokia
         SROS series systems."
    ::= { tmnxChassisV23v0Groups 20 }

tnmxCardEqNotifsV23v0Grp         NOTIFICATION-GROUP
    NOTIFICATIONS {
        tmnxEqCardMissing,
        tmnxEqCardMissingClear
    }
    STATUS      current
    DESCRIPTION
        "The group of objects supporting card equipment notifications in
         release 23.0 of Nokia SROS series systems."
    ::= { tmnxChassisV23v0Groups 21 }

tFPResSrv6TunnelTermV23v0Group   OBJECT-GROUP
    OBJECTS     {
        tFPResCamBanksIUBSrv6TunnelTerm
    }
    STATUS      current
    DESCRIPTION
        "The group of objects supporting management of FP Resource Information
         on release 23.0 of Nokia SROS series systems."
    ::= { tmnxChassisV23v0Groups 22 }

tFPResEgrHwAggShaperV23v0Group   OBJECT-GROUP
    OBJECTS     {
        tFPResEgrHwAggShapQSetSize1Total,
        tFPResEgrHwAggShapQSetSize1Alloc,
        tFPResEgrHwAggShapQSetSize2Total,
        tFPResEgrHwAggShapQSetSize2Alloc,
        tFPResEgrHwAggShapQSetSize3Total,
        tFPResEgrHwAggShapQSetSize3Alloc,
        tFPResEgrHwAggShapQSetSize4Total,
        tFPResEgrHwAggShapQSetSize4Alloc,
        tFPResEgrHwAggShapQSetSize5Total,
        tFPResEgrHwAggShapQSetSize5Alloc,
        tFPResEgrHwAggShapQSetSize6Total,
        tFPResEgrHwAggShapQSetSize6Alloc,
        tFPResEgrHwAggShapQSetSize7Total,
        tFPResEgrHwAggShapQSetSize7Alloc
    }
    STATUS      obsolete
    DESCRIPTION
        "The group of objects supporting management of FP Resource Information
         on release 23.0 of Nokia SROS series systems."
    ::= { tmnxChassisV23v0Groups 23 }

tmnxChassisIxrResourceJ2Group    OBJECT-GROUP
    OBJECTS     {
        tChassisIxrResAcLifTotal,
        tChassisIxrResAcLifAlloc,
        tChassisIxrResAcLifFree,
        tChassisIxrResMplsNhlfeLifTotal,
        tChassisIxrResMplsNhlfeLifAlloc,
        tChassisIxrResMplsNhlfeLifFree,
        tChassisIxrResBgpLblRtLifTotal,
        tChassisIxrResBgpLblRtLifAlloc,
        tChassisIxrResBgpLblRtLifFree,
        tChassisIxrResSdpBndMplsLifTotal,
        tChassisIxrResSdpBndMplsLifAlloc,
        tChassisIxrResSdpBndMplsLifFree,
        tChassisIxrResSdpBndGreLifTotal,
        tChassisIxrResSdpBndGreLifAlloc,
        tChassisIxrResSdpBndGreLifFree,
        tChassisIxrResSsidLifTotal,
        tChassisIxrResSsidLifAlloc,
        tChassisIxrResSsidLifFree,
        tChassisIxrResSrv6TunnelLifTotal,
        tChassisIxrResSrv6TunnelLifAlloc,
        tChassisIxrResSrv6TunnelLifFree,
        tChassisIxrResL2ServiceTotal,
        tChassisIxrResL2ServiceAlloc,
        tChassisIxrResL2ServiceFree,
        tChassisIxrResStationIdTotal,
        tChassisIxrResStationIdAlloc,
        tChassisIxrResStationIdFree,
        tChassisIxrResVxlanLifTotal,
        tChassisIxrResVxlanLifAlloc,
        tChassisIxrResVxlanLifFree,
        tChasIxrResOwnAcLifAlloc,
        tChasIxrResOwnMplsNhlfeLifAlloc,
        tChasIxrResOwnBgpLblRtLifTotal,
        tChasIxrResOwnBgpLblRtLifAlloc,
        tChasIxrResOwnBgpLblRtLifFree,
        tChasIxrResOwnSdpBndMplsLifAlloc,
        tChasIxrResOwnSdpBndGreLifAlloc,
        tChasIxrResOwnSsidLifAlloc,
        tChasIxrResOwnSrv6TunnelLifAlloc,
        tChasIxrResOwnL2ServiceAlloc,
        tChasIxrResOwnStationIdAlloc,
        tChasIxrResOwnVxlanLifAlloc,
        tFpIxrResourceEgressBanksTotal,
        tFpIxrResourceEgressBanksAlloc,
        tFpIxrResourceEgressBanksFree,
        tFpIxrResourceEgressPhases,
        tFpIxrRsEgPhLinkedDataBanks,
        tFpIxrRsEgPhLinkedDataTotal,
        tFpIxrRsEgPhLinkedDataAlloc,
        tFpIxrRsEgPhLinkedDataFree,
        tFpIxrRsEgPhNonLinkedDataBanks,
        tFpIxrRsEgPhNonLinkedDataTotal,
        tFpIxrRsEgPhNonLinkedDataAlloc,
        tFpIxrRsEgPhNonLinkedDataFree,
        tFpIxrRsEgPhLinkedListBanks,
        tFpIxrRsEgPhLinkedListTotal,
        tFpIxrRsEgPhLinkedListAlloc,
        tFpIxrRsEgPhLinkedListFree
    }
    STATUS      current
    DESCRIPTION
        "The group of objects supporting IXR J2 resource index  on Nokia SROS
         series systems"
    ::= { tmnxChassisV23v0Groups 24 }

tmnxIxrRsrcObsoletedGroup        OBJECT-GROUP
    OBJECTS     {
        tCardIxrResMplsEcmpGroupsTotal,
        tCardIxrResMplsEcmpGroupsAlloc,
        tCardIxrResMplsEcmpGroupsFree,
        tCardIxrResIpEcmpGroupsTotal,
        tCardIxrResIpEcmpGroupsAlloc,
        tCardIxrResIpEcmpGroupsFree
    }
    STATUS      current
    DESCRIPTION
        "The group of IXR resource related objects deprecated in release 23.10
         on Nokia SROS series systems."
    ::= { tmnxChassisV23v0Groups 25 }

tChassisIxrResDynEcmpAllocGroup  OBJECT-GROUP
    OBJECTS     {
        tCardIxrResGrpFecsTotal,
        tCardIxrResGrpFecsAlloc,
        tCardIxrResGrpFecsFree,
        tCardIxrResGrpFecBanksTotal,
        tCardIxrResGrpFecBanksAlloc,
        tCardIxrResGrpFecBanksFree,
        tCardIxrResGrpFecLvl1BanksAlloc,
        tCardIxrResGrpFecLvl2BanksAlloc,
        tCardIxrResGrpFecLevel1Total,
        tCardIxrResGrpFecLevel1Alloc,
        tCardIxrResGrpFecLevel1Free,
        tCardIxrResGrpFecLevel2Total,
        tCardIxrResGrpFecLevel2Alloc,
        tCardIxrResGrpFecLevel2Free,
        tCardIxrResOwnGrpFecAlloc,
        tCardIxrResOwnGrpFecLevel1Alloc,
        tCardIxrResOwnGrpFecLevel2Alloc
    }
    STATUS      current
    DESCRIPTION
        "The group of objects supporting dynamic allocation of ECMP resources
         on Nokia SROS series systems"
    ::= { tmnxChassisV23v0Groups 26 }

tmnxChassisResMtuProfileV23v0Grp OBJECT-GROUP
    OBJECTS     {
        tChassisResMtuProfileTotal,
        tChassisResMtuProfileAlloc
    }
    STATUS      current
    DESCRIPTION
        "The group of objects supporting management of Resource Information
         related to mtu profiles."
    ::= { tmnxChassisV23v0Groups 27 }

tmnxChassisResEprirSrV23v0Grp    OBJECT-GROUP
    OBJECTS     {
        tChassisResEprirRadiusAlloc,
        tChassisResEprirReservedAlloc,
        tChassisResEprirSatTrafGenTotal,
        tChassisResEprirSatTrafGenAlloc
    }
    STATUS      current
    DESCRIPTION
        "The group of objects supporting management of Resource Information
         related to Egress Packet Re-injection Resources (EPRIR) on SR only in
         release 23."
    ::= { tmnxChassisV23v0Groups 28 }

tmnxChassisResEprirIxrV23v0Grp   OBJECT-GROUP
    OBJECTS     {
        tChassisResEprirFilterAlloc
    }
    STATUS      current
    DESCRIPTION
        "The group of objects supporting management of Resource Information
         related to Egress Packet Re-injection Resources (EPRIR) for filters on
         IXR only in release 23."
    ::= { tmnxChassisV23v0Groups 29 }

tmnxChassisResEprirSrIxrV23v0Grp OBJECT-GROUP
    OBJECTS     {
        tChassisResEprirTotal,
        tChassisResEprirAlloc,
        tChassisResEprirMirrorAlloc
    }
    STATUS      current
    DESCRIPTION
        "The group of objects supporting management of Resource Information
         related to Egress Packet Re-injection Resources (EPRIR) on SR and IXR
         in release 23."
    ::= { tmnxChassisV23v0Groups 30 }

tmnxChassisResEprirNotSrV23v0Grp OBJECT-GROUP
    OBJECTS     {
        tFPResOamSathTrafGenBandwAlloc,
        tFPResOamSathTrafGenBandwTotal,
        tFPResOamSathTrafGenSvcStrmTotal,
        tFPResOamSathTrafGenSvcStrmTotal
    }
    STATUS      current
    DESCRIPTION
        "The group of objects supporting management of Resource Information
         related to Egress Packet Re-injection Resources (EPRIR) not on SR in
         release 23."
    ::= { tmnxChassisV23v0Groups 31 }

tmnxChassisIxrResourceV24v0Group OBJECT-GROUP
    OBJECTS     {
        tChassisIxrResCommonLifTotal,
        tChassisIxrResCommonLifAlloc,
        tChassisIxrResCommonLifFree,
        tChassisIxrResArpLifTotal,
        tChassisIxrResArpLifAlloc,
        tChassisIxrResArpLifFree,
        tChassisIxrResMplsLifTotal,
        tChassisIxrResMplsLifAlloc,
        tChassisIxrResMplsLifFree,
        tChassisIxrResL3VsiRifTotal,
        tChassisIxrResL3VsiRifAlloc,
        tChassisIxrResL3VsiRifFree,
        tChassisIxrResFecUnpairedTotal,
        tChassisIxrResFecUnpairedAlloc,
        tChassisIxrResFecUnpairedFree,
        tChassisIxrResFecPairedTotal,
        tChassisIxrResFecPairedAlloc,
        tChassisIxrResFecPairedFree,
        tChassisIxrResOamLmCtrTotal,
        tChassisIxrResOamLmCtrAlloc,
        tChassisIxrResOamLmCtrFree,
        tChassisIxrResOwnCommonLifTotal,
        tChassisIxrResOwnCommonLifAlloc,
        tChassisIxrResOwnCommonLifFree,
        tChassisIxrResOwnArpLifAlloc,
        tChassisIxrResOwnMplsLifAlloc,
        tChassisIxrResOwnL3VsiRifAlloc,
        tChassisIxrResOwnFecUnpairAlloc,
        tChassisIxrResOwnFecPairedAlloc,
        tChassisIxrResOwnOamLmCtrAlloc,
        tCardIxrResFecBanksTotal,
        tCardIxrResFecBanksAlloc,
        tCardIxrResFecBanksFree,
        tCardIxrResFecLevel1BanksAlloc,
        tCardIxrResFecLevel2BanksAlloc,
        tCardIxrResFecsTotal,
        tCardIxrResFecsAlloc,
        tCardIxrResFecsFree,
        tCardIxrResFecLevel1Total,
        tCardIxrResFecLevel1Alloc,
        tCardIxrResFecLevel1Free,
        tCardIxrResFecLevel2Total,
        tCardIxrResFecLevel2Alloc,
        tCardIxrResFecLevel2Free,
        tCardIxrResOwnFecLevel1Alloc,
        tCardIxrResOwnFecLevel2Alloc,
        tFpIxrResEgrGlobalLifMapTotal,
        tFpIxrResEgrGlobalLifMapAlloc,
        tFpIxrResEgrGlobalLifMapFree,
        tFpIxrResIngTerminationATotal,
        tFpIxrResIngTerminationAAlloc,
        tFpIxrResIngTerminationAFree,
        tFpIxrResIngTerminationBTotal,
        tFpIxrResIngTerminationBAlloc,
        tFpIxrResIngTerminationBFree,
        tFpIxrResIngEndpoint1Total,
        tFpIxrResIngEndpoint1Alloc,
        tFpIxrResIngEndpoint1Free,
        tFpIxrResIngEndpoint2Total,
        tFpIxrResIngEndpoint2Alloc,
        tFpIxrResIngEndpoint2Free,
        tFpIxrResIngEndpoint3Total,
        tFpIxrResIngEndpoint3Alloc,
        tFpIxrResIngEndpoint3Free,
        tFpIxrResEgrEncapEntriesTotal,
        tFpIxrResEgrEncapEntriesAlloc,
        tFpIxrResEgrEncapEntriesFree,
        tFpIxrResEgrEncapBanksTotal,
        tFpIxrResEgrEncapBanksAlloc,
        tFpIxrResEgrEncapBanksFree,
        tFpIxrResEgrRoutedTotal,
        tFpIxrResEgrRoutedAlloc,
        tFpIxrResEgrRoutedFree,
        tFpIxrResEgrRoutedBanks,
        tFpIxrResEgrTdmTotal,
        tFpIxrResEgrTdmAlloc,
        tFpIxrResEgrTdmFree,
        tFpIxrResEgrTdmBanks,
        tFpIxrResEgrPortVlanXlatTotal,
        tFpIxrResEgrPortVlanXlatAlloc,
        tFpIxrResEgrPortVlanXlatFree,
        tFpIxrResEgrPortVlanXlatBanks,
        tFpIxrResEgrArpTotal,
        tFpIxrResEgrArpAlloc,
        tFpIxrResEgrArpFree,
        tFpIxrResEgrArpBanks,
        tFpIxrResEgrLabelPushTotal,
        tFpIxrResEgrLabelPushAlloc,
        tFpIxrResEgrLabelPushFree,
        tFpIxrResEgrLabelPushBanks,
        tFpIxrResEgrLabelSwapPushTotal,
        tFpIxrResEgrLabelSwapPushAlloc,
        tFpIxrResEgrLabelSwapPushFree,
        tFpIxrResEgrLabelSwapPushBanks,
        tFpIxrResEgrPortVlanXltExtTotal,
        tFpIxrResEgrPortVlanXltExtAlloc,
        tFpIxrResEgrPortVlanXltExtFree,
        tFpIxrResEgrPortVlanXltExtBanks,
        tFpIxrResEgrArpExtTotal,
        tFpIxrResEgrArpExtAlloc,
        tFpIxrResEgrArpExtFree,
        tFpIxrResEgrArpExtBanks,
        tFpIxrResEgrLabelPushExtTotal,
        tFpIxrResEgrLabelPushExtAlloc,
        tFpIxrResEgrLabelPushExtFree,
        tFpIxrResEgrLabelPushExtBanks,
        tFpIxrResEgrLabelSwapPshExTotal,
        tFpIxrResEgrLabelSwapPshExAlloc,
        tFpIxrResEgrLabelSwapPshExFree,
        tFpIxrResEgrLabelSwapPshExBanks,
        tFpIxrResEgrEncapExtEntriesTotal,
        tFpIxrResEgrEncapExtEntriesAlloc,
        tFpIxrResEgrEncapExtEntriesFree,
        tFpIxrResEgrEncapExtBanksTotal,
        tFpIxrResEgrEncapExtBanksAlloc,
        tFpIxrResEgrEncapExtBanksFree,
        tFpIxrResEgrExPortVlanXlatTotal,
        tFpIxrResEgrExPortVlanXlatAlloc,
        tFpIxrResEgrExPortVlanXlatFree,
        tFpIxrResEgrExPortVlanXlatBanks,
        tFpIxrResEgrExArpTotal,
        tFpIxrResEgrExArpAlloc,
        tFpIxrResEgrExArpFree,
        tFpIxrResEgrExArpBanks,
        tFpIxrResEgrExLabelPushTotal,
        tFpIxrResEgrExLabelPushAlloc,
        tFpIxrResEgrExLabelPushFree,
        tFpIxrResEgrExLabelPushBanks,
        tFpIxrResEgrExLabelSwapPshTotal,
        tFpIxrResEgrExLabelSwapPshAlloc,
        tFpIxrResEgrExLabelSwapPshFree,
        tFpIxrResEgrExLabelSwapPshBanks
    }
    STATUS      current
    DESCRIPTION
        "The group of objects supporting IXR resource index  on Nokia SROS
         series systems"
    ::= { tmnxChassisV23v0Groups 32 }

tmnxVlanQosScalingModeGroup      OBJECT-GROUP
    OBJECTS     {
        tChassisResEgrStat4QVVoQTotal,
        tChassisResEgrStat4QVVoQAlloc,
        tChassisResEgrNoStat4QVVoQTotal,
        tChassisResEgrNoStat4QVVoQAlloc,
        tCoreRes4QVlanVoqTotal,
        tCoreRes4QVlanVoqAlloc
    }
    STATUS      current
    DESCRIPTION
        "The group of additional objects supporting management of XIOM
         capabilities in release 23 on Nokia SROS series systems."
    ::= { tmnxChassisV23v0Groups 33 }

tmnxChassisV24v0Groups           OBJECT IDENTIFIER ::= { tmnxChassisGroups 86 }

tmnxChassisMDAV24v0ObsoletedGrp  OBJECT-GROUP
    OBJECTS     {
        tmnxMDAClockMode
    }
    STATUS      current
    DESCRIPTION
        "The group of MDA related objects obsoleted in release 24.0 on Nokia
         SROS series systems."
    ::= { tmnxChassisV24v0Groups 1 }

tmnxChassisCemMDAV24v0Group      OBJECT-GROUP
    OBJECTS     {
        tmnxMDADiffTimestampFreq
    }
    STATUS      current
    DESCRIPTION
        "The group of CEM MDA related objects supported in release 24.0 on
         Nokia SROS series systems."
    ::= { tmnxChassisV24v0Groups 2 }

tFPResEgrHwAggSV24v0ObsoletedGrp OBJECT-GROUP
    OBJECTS     {
        tFPResEgrHwAggShapQSetSizeTotal,
        tFPResEgrHwAggShapQSetSizeAlloc,
        tFPResEgrHwAggShapQSetSize1Total,
        tFPResEgrHwAggShapQSetSize1Alloc
    }
    STATUS      current
    DESCRIPTION
        "The group of FP Resource related objects obsoleted in release 24.0 on
         Nokia SROS series systems."
    ::= { tmnxChassisV24v0Groups 3 }

tFPResEgrHwAggShaperV24v0Group   OBJECT-GROUP
    OBJECTS     {
        tFPResEgrHwAggShpDefSapQSetSz,
        tFPResEgrHwAggShpDefSubQSetSz,
        tFPResEgrHwAggShpDefQGrpQSetSz,
        tFPResEgrHwAggShapQSetSize2Total,
        tFPResEgrHwAggShapQSetSize2Alloc,
        tFPResEgrHwAggShapQSetSize3Total,
        tFPResEgrHwAggShapQSetSize3Alloc,
        tFPResEgrHwAggShapQSetSize4Total,
        tFPResEgrHwAggShapQSetSize4Alloc,
        tFPResEgrHwAggShapQSetSize5Total,
        tFPResEgrHwAggShapQSetSize5Alloc,
        tFPResEgrHwAggShapQSetSize6Total,
        tFPResEgrHwAggShapQSetSize6Alloc,
        tFPResEgrHwAggShapQSetSize7Total,
        tFPResEgrHwAggShapQSetSize7Alloc
    }
    STATUS      current
    DESCRIPTION
        "The group of objects supporting management of FP Resource Information
         on release 24.0 of Nokia SROS series systems."
    ::= { tmnxChassisV24v0Groups 4 }

tmnxFlashV24v0Group              OBJECT-GROUP
    OBJECTS     {
        tmnxFlashSerialNumber,
        tmnxFlashOperStatus,
        tmnxFlashFirmwareRevision,
        tmnxFlashModelNumber,
        tmnxFlashCapacity,
        tmnxFlashUsed,
        tmnxFlashPercentageUsed
    }
    STATUS      current
    DESCRIPTION
        "The group of objects supporting management of flash unit information
         on release 24.0 of Nokia SROS series systems."
    ::= { tmnxChassisV24v0Groups 5 }

tmnxEsaHwStatusPwrLoadV24v0Grp   OBJECT-GROUP
    OBJECTS     {
        tmnxEsaStatsPowerSupply1Voltage,
        tmnxEsaStatsPowerSupply2Voltage,
        tmnxEsaStatsPowerSupply1OutPwr,
        tmnxEsaStatsPowerSupply2OutPwr,
        tmnxEsaStatsPowerSupply1MaxPwr,
        tmnxEsaStatsPowerSupply2MaxPwr
    }
    STATUS      current
    DESCRIPTION
        "The group of objects for ESA HW status power load display  in release
         24.x on Nokia systems."
    ::= { tmnxChassisV24v0Groups 6 }

tmnxEsaHwStatusTempV24v0Grp      OBJECT-GROUP
    OBJECTS     {
        tmnxEsaStatsCpu1TempThreshold,
        tmnxEsaStatsCpu2TempThreshold,
        tmnxEsaStatsNic1Temperature,
        tmnxEsaStatsNic2Temperature,
        tmnxEsaStatsNic1TempThreshold,
        tmnxEsaStatsNic2TempThreshold
    }
    STATUS      current
    DESCRIPTION
        "The group of objects for ESA HW status temperature stats  in release
         24.x on Nokia systems."
    ::= { tmnxChassisV24v0Groups 7 }

tmnxVirtualSchedAdjV24v0Grp      OBJECT-GROUP
    OBJECTS     {
        tmnxCardManulCntrlParamRowStatus,
        tmnxCardManulCntrlParamLastChngd,
        tmnxCardManualCntrlAdminState,
        tmnxCardManualCntrlParamPrcnt
    }
    STATUS      current
    DESCRIPTION
        "The group of objects for configurable controls for HQOS CPU limits in
         release 24.x on Nokia systems."
    ::= { tmnxChassisV24v0Groups 8 }

tmnxEsaHostPortStatsV24v0Grp     OBJECT-GROUP
    OBJECTS     {
        tmnxEsaHostPortNicXceiverType,
        tmnxEsaHostPortNicXceiverMN,
        tmnxEsaHostPortNicXceiverLWL,
        tmnxEsaHostPortNicSFPNumLanes,
        tmnxEsaHostPortNicSFPVendorOUI,
        tmnxEsaHostPortNictSFPConCode,
        tmnxEsaHostPortNicSFPVendorMfg,
        tmnxEsaHostPortNicSFPMedia,
        tmnxEsaHostPortNicSFPVendorSN,
        tmnxEsaHostPortNicSFPVendorPN,
        tmnxEsaHostPortNicOptCompliance,
        tmnxEsaHostPortNicOptCCExtension,
        tmnxEsaHostPortNicLinkLenInfo,
        tmnxEsaHostPortNicDDMTemp,
        tmnxEsaHostPortNicDDMTempLowWarn,
        tmnxEsaHostPortNicDDMTempLwAlarm,
        tmnxEsaHostPortNicDDMTempHiWarn,
        tmnxEsaHostPortNicDDMTempHiAlarm,
        tmnxEsaHostPortNicDDMSupVoltage,
        tmnxEsaHostPortNicDDMSVLowWarn,
        tmnxEsaHostPortNicDDMSVLowAlarm,
        tmnxEsaHostPortNicDDMSVHiWarn,
        tmnxEsaHostPortNicDDMSVHiAlarm,
        tmnxEsaHostPortNicDDMTxBiasCurr,
        tmnxEsaHostPortNicDDMTxBCLwWarn,
        tmnxEsaHostPortNicDDMTxBCLwAlarm,
        tmnxEsaHostPortNicDDMTxBCHiWarn,
        tmnxEsaHostPortNicDDMTxBCHiAlarm,
        tmnxEsaHostPortNicDDMTxOutPower,
        tmnxEsaHostPortNicDDMTxOPLwWarn,
        tmnxEsaHostPortNicDDMTxOPLwAlarm,
        tmnxEsaHostPortNicDDMTxOPHiWarn,
        tmnxEsaHostPortNicDDMTxOPHiAlarm,
        tmnxEsaHostPortNicDDMRxOpPower,
        tmnxEsaHostPortNicDDMRxOpPLwWarn,
        tmnxEsaHostPortNicDDMRxOpPLwAlrm,
        tmnxEsaHostPortNicDDMRxOpPHiWarn,
        tmnxEsaHostPortNicDDMRxOpPHiAlrm,
        tmnxEsaHostPortOperStatus,
        tmnxEsaHostPortFwdStatus,
        tmnxEsaHostPortRxTotalPkts,
        tmnxEsaHostPortTxTotalPkts,
        tmnxEsaHostPortRxDiscards,
        tmnxEsaHostPortRxCrcErrors,
        tmnxEsaHostPortRxSymErrors
    }
    STATUS      current
    DESCRIPTION
        "The group of objects for configurable controls for HQOS CPU limits in
         release 24.x on Nokia systems."
    ::= { tmnxChassisV24v0Groups 9 }

tmnxIpsecLoadBalV24Group         OBJECT-GROUP
    OBJECTS     {
        tmnxIPsecIsaGrpSpiRangeIndex,
        tmnxTunnelGrpEsaVmWeight,
        tmnxTunnelGrpEsaVmAllocHashSlots
    }
    STATUS      current
    DESCRIPTION
        "The group of objects supporting the management of IPsec Weighted Load
         Balancing in release 24.0 on Nokia SROS series systems."
    ::= { tmnxChassisV24v0Groups 10 }

tmnxChassisPwrMgmtV24v0Grp       OBJECT-GROUP
    OBJECTS     {
        tmnxChassisPwrMgmtTotalWattage
    }
    STATUS      current
    DESCRIPTION
        "The group of objects supporting the management of reporting the total
         wattage in release 24.0 on Nokia SROS series systems."
    ::= { tmnxChassisV24v0Groups 11 }

tFPResV24v0Group                 OBJECT-GROUP
    OBJECTS     {
        tFPResDCpuProtCamEntryTotal,
        tFPResDCpuProtCamEntryAlloc,
        tCoreResSharedPolicerStatsTotal,
        tCoreResSharedPolicerStatsAlloc
    }
    STATUS      current
    DESCRIPTION
        "The group of objects supporting management of FP Resource Information
         on release 24.0 of Nokia SROS series systems."
    ::= { tmnxChassisV24v0Groups 13 }

tmnxMdaFlexEV24v0Grp             OBJECT-GROUP
    OBJECTS     {
        tMdaFlexMbrInstOperInstNum,
        tMdaFlexMbrInstOperCurrentAlarm,
        tMdaFlexMbrInstOperReportedAlm,
        tmnxMdaFlexGroupNumber,
        tmnxMdaFlexGroupCurrentAlarm,
        tmnxMdaFlexGroupReportAlarm,
        tmnxMdaFlexGroupReportedAlarm,
        tmnxMdaFlexMemberReportAlarm,
        tmnxMdaFlexMemberCurrentAlarm,
        tmnxMdaFlexMemberReportedAlarm,
        tMdaFlexMbrInstOperDeskewDepth,
        tMdaFlexMbrInstOperInfoValid,
        tMdaFlexMbrInstOperCalInUse,
        tMdaFlexMbrInstOperFlexEMap,
        tMdaFlexMbrInstOperCalASlots,
        tMdaFlexMbrInstOperCalBSlots,
        tMdaFlexMbrInstOperRcvdGrpNum,
        tMdaFlexMbrInstOperRcvdInstNum,
        tmnxMdaFlexMemberPhyReportAlarm
    }
    STATUS      current
    DESCRIPTION
        "The group of objects supporting the management specific to FlexE on
         release 24.0 of Nokia SROS series systems."
    ::= { tmnxChassisV24v0Groups 14 }

tmnxEsaHostPortCrcMonV24v0Group  OBJECT-GROUP
    OBJECTS     {
        tmnxEsaHostPortCrcMonSdThreshold,
        tmnxEsaHostPortCrcMonSdTMltplier,
        tmnxEsaHostPortCrcMonSfThreshold,
        tmnxEsaHostPortCrcMonSfTMltplier,
        tmnxEsaHostPortCrcMonWindowSize
    }
    STATUS      current
    DESCRIPTION
        "The group of objects supporting the crc monitoring specific to ESA
         Host Port."
    ::= { tmnxChassisV24v0Groups 15 }

tmnxChassisFpIxrResV24v0Group    OBJECT-GROUP
    OBJECTS     {
        tFpIxrResLargeExactMatchTotal,
        tFpIxrResLargeExactMatchAlloc,
        tFpIxrResLargeExactMatchFree
    }
    STATUS      current
    DESCRIPTION
        "The group of objects supporting additional information about FP
         resource utilization specific to the Nokia IXR systems."
    ::= { tmnxChassisV24v0Groups 16 }

tmnxEsaHostPortNotifV24v0Group   NOTIFICATION-GROUP
    NOTIFICATIONS {
        tmnxEqEsaHostPortCrcAlarm,
        tmnxEqEsaHostPortCrcAlarmClear
    }
    STATUS      current
    DESCRIPTION
        "The group of notifications extending host port capabilities for
         revision 24.0 on Nokia SROS series systems."
    ::= { tmnxChassisV24v0Groups 17 }

tmnxChassisOsSecV24v0Group       OBJECT-GROUP
    OBJECTS     {
        tmnxChassisOsSecPasswd,
        tmnxCpmCardAntiTheft,
        tmnxChassisAntiTheftLocked
    }
    STATUS      current
    DESCRIPTION
        "The group of objects supporting chassis-specific information about OS
         Security features in the Nokia SR series of systems."
    ::= { tmnxChassisV24v0Groups 18 }

tmnxEsaFirmUpgNotifV24v0Group    NOTIFICATION-GROUP
    NOTIFICATIONS {
        tmnxEsaFirmwareUpgradeInProgress,
        tmnxEsaFirmwareUpgradeDone,
        tmnxEsaFirmwareUpgradeFailed
    }
    STATUS      current
    DESCRIPTION
        "The group of notifications extending esa firmware upgrade capabilities
         for revision 24.0 on Nokia SROS series systems."
    ::= { tmnxChassisV24v0Groups 19 }

tmnxChassisIxrResOwnV24v0Group   OBJECT-GROUP
    OBJECTS     {
        tChasIxrResOwnAcLifTotal,
        tChasIxrResOwnAcLifFree
    }
    STATUS      current
    DESCRIPTION
        "The group of objects extending support for IXR resource index  on
         Nokia SROS series systems"
    ::= { tmnxChassisV24v0Groups 20 }

tmnxChassisIxrResScaleV24v0Grp   OBJECT-GROUP
    OBJECTS     {
        tCardIxrResIlmSwapTotal,
        tCardIxrResIlmSwapAlloc,
        tCardIxrResIlmSwapFree
    }
    STATUS      current
    DESCRIPTION
        "The group of objects extending support for dynamic allocation for
         revision 24.0 on Nokia SROS series systems."
    ::= { tmnxChassisV24v0Groups 21 }

tmnxCardIxrResourcesV24v0Group   OBJECT-GROUP
    OBJECTS     {
        tCardIxrResFecLevel3Total,
        tCardIxrResFecLevel3Alloc,
        tCardIxrResFecLevel3Free,
        tCardIxrResGrpFecLvl3BanksAlloc,
        tCardIxrResGrpFecLevel3Total,
        tCardIxrResGrpFecLevel3Alloc,
        tCardIxrResGrpFecLevel3Free,
        tCardIxrResOwnFecLevel3Alloc,
        tCardIxrResOwnGrpFecLevel3Alloc
    }
    STATUS      current
    DESCRIPTION
        "The group of objects extending support for IXR resource index on Nokia
         SROS series systems"
    ::= { tmnxChassisV24v0Groups 22 }

tmnxChassisOsSecV24v0NotifGrp    NOTIFICATION-GROUP
    NOTIFICATIONS {
        tmnxChassisAntiTheftModeBoot,
        tmnxChassisAntiTheftUnlocked
    }
    STATUS      current
    DESCRIPTION
        "The group of objects supporting chassis-specific notifications about
         OS Security features in the Nokia SR series of systems."
    ::= { tmnxChassisV24v0Groups 24 }

tmnxCardIxrPpmcResourcesGroup    OBJECT-GROUP
    OBJECTS     {
        tCardIxrResPpmcBestCaseEstTotal,
        tCardIxrResPpmcWrstCaseEstTotal,
        tCardIxrResPpmcSingleLevelAlloc,
        tCardIxrResPpmcMultiLevelAlloc,
        tCardIxrResOwnPpmcSingleLvlAlloc,
        tCardIxrResOwnPpmcMultiLvlAlloc
    }
    STATUS      current
    DESCRIPTION
        "The group of objects extending support for IXR resource index on Nokia
         SROS series systems"
    ::= { tmnxChassisV24v0Groups 25 }

tmnxCardIxrPpmcResourcesGroup2   OBJECT-GROUP
    OBJECTS     {
        tCardIxrResPpmcExhausted
    }
    STATUS      current
    DESCRIPTION
        "The group of objects extending support for IXR resource index on Nokia
         SROS series systems"
    ::= { tmnxChassisV24v0Groups 26 }

tmnxChassisV25v0Groups           OBJECT IDENTIFIER ::= { tmnxChassisGroups 87 }

tFPResV25v0Group                 OBJECT-GROUP
    OBJECTS     {
        tFPResSapIngAggPolicerTotal,
        tFPResSapIngAggPolicerAlloc
    }
    STATUS      current
    DESCRIPTION
        "The group of objects supporting management of FP Resource Information
         on release 25.0 of Nokia SROS series systems."
    ::= { tmnxChassisV25v0Groups 1 }

tmnxChassisPwrMgmtLowPwrV25v0Grp OBJECT-GROUP
    OBJECTS     {
        tChassisPwrMgmtLowPwrFabAdmState,
        tChassisPwrMgmtLowPwrFabCapacity,
        tChassisPwrMgmtLowPwrFabOprState,
        tChassisPwrMgmtLowPwrFabLstChgd
    }
    STATUS      current
    DESCRIPTION
        "The group of objects adding support for low power switch fabric mode
         on Nokia SROS series systems"
    ::= { tmnxChassisV25v0Groups 2 }

tmnxLowPowerSwFabV25v0NotifGrp   NOTIFICATION-GROUP
    NOTIFICATIONS {
        tmnxEqLowPowerSwFabModeEnabled,
        tmnxEqLowPowerSwFabModeDisabled
    }
    STATUS      current
    DESCRIPTION
        "The group of notifications supporting for low power switch fabric mode
         on the Nokia SROS series systems."
    ::= { tmnxChassisV25v0Groups 3 }

tmnxChGoldenStatusV25v0Group     NOTIFICATION-GROUP
    NOTIFICATIONS {
        tmnxChassisGoldenStatusEvent
    }
    STATUS      current
    DESCRIPTION
        "The group of notifications supporting for anti-rollback mode on the
         Nokia SROS series systems."
    ::= { tmnxChassisV25v0Groups 4 }

tmnxSyncFreqOffsetInPpbGroup     OBJECT-GROUP
    OBJECTS     {
        tmnxSyncIfTimingFreqOffsetPpb
    }
    STATUS      current
    DESCRIPTION
        "The group of objects adding support Frequency Offset in Parts per
         Billion on Nokia SROS series systems"
    ::= { tmnxChassisV25v0Groups 5 }

tmnxMDAMacModeV25v0Grp           OBJECT-GROUP
    OBJECTS     {
        tmnxMDAMacMode
    }
    STATUS      current
    DESCRIPTION
        "The group of objects supporting MDA-level MAC mode on release 25.0 of
         the Nokia SROS series systems."
    ::= { tmnxChassisV25v0Groups 6 }

tmnxFltrSharedPlcrV25v0Grp       OBJECT-GROUP
    OBJECTS     {
        tCoreResFltrSharedPlcrTotal,
        tCoreResFltrSharedPlcrAlloc,
        tCoreResFltrSharedPlcrStatsTotal,
        tCoreResFltrSharedPlcrStatsAlloc
    }
    STATUS      current
    DESCRIPTION
        "The group of additional objects supporting management of flexqos
         application filter-shared-policer in release 25 on Nokia SROS series
         systems."
    ::= { tmnxChassisV25v0Groups 7 }

tmnxSchedulerFlowsV25v0Grp       OBJECT-GROUP
    OBJECTS     {
        tCoreResSchedulerFlowTotal,
        tCoreResSchedulerFlowAlloc,
        tCoreResSchedulerInterfacesTotal,
        tCoreResSchedulerInterfacesAlloc
    }
    STATUS      current
    DESCRIPTION
        "The group of objects supporting scheduler flows per core on the Nokia
         SROS series systems."
    ::= { tmnxChassisV25v0Groups 10 }

tmnxChassisFpIxrResV25v0Group    OBJECT-GROUP
    OBJECTS     {
        tFpIxrResLargeExactMatch1Total,
        tFpIxrResLargeExactMatch1Alloc,
        tFpIxrResLargeExactMatch1Free,
        tFpIxrResLargeExactMatch2Total,
        tFpIxrResLargeExactMatch2Alloc,
        tFpIxrResLargeExactMatch2Free,
        tFpIxrRsEgPhLinkedDataLifs,
        tFpIxrRsEgPhNonLinkedDataLifs
    }
    STATUS      current
    DESCRIPTION
        "The group of objects supporting additional information about FP
         resource utilization specific to the Nokia IXR systems."
    ::= { tmnxChassisV25v0Groups 11 }

tmnxChassisPortSpeedModeV25v0Grp OBJECT-GROUP
    OBJECTS     {
        tmnxChassisPortSpeedMode
    }
    STATUS      current
    DESCRIPTION
        "The group of objects supporting chassis port speed mode on release
         25.0 of the Nokia SROS series systems."
    ::= { tmnxChassisV25v0Groups 12 }

tmnxCpmCardOsSecurityV25v0Grp    OBJECT-GROUP
    OBJECTS     {
        tmnxCpmCardPwdPendingActivation
    }
    STATUS      current
    DESCRIPTION
        "The group of objects supporting OS Security password enhancements on
         release 25.0 of the Nokia SROS series systems."
    ::= { tmnxChassisV25v0Groups 13 }

tmnxSecEraseNotifyObjsV25v0Grp   OBJECT-GROUP
    OBJECTS     {
        tmnxChassisNotifyDiskFormatType
    }
    STATUS      current
    DESCRIPTION
        "The group of notifications supporting secure erase on storage devices
         on release 25.0 of the Nokia SROS series systems."
    ::= { tmnxChassisV25v0Groups 14 }

tmnxSecEraseNotificationGrpV25v0 NOTIFICATION-GROUP
    NOTIFICATIONS {
        tmnxEqFlashDiskFormatStart,
        tmnxEqFlashDiskFormatFinish
    }
    STATUS      current
    DESCRIPTION
        "The group of notifications supporting secure erase on storage devices
         on release 25.0 of the Nokia SROS series systems."
    ::= { tmnxChassisV25v0Groups 15 }

tmnxVirtualFlowsV25v0Grp         OBJECT-GROUP
    OBJECTS     {
        tCoreRes8QVirtualFlowTotal,
        tCoreRes8QVirtualFlowAlloc,
        tCoreRes4QVirtualFlowTotal,
        tCoreRes4QVirtualFlowAlloc
    }
    STATUS      current
    DESCRIPTION
        "The group of objects supporting virtual flows per core on the Nokia
         SROS series systems."
    ::= { tmnxChassisV25v0Groups 16 }

tmnxBfdMHopV25v0Grp              OBJECT-GROUP
    OBJECTS     {
        tFPResBfdMhopIPv4CamEntryTotal,
        tFPResBfdMhopIPv4CamEntryAlloc,
        tFPResBfdMhopIPv6CamEntryTotal,
        tFPResBfdMhopIPv6CamEntryAlloc,
        tFPResCamBanksIUBSeamlessBfd
    }
    STATUS      current
    DESCRIPTION
        "The group of objects supporting virtual flows per core on the Nokia
         SROS series systems."
    ::= { tmnxChassisV25v0Groups 17 }

tmnxChassisV26v0Groups           OBJECT IDENTIFIER ::= { tmnxChassisGroups 88 }

tmnxBluetoothObsoleteV26Group    OBJECT-GROUP
    OBJECTS     {
        tmnxBluetoothTableLastChange,
        tmnxBluetoothPasskey,
        tmnxBluetoothAdvertisingTimeout,
        tmnxBluetoothPowerState,
        tmnxBluetoothPairingButton,
        tmnxBluetoothDeviceTableLastChg,
        tmnxBluetoothDeviceRowStatus,
        tmnxBluetoothDeviceEntryLastChg,
        tmnxBluetoothDeviceDescription,
        tmnxBluetoothModuleTableLastChg,
        tmnxBluetoothModuleEntryLastChg,
        tmnxBluetoothModuleCfgIdentifier,
        tmnxBluetoothModuleIdentifier,
        tmnxBluetoothModuleConnected,
        tmnxBluetoothModuleConnectedMac
    }
    STATUS      current
    DESCRIPTION
        "The group of objects supporting management of Bluetooth capabilities
         made obsolete on Nokia SROS series systems for release 26.0."
    ::= { tmnxChassisV26v0Groups 2 }

tmnxMDAPreClassPlcyV26v0Grp      OBJECT-GROUP
    OBJECTS     {
        tmnxMDAIngPreClassifierPolicy,
        tmnxMDAIngPreClassfrUngtagDot1p
    }
    STATUS      current
    DESCRIPTION
        "The group of objects supporting MDA-level pre-classifier-policy on
         release 26.7 of the Nokia SROS series systems."
    ::= { tmnxChassisV26v0Groups 4 }

tmnxLowRateVlanVoqV26v0Grp       OBJECT-GROUP
    OBJECTS     {
        tCoreRes8QLowRateVlanVoqTotal,
        tCoreRes8QLowRateVlanVoqAlloc,
        tCoreRes4QLowRateVlanVoqTotal,
        tCoreRes4QLowRateVlanVoqAlloc
    }
    STATUS      current
    DESCRIPTION
        "The group of objects supporting low rate vlan voq resources per core
         on the Nokia SROS series systems."
    ::= { tmnxChassisV26v0Groups 7 }

tmnxEthStormCtrlV26v0Grp         OBJECT-GROUP
    OBJECTS     {
        tFPResCamBanksIUBEthStormControl,
        tFPResEthStormCtrlCamBanksTotal,
        tFPResEthStormCtrlCamBanksAlloc,
        tFPResEthStormCtrlCamEntryTotal,
        tFPResEthStormCtrlCamEntryAlloc
    }
    STATUS      current
    DESCRIPTION
        "The group of objects supporting ethernet storm control FP resources on
         the Nokia SROS series systems."
    ::= { tmnxChassisV26v0Groups 8 }

tmnxChassisFpSarG2PolStatsV26Grp OBJECT-GROUP
    OBJECTS     {
        tmnxCardFpSarG2TC0PolCntRed,
        tmnxCardFpSarG2TC0PolCntYellow,
        tmnxCardFpSarG2TC0PolCntGreen,
        tmnxCardFpSarG2TC0PolCntReRed,
        tmnxCardFpSarG2TC0PolCntReYellow,
        tmnxCardFpSarG2TC1PolCntRed,
        tmnxCardFpSarG2TC1PolCntYellow,
        tmnxCardFpSarG2TC1PolCntGreen,
        tmnxCardFpSarG2TC1PolCntReRed,
        tmnxCardFpSarG2TC1PolCntReYellow,
        tmnxCardFpSarG2TC2PolCntRed,
        tmnxCardFpSarG2TC2PolCntYellow,
        tmnxCardFpSarG2TC2PolCntGreen,
        tmnxCardFpSarG2TC2PolCntReRed,
        tmnxCardFpSarG2TC2PolCntReYellow,
        tmnxCardFpSarG2TC3PolCntRed,
        tmnxCardFpSarG2TC3PolCntYellow,
        tmnxCardFpSarG2TC3PolCntGreen,
        tmnxCardFpSarG2TC3PolCntReRed,
        tmnxCardFpSarG2TC3PolCntReYellow,
        tmnxCardFpSarG2TC4PolCntRed,
        tmnxCardFpSarG2TC4PolCntYellow,
        tmnxCardFpSarG2TC4PolCntGreen,
        tmnxCardFpSarG2TC4PolCntReRed,
        tmnxCardFpSarG2TC4PolCntReYellow,
        tmnxCardFpSarG2TC5PolCntRed,
        tmnxCardFpSarG2TC5PolCntYellow,
        tmnxCardFpSarG2TC5PolCntGreen,
        tmnxCardFpSarG2TC5PolCntReRed,
        tmnxCardFpSarG2TC5PolCntReYellow,
        tmnxCardFpSarG2TC6PolCntRed,
        tmnxCardFpSarG2TC6PolCntYellow,
        tmnxCardFpSarG2TC6PolCntGreen,
        tmnxCardFpSarG2TC6PolCntReRed,
        tmnxCardFpSarG2TC6PolCntReYellow,
        tmnxCardFpSarG2TC7PolCntRed,
        tmnxCardFpSarG2TC7PolCntYellow,
        tmnxCardFpSarG2TC7PolCntGreen,
        tmnxCardFpSarG2TC7PolCntReRed,
        tmnxCardFpSarG2TC7PolCntReYellow,
        tmnxMdaFpSarG2TC0PolCntRed,
        tmnxMdaFpSarG2TC0PolCntYellow,
        tmnxMdaFpSarG2TC0PolCntGreen,
        tmnxMdaFpSarG2TC0PolCntReRed,
        tmnxMdaFpSarG2TC0PolCntReYellow,
        tmnxMdaFpSarG2TC1PolCntRed,
        tmnxMdaFpSarG2TC1PolCntYellow,
        tmnxMdaFpSarG2TC1PolCntGreen,
        tmnxMdaFpSarG2TC1PolCntReRed,
        tmnxMdaFpSarG2TC1PolCntReYellow,
        tmnxMdaFpSarG2TC2PolCntRed,
        tmnxMdaFpSarG2TC2PolCntYellow,
        tmnxMdaFpSarG2TC2PolCntGreen,
        tmnxMdaFpSarG2TC2PolCntReRed,
        tmnxMdaFpSarG2TC2PolCntReYellow,
        tmnxMdaFpSarG2TC3PolCntRed,
        tmnxMdaFpSarG2TC3PolCntYellow,
        tmnxMdaFpSarG2TC3PolCntGreen,
        tmnxMdaFpSarG2TC3PolCntReRed,
        tmnxMdaFpSarG2TC3PolCntReYellow,
        tmnxMdaFpSarG2TC4PolCntRed,
        tmnxMdaFpSarG2TC4PolCntYellow,
        tmnxMdaFpSarG2TC4PolCntGreen,
        tmnxMdaFpSarG2TC4PolCntReRed,
        tmnxMdaFpSarG2TC4PolCntReYellow,
        tmnxMdaFpSarG2TC5PolCntRed,
        tmnxMdaFpSarG2TC5PolCntYellow,
        tmnxMdaFpSarG2TC5PolCntGreen,
        tmnxMdaFpSarG2TC5PolCntReRed,
        tmnxMdaFpSarG2TC5PolCntReYellow,
        tmnxMdaFpSarG2TC6PolCntRed,
        tmnxMdaFpSarG2TC6PolCntYellow,
        tmnxMdaFpSarG2TC6PolCntGreen,
        tmnxMdaFpSarG2TC6PolCntReRed,
        tmnxMdaFpSarG2TC6PolCntReYellow,
        tmnxMdaFpSarG2TC7PolCntRed,
        tmnxMdaFpSarG2TC7PolCntYellow,
        tmnxMdaFpSarG2TC7PolCntGreen,
        tmnxMdaFpSarG2TC7PolCntReRed,
        tmnxMdaFpSarG2TC7PolCntReYellow
    }
    STATUS      current
    DESCRIPTION
        "The group of card and MDA objects supporting datapath policer
         statistics on SAR Gen 2 platforms in release 26.0 of Nokia SROS series
         systems."
    ::= { tmnxChassisV26v0Groups 9 }

tmnxChassisOsSecV26v0NotifGrp    NOTIFICATION-GROUP
    NOTIFICATIONS {
        tmnxChassisAntiTheftMismatch,
        tmnxChassisAntiTheftMismatchClr
    }
    STATUS      current
    DESCRIPTION
        "The group of notifications for anti-theft redundant CPM state in
         release 26.0 of Nokia SROS series systems."
    ::= { tmnxChassisV26v0Groups 12 }

tmnxChassisDCCompliances         OBJECT IDENTIFIER ::= { tmnxChassisConformance 3 }

tmnxChassisDCGroups              OBJECT IDENTIFIER ::= { tmnxChassisConformance 4 }

tmnxHwNotification               OBJECT IDENTIFIER ::= { tmnxSRNotifyPrefix 2 }

tmnxChassisNotifyPrefix          OBJECT IDENTIFIER ::= { tmnxHwNotification 1 }

tmnxChassisNotification          OBJECT IDENTIFIER ::= { tmnxChassisNotifyPrefix 0 }

tmnxHwConfigChange               NOTIFICATION-TYPE
    OBJECTS     {
        tmnxChassisNotifyHwIndex,
        tmnxHwID,
        tmnxHwClass
    }
    STATUS      obsolete
    DESCRIPTION
        "A tmnxHwConfigChange notification is generated when the value of
         tmnxHwLastChange is updated.  It can be used by the NMS to trigger
         maintenance polls of the hardware configuration information.

         Only one tmnxHwConfigChange notification event will be generated
         in a 5 second throttling time period.  A notification event is
         the transmission of a single trap to a list of notification
         destinations configured in the SNMP-TARGET-MIB.

         If additional hardware configuration change occurs within the
         throttling period, the notification events for these changes are
         suppressed until the throttling period expires.  At the end of
         the throttling period, one notification event is generated if
         any addition configuration changes occurred within the just
         completed throttling period and another throttling period is
         started.

         The NMS should periodically check the value of tmnxHwConfigChange to
         detect any missed tmnxHwConfigChange traps.

         This notification was made obsolete in the 2.1 release.

         The tmnxHwConfigChange notification has been replaced with the generic
         change notifications from the TIMETRA-SYSTEM-MIB: tmnxConfigModify,
         tmnxConfigCreate, tmnxConfigDelete, tmnxStateChange."
    ::= { tmnxChassisNotification 1 }

tmnxEnvTempTooHigh               NOTIFICATION-TYPE
    OBJECTS     {
        tmnxChassisNotifyHwIndex,
        tmnxHwID,
        tmnxHwClass,
        tmnxHwTemperature,
        tmnxHwTempThreshold
    }
    STATUS      current
    DESCRIPTION
        "[CAUSE] Generated when the temperature sensor reading on an equipment
         object is greater than its configured threshold.

         [EFFECT] This could be causing intermittent errors and could also
         cause permanent damage to components.

         [RECOVERY] Remove or power down the affected cards, or improve the
         cooling to the node. More powerful fan trays may also be required."
    ::= { tmnxChassisNotification 2 }

tmnxEqPowerSupplyFailure         NOTIFICATION-TYPE
    OBJECTS     {
        tmnxChassisNotifyHwIndex,
        tmnxHwID,
        tmnxHwClass,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyInputStatus,
        tmnxChassisPowerSupplyOutputStatus
    }
    STATUS      obsolete
    DESCRIPTION
        "Generated when one of the chassis's power supplies fails.

         This notification was made obsolete in release 15.0."
    ::= { tmnxChassisNotification 3 }

tmnxEqPowerSupplyInserted        NOTIFICATION-TYPE
    OBJECTS     {
        tmnxChassisNotifyHwIndex,
        tmnxHwID,
        tmnxHwClass
    }
    STATUS      current
    DESCRIPTION
        "Generated when one of the chassis' power supplies is inserted."
    ::= { tmnxChassisNotification 4 }

tmnxEqPowerSupplyRemoved         NOTIFICATION-TYPE
    OBJECTS     {
        tmnxChassisNotifyHwIndex,
        tmnxHwID,
        tmnxHwClass
    }
    STATUS      current
    DESCRIPTION
        "[CAUSE] The tmnxEqPowerSupplyRemoved notification is generated when
         one of the power supplies is removed from the chassis or low input
         voltage is detected. The operating voltage range for the 7750 SR-7 and
         7750 SR-12 is -40 to -72 VDC. The notification is generated if the
         system detects that the voltage of the power supply has dropped to
         -42.5 VDC.

         [EFFECT] Reduced power can cause intermittent errors and could also
         cause permanent damage to components.

         [RECOVERY] Reinsert the power supply or raise the input voltage above
         -42.5 VDC."
    ::= { tmnxChassisNotification 5 }

tmnxEqFanFailure                 NOTIFICATION-TYPE
    OBJECTS     {
        tmnxChassisNotifyHwIndex,
        tmnxHwID,
        tmnxHwClass,
        tmnxChassisFanOperStatus,
        tmnxChassisFanSpeedPercent
    }
    STATUS      obsolete
    DESCRIPTION
        "Generated when one of the fans in a fan tray has failed.

         This notification was made obsolete in release 15.0."
    ::= { tmnxChassisNotification 6 }

tmnxEqCardFailure                NOTIFICATION-TYPE
    OBJECTS     {
        tmnxChassisNotifyHwIndex,
        tmnxHwID,
        tmnxHwClass,
        tmnxHwOperState,
        tmnxChassisNotifyCardFailureReason
    }
    STATUS      current
    DESCRIPTION
        "[CAUSE] Generated when one of the cards in a chassis has failed. The
         card type may be IOM (or XCM), MDA (or XMA), SFM, CCM, Compact Flash,
         etc. The reason is indicated in the details of the log event or alarm,
         and also available in the tmnxChassisNotifyCardFailureReason attribute
         in the SNMP notification.

         [EFFECT] The effect is dependent on the card that has failed. IOM (or
         XCM) or MDA (or XMA) failure will cause a loss of service for all
         services running on that card. A fabric failure can impact traffic
         to/from all cards. 7750 SR/7450 ESS - If the IOM/IMM fails then the
         two associated MDAs for the slot will also go down. 7950 XRS - If one
         out of two XMAs fails in a XCM slot then the XCM will remain up. If
         only one remaining operational XMA within a XCM slot fails, then the
         XCM will go into a booting operational state.

         [RECOVERY] Before taking any recovery steps, collect a tech-support
         file, then try resetting (clear) the card. If that doesn't work then
         try removing and then reinserting the card. If that doesn't work then
         replace the card."
    ::= { tmnxChassisNotification 7 }

tmnxEqCardInserted               NOTIFICATION-TYPE
    OBJECTS     {
        tmnxChassisNotifyHwIndex,
        tmnxHwID,
        tmnxHwClass,
        tmnxChassisNotifyCardName
    }
    STATUS      current
    DESCRIPTION
        "Generated when a card is inserted into the chassis.  The card type
         may be IOM, Fabric, MDA, CCM CPM module, compact flash module,
         etc."
    ::= { tmnxChassisNotification 8 }

tmnxEqCardRemoved                NOTIFICATION-TYPE
    OBJECTS     {
        tmnxChassisNotifyHwIndex,
        tmnxHwID,
        tmnxHwClass,
        tmnxChassisNotifyCardName
    }
    STATUS      current
    DESCRIPTION
        "[CAUSE] Generated when a card is removed from the chassis. The card
         type may be IOM (or XCM), MDA (or XMA), SFM, CCM, CPM, Compact Flash,
         etc.

         [EFFECT] The effect is dependent on the card that has been removed.
         IOM (or XCM) or MDA (or XMA) removal will cause a loss of service for
         all services running on that card. A fabric removal can impact traffic
         to/from all cards.

         [RECOVERY] Before taking any recovery steps collect a tech-support
         file, then try re-inserting the card. If that doesn't work then
         replace the card."
    ::= { tmnxChassisNotification 9 }

tmnxEqWrongCard                  NOTIFICATION-TYPE
    OBJECTS     {
        tmnxChassisNotifyHwIndex,
        tmnxHwID,
        tmnxHwClass
    }
    STATUS      current
    DESCRIPTION
        "[CAUSE] Generated when the wrong type of card is inserted into a slot of
         the chassis.  Even though a card may be physically supported by
         the slot, it may have been administratively configured to allow
         only certain card types in a particular slot location.  The card
         type may be IOM (or XCM), Fabric, MDA (or XMA), CPM module, etc.

         [EFFECT] The effect is dependent on the card that has been incorrectly
         inserted. Incorrect IOM (or XCM) or MDA (or XMA) insertion will cause
         a loss of service for all services running on that card.

         [RECOVERY] Insert the correct card into the correct slot, and ensure
         the slot is configured for the correct type of card."
    ::= { tmnxChassisNotification 10 }

tmnxEqCpuFailure                 NOTIFICATION-TYPE
    OBJECTS     {
        tmnxChassisNotifyHwIndex,
        tmnxHwID,
        tmnxHwClass
    }
    STATUS      obsolete
    DESCRIPTION
        "Generated when a failure is detected for a CPU on an IOM card or CPM
         module.

         This notification was made obsolete in the 2.1 release.

         A cpu failure on a CPM card is detected by the hardware bootup and is
         indicated by the boot diagnostic display. If there is no working
         redundant CPM card, the system does not come up.

         A failure of an IOM card or standby redundant CPM card causes the
         tmnxEqCardFailure notification to be sent."
    ::= { tmnxChassisNotification 11 }

tmnxEqMemoryFailure              NOTIFICATION-TYPE
    OBJECTS     {
        tmnxChassisNotifyHwIndex,
        tmnxHwID,
        tmnxHwClass
    }
    STATUS      obsolete
    DESCRIPTION
        "Generated when a memory module failure is detected for an IOM card or
         CPM module.

         This notification was made obsolete in the 2.1 release.

         A failure of the memory device is detected by the
         hardware bootup and is indicated by the boot diagnostic
         display.  If there is no working redundant CPM card,
         the system does not come up.

         A failure of the memory device during run-time causes the system to
         fail and the 'admin tech-support' information to be saved.

         A failure of an IOM card or standby redundant CPM card causes the
         tmnxEqCardFailure notification to be sent."
    ::= { tmnxChassisNotification 12 }

tmnxEqBackdoorBusFailure         NOTIFICATION-TYPE
    OBJECTS     {
        tmnxChassisNotifyChassisId
    }
    STATUS      obsolete
    DESCRIPTION
        "Generated when the backdoor bus has failed.

         This notification was made obsolete in the 2.1 release."
    ::= { tmnxChassisNotification 13 }

tmnxPeSoftwareError              NOTIFICATION-TYPE
    OBJECTS     {
        tmnxChassisNotifyHwIndex,
        tmnxHwID,
        tmnxHwClass
    }
    STATUS      obsolete
    DESCRIPTION
        "Generated when a software error has been detected.

         This notification was made obsolete in the 2.1 release.

         Many of the other notifications more specifically indicate detection
         of some type of software error.

         The 'admin tech-support' information helps developers diagnose a
         failure of the software in the field."
    ::= { tmnxChassisNotification 14 }

tmnxPeSoftwareAbnormalHalt       NOTIFICATION-TYPE
    OBJECTS     {
        tmnxChassisNotifyHwIndex,
        tmnxHwID,
        tmnxHwClass
    }
    STATUS      obsolete
    DESCRIPTION
        "Generated when the software has abnormally terminated.

         This notification was made obsolete in the 2.1 release.

          Many of the other notifications more specifically
          indicate detection of some type of software error.

          The 'admin tech-support' information helps developers
          diagnose a failure of the software in the field."
    ::= { tmnxChassisNotification 15 }

tmnxPeSoftwareVersionMismatch    NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between software versions of the
         active CPM and standby CPM or the CPM and IOM.
         tmnxChassisNotifyHwIndex identifies the mismatched CPM/IOM card and
         tmnxChassisNotifyMismatchedVer will contain the version of the
         mismatched card. The tmnxHwSoftwareCodeVersion object will contain the
         expected version."
    ::= { tmnxChassisNotification 16 }

tmnxPeOutOfMemory                NOTIFICATION-TYPE
    OBJECTS     {
        tmnxChassisNotifyHwIndex,
        tmnxHwID,
        tmnxHwClass
    }
    STATUS      obsolete
    DESCRIPTION
        "Generated when there is an out of memory error detected.

         This notification was made obsolete in the 2.1 release.

         The tmnxPeOutOfMemory notification has been replaced with the module
         specific notification from the TIMETRA-SYSTEM-MIB:
         tmnxModuleMallocFailed."
    ::= { tmnxChassisNotification 17 }

tmnxPeConfigurationError         NOTIFICATION-TYPE
    OBJECTS     {
        tmnxChassisNotifyHwIndex,
        tmnxHwID,
        tmnxHwClass
    }
    STATUS      obsolete
    DESCRIPTION
        "Generated when a configuration error has been detected.

         This notification was made obsolete in the 2.1 release.

         Many other notifications more specifically indicate
         detection of a configuration error.  In most cases the
         SNMP SET request that tries to make an invalid
         configuration results in an error response.

         In some cases the configuration parameters are valid
         and the SNMP SET request succeeds but the system cannot
         successfully apply the new parameters.  The affected
         object may then put into an operational 'down' state.
         A state change notification such as tmnxStateChange or
         a more specific notification is sent to alert about the
         problem.

         For example, an attempt to create an event log with a file-type
         destination when the specified cflash media is full or not present
         results in TIMETRA-LOG-MIB notifications tmnxLogSpaceContention,
         tmnxLogAdminLocFailed, or tmnxLogBackupLocFailed."
    ::= { tmnxChassisNotification 18 }

tmnxPeStorageProblem             NOTIFICATION-TYPE
    OBJECTS     {
        tmnxChassisNotifyHwIndex,
        tmnxHwID,
        tmnxHwClass
    }
    STATUS      obsolete
    DESCRIPTION
        "Generated when there is a storage capacity problem.

         This notification was made obsolete in the 2.1 release.

         The only 'storage' devices on the SR7750 are the cflash
         drives.  Cflash write errors cause a tmnxEqFlashDataLoss
         notification to be sent.  The tmnxEqFlashDiskFull
         notification is sent when the driver detects that the
         cflash device is full."
    ::= { tmnxChassisNotification 19 }

tmnxPeCpuCyclesExceeded          NOTIFICATION-TYPE
    OBJECTS     {
        tmnxChassisNotifyHwIndex,
        tmnxHwID,
        tmnxHwClass
    }
    STATUS      obsolete
    DESCRIPTION
        "Generated when the CPU cycle usage limit has been exceeded.

         This notification was made obsolete in the 2.1 release.

         It does not apply. The SR7750 software architecture does not restrict
         CPU cycles used by a specific code module."
    ::= { tmnxChassisNotification 20 }

tmnxRedPrimaryCPMFail            NOTIFICATION-TYPE
    OBJECTS     {
        tmnxChassisNotifyHwIndex,
        tmnxHwID,
        tmnxHwClass
    }
    STATUS      current
    DESCRIPTION
        "Generated when the primary CPM fails."
    ::= { tmnxChassisNotification 21 }

tmnxRedSecondaryCPMStatusChange  NOTIFICATION-TYPE
    OBJECTS     {
        tmnxChassisNotifyHwIndex,
        tmnxHwID,
        tmnxHwClass,
        tmnxRedSecondaryCPMStatus
    }
    STATUS      obsolete
    DESCRIPTION
        "Generated when there is a change in the secondary CPM status.

         This notification was made obsolete in the 2.1 release.

         There is no way to administratively enable or disable CPM cards so
         there is no need for a status change event for administrative state
         changes.

         Operational changes detected about the standby CPM card are indicated
         by more specific notifications such as tmnxEqCardFailure,
         tmnxEqCardRemoved, tmnxEqCardInserted
         TIMETRA-SYSTEM-MIB::ssiRedStandbyReady,
         TIMETRA-SYSTEM-MIB::ssiRedStandbySyncLost, and
         TIMETRA-SYSTEM-MIB::ssiRedStandbySyncLost."
    ::= { tmnxChassisNotification 22 }

tmnxRedRestoreSuccess            NOTIFICATION-TYPE
    OBJECTS     {
        tmnxChassisNotifyHwIndex,
        tmnxHwID,
        tmnxHwClass
    }
    STATUS      obsolete
    DESCRIPTION
        "Generated when the secondary CPM successfully restores the config and
         state.

         This notification was made obsolete in the 2.1 release.

         It does not apply. This event was originally created for an early
         redundancy mechanism that was never released."
    ::= { tmnxChassisNotification 23 }

tmnxRedRestoreFail               NOTIFICATION-TYPE
    OBJECTS     {
        tmnxChassisNotifyHwIndex,
        tmnxHwID,
        tmnxHwClass
    }
    STATUS      obsolete
    DESCRIPTION
        "Generated when the secondary CPM fails to restore the config and
         state.

         This notification was made obsolete in the 2.1 release.

         It does not apply. This event was originally created for an early
         redundancy mechanism that was never released."
    ::= { tmnxChassisNotification 24 }

tmnxChassisNotificationClear     NOTIFICATION-TYPE
    OBJECTS     {
        tmnxChassisNotifyHwIndex,
        tmnxHwID,
        tmnxHwClass,
        tmnxChassisNotifyOID
    }
    STATUS      current
    DESCRIPTION
        "A trap indicating the clear of a chassis notification identified by
         tmnxChassisNotifyOID."
    ::= { tmnxChassisNotification 25 }

tmnxEqSyncIfTimingHoldover       NOTIFICATION-TYPE
    OBJECTS     {
        tmnxChassisNotifyHwIndex,
        tmnxHwID,
        tmnxHwClass
    }
    STATUS      current
    DESCRIPTION
        "Generated when the synchronous equipment timing subsystem transitions
         into a holdover state. This notification will have the same indices as
         those of the tmnxCpmCardTable."
    ::= { tmnxChassisNotification 26 }

tmnxEqSyncIfTimingHoldoverClear  NOTIFICATION-TYPE
    OBJECTS     {
        tmnxChassisNotifyHwIndex,
        tmnxHwID,
        tmnxHwClass
    }
    STATUS      current
    DESCRIPTION
        "[CAUSE] Generated when the synchronous equipment timing subsystem
         transitions out of the holdover state. This notification will have the
         same indices as those of the tmnxCpmCardTable.

         [EFFECT] Any node-timed ports will have very slow frequency drift
         limited by the central clock oscillator stability. The oscillator
         meets the holdover requirements of a Stratum 3 and G.813 Option 1
         clock.

         [RECOVERY] Address issues with the central clock input references."
    ::= { tmnxChassisNotification 27 }

tmnxEqSyncIfTimingRef1Alarm      NOTIFICATION-TYPE
    OBJECTS     {
        tmnxChassisNotifyHwIndex,
        tmnxHwID,
        tmnxHwClass,
        tmnxSyncIfTimingNotifyAlarm
    }
    STATUS      current
    DESCRIPTION
        "[CAUSE] Generated when an alarm condition on the first timing
         reference is detected. The type of alarm (los, oof, etc) is indicated
         in the details of the log event or alarm, and is also available in the
         tmnxSyncIfTimingNotifyAlarm attribute included in the SNMP
         notification. The SNMP notification will have the same indices as
         those of the tmnxCpmCardTable.

         [EFFECT] Indicated timing reference (1, 2, or BITS) cannot be used as
         a source of timing into the central clock.

         [RECOVERY] Address issues with the signal associated with indicated
         timing reference (1, 2, or BITS)."
    ::= { tmnxChassisNotification 28 }

tmnxEqSyncIfTimingRef1AlarmClear NOTIFICATION-TYPE
    OBJECTS     {
        tmnxChassisNotifyHwIndex,
        tmnxHwID,
        tmnxHwClass,
        tmnxSyncIfTimingNotifyAlarm
    }
    STATUS      current
    DESCRIPTION
        "Generated when an alarm condition on the first timing reference is
         cleared. This notification will have the same indices as those of the
         tmnxCpmCardTable."
    ::= { tmnxChassisNotification 29 }

tmnxEqSyncIfTimingRef2Alarm      NOTIFICATION-TYPE
    OBJECTS     {
        tmnxChassisNotifyHwIndex,
        tmnxHwID,
        tmnxHwClass,
        tmnxSyncIfTimingNotifyAlarm
    }
    STATUS      current
    DESCRIPTION
        "Generated when an alarm condition on the second timing reference is
         detected. This notification will have the same indices as those of the
         tmnxCpmCardTable."
    ::= { tmnxChassisNotification 30 }

tmnxEqSyncIfTimingRef2AlarmClear NOTIFICATION-TYPE
    OBJECTS     {
        tmnxChassisNotifyHwIndex,
        tmnxHwID,
        tmnxHwClass,
        tmnxSyncIfTimingNotifyAlarm
    }
    STATUS      current
    DESCRIPTION
        "Generated when an alarm condition on the second timing reference is
         cleared. This notification will have the same indices as those of the
         tmnxCpmCardTable."
    ::= { tmnxChassisNotification 31 }

tmnxEqFlashDataLoss              NOTIFICATION-TYPE
    OBJECTS     {
        tmnxChassisNotifyHwIndex,
        tmnxHwID,
        tmnxHwClass,
        tmnxHwOperState
    }
    STATUS      current
    DESCRIPTION
        "tmnxEqFlashDataLoss is generated when an error occurs while data was
         being written to the compact flash. This notification indicates a
         probable data loss."
    ::= { tmnxChassisNotification 32 }

tmnxEqFlashDiskFull              NOTIFICATION-TYPE
    OBJECTS     {
        tmnxChassisNotifyHwIndex,
        tmnxHwID,
        tmnxHwClass,
        tmnxHwOperState,
        tmnxChassisNotifyDiskFullReason
    }
    STATUS      current
    DESCRIPTION
        "tmnxEqFlashDiskFull is generated when there is no space left on the
         compact flash. No more data can be written to it."
    ::= { tmnxChassisNotification 33 }

tmnxPeSoftwareLoadFailed         NOTIFICATION-TYPE
    OBJECTS     {
        tmnxChassisNotifyHwIndex,
        tmnxHwID,
        tmnxHwClass,
        tmnxChassisNotifySoftwareLocation
    }
    STATUS      current
    DESCRIPTION
        "Generated when the CPM fails to load the software from a specified
         location. tmnxChassisNotifyHwIndex identifies the card for which the
         software load failed and tmnxChassisNotifySoftwareLocation contains
         the location from where the software load was attempted."
    ::= { tmnxChassisNotification 34 }

tmnxPeBootloaderVersionMismatch  NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between the CPM and boot loader
         versions. tmnxChassisNotifyHwIndex identifies the CPM card.
         tmnxChassisNotifyMismatchedVer contains the mismatched version of
         bootloader and tmnxHwSoftwareCodeVersion contains the expected version
         of the bootloader."
    ::= { tmnxChassisNotification 35 }

tmnxPeBootromVersionMismatch     NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between the boot rom versions.
         tmnxChassisNotifyHwIndex identifies the IOM card.
         tmnxChassisNotifyMismatchedVer contains the mismatched version of
         bootrom and tmnxHwSoftwareCodeVersion contains the expected version of
         the bootrom."
    ::= { tmnxChassisNotification 36 }

tmnxPeFPGAVersionMismatch        NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between the FPGA versions.
         tmnxChassisNotifyHwIndex identifies the IOM card.
         tmnxChassisNotifyMismatchedVer contains the mismatched version of FPGA
         and tmnxHwSoftwareCodeVersion contains the expected version of the
         FPGA."
    ::= { tmnxChassisNotification 37 }

tmnxEqSyncIfTimingBITSAlarm      NOTIFICATION-TYPE
    OBJECTS     {
        tmnxChassisNotifyHwIndex,
        tmnxHwID,
        tmnxHwClass,
        tmnxSyncIfTimingNotifyAlarm
    }
    STATUS      current
    DESCRIPTION
        "Generated when an alarm condition on the BITS timing reference is
         detected. This notification will have the same indices as those of the
         tmnxCpmCardTable."
    ::= { tmnxChassisNotification 38 }

tmnxEqSyncIfTimingBITSAlarmClear NOTIFICATION-TYPE
    OBJECTS     {
        tmnxChassisNotifyHwIndex,
        tmnxHwID,
        tmnxHwClass,
        tmnxSyncIfTimingNotifyAlarm
    }
    STATUS      current
    DESCRIPTION
        "Generated when an alarm condition on the BITS timing reference is
         cleared. This notification will have the same indices as those of the
         tmnxCpmCardTable."
    ::= { tmnxChassisNotification 39 }

tmnxEqCardFirmwareUpgraded       NOTIFICATION-TYPE
    OBJECTS     {
        tmnxChassisNotifyHwIndex,
        tmnxHwID,
        tmnxHwClass
    }
    STATUS      current
    DESCRIPTION
        "Generated when a card is hot-inserted into the chassis and its
         firmware is automatically upgraded.  The card type may be IOM or
         CPM module."
    ::= { tmnxChassisNotification 40 }

tmnxChassisUpgradeInProgress     NOTIFICATION-TYPE
    OBJECTS     {
        tmnxChassisNotifyHwIndex,
        tmnxHwID,
        tmnxHwClass
    }
    STATUS      current
    DESCRIPTION
        "[CAUSE] The tmnxChassisUpgradeInProgress notification is generated
         only after a CPM switchover occurs and the new active CPM is running
         new software, while the IOMs or XCMs are still running old software.
         This is the start of the upgrade process. The
         tmnxChassisUpgradeInProgress notification will continue to be
         generated every 30 minutes while at least one IOM is still running
         older software.

         [EFFECT] A software mismatch between the CPM and IOM or XCM is
         generally fine for a short duration (during an upgrade) but may not
         allow for correct long term operation.

         [RECOVERY] Complete the upgrade of all IOMs or XCMs."
    ::= { tmnxChassisNotification 41 }

tmnxChassisUpgradeComplete       NOTIFICATION-TYPE
    OBJECTS     {
        tmnxChassisNotifyHwIndex,
        tmnxHwID,
        tmnxHwClass
    }
    STATUS      current
    DESCRIPTION
        "The tmnxChassisUpgradeComplete notification is generated to indicate
         that all the IOMs are running matching software versions in reference
         to the active CPM software version changed as part of the upgrade
         process."
    ::= { tmnxChassisNotification 42 }

tmnxChassisHiBwMcastAlarm        NOTIFICATION-TYPE
    OBJECTS     {
        tmnxChassisNotifyHwIndex,
        tmnxHwID,
        tmnxHwClass
    }
    STATUS      current
    DESCRIPTION
        "The tmnxChassisHiBwMcastAlarm notification is generated when a plane
         is  shared by more than one high bandwidth multicast tap."
    ::= { tmnxChassisNotification 43 }

tmnxEqMdaCfgNotCompatible        NOTIFICATION-TYPE
    OBJECTS     {
        tmnxChassisNotifyHwIndex,
        tmnxHwID,
        tmnxHwClass,
        tmnxMdaNotifyType
    }
    STATUS      current
    DESCRIPTION
        "Generated when a supported MDA is inserted into a slot of an IOM, the
         MDA is compatible with the currently provisioned MDA, but the current
         configuration on the MDA's ports is not compatible with the inserted
         MDA.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxChassisNotification 44 }

tmnxCpmCardSyncFileNotPresent    NOTIFICATION-TYPE
    OBJECTS     {
        tmnxChassisNotifyHwIndex,
        tmnxHwID,
        tmnxHwClass,
        tmnxChassisNotifyCardSyncFile
    }
    STATUS      current
    DESCRIPTION
        "The tmnxCpmCardSyncFileNotPresent notification is generated when the
         redundancy file synchronization failed to locate an optional file."
    ::= { tmnxChassisNotification 45 }

tmnxEqMdaXplError                NOTIFICATION-TYPE
    OBJECTS     {
        tmnxMDAXplFailedCount
    }
    STATUS      current
    DESCRIPTION
        "[CAUSE] The tmnxEqMdaXplError notification is generated when an MDA
         exhibits persistent egress XPL errors, and the tmnxEqMdaIngrXplError
         notification is generated when ingress XPL errors occur.

         [EFFECT] Contact Nokia customer support.

         [RECOVERY] Contact Nokia customer support."
    ::= { tmnxChassisNotification 46 }

tmnxEqCardPChipError             NOTIFICATION-TYPE
    OBJECTS     {
        tmnxChassisNotifyHwIndex,
        tmnxHwID,
        tmnxHwClass,
        tmnxCardComplexNumber,
        tmnxCardFwdDirection,
        tmnxCardSrcSlotBitmap
    }
    STATUS      current
    DESCRIPTION
        "The tmnxEqCardPChipError notification is generated when persistent FCS
         errors are detected by the P chip in either the ingress or egress
         datapath/complex.  The value tmnxCardSrcSlotBitmap is only used for the
         egress datapath/complex direction."
    ::= { tmnxChassisNotification 47 }

tmnxEqCardSoftResetAlarm         NOTIFICATION-TYPE
    OBJECTS     {
        tmnxChassisNotifyHwIndex,
        tmnxHwID,
        tmnxHwClass,
        tmnxCardSoftResetState
    }
    STATUS      current
    DESCRIPTION
        "The tmnxEqCardSoftResetAlarm notification is generated when an IOM
         card enters and exits the 'soft-reset' state."
    ::= { tmnxChassisNotification 48 }

tmnxEqMdaSyncENotCompatible      NOTIFICATION-TYPE
    OBJECTS     {
        tmnxChassisNotifyHwIndex,
        tmnxHwID,
        tmnxHwClass,
        tmnxMdaNotifyType
    }
    STATUS      current
    DESCRIPTION
        "The tmnxEqMdaSyncENotCompatible notification is generated when an MDA
         card is inserted into a slot of an IOM. The MDA is compatible with the
         currently provisioned MDA, but the currently configured synchronous
         ethernet, tmnxMDASynchronousEthernet, is not compatible with the
         inserted MDA.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxChassisNotification 49 }

tmnxIPsecIsaGrpActiveIsaChgd     NOTIFICATION-TYPE
    OBJECTS     {
        tmnxIPsecIsaGrpPrimaryIsa,
        tmnxIPsecIsaGrpBackupIsa,
        tmnxIPsecIsaGrpActiveIsa
    }
    STATUS      current
    DESCRIPTION
        "The tmnxIPsecIsaGrpActiveIsaChgd notification is generated when a
         change in the active ISA (Integrated Service Adaptor) occurs in an
         IPsec ISA module group."
    ::= { tmnxChassisNotification 50 }

tmnxEqCardPChipMemoryEvent       NOTIFICATION-TYPE
    OBJECTS     {
        tmnxChassisNotifyHwIndex,
        tmnxHwID,
        tmnxHwClass,
        tmnxCardComplexNumber
    }
    STATUS      current
    DESCRIPTION
        "The tmnxEqCardPChipMemoryEvent notification is generated when a P-chip
         experiences an occurrence of a memory error."
    ::= { tmnxChassisNotification 51 }

tmnxIPsecIsaGrpUnableToSwitch    NOTIFICATION-TYPE
    OBJECTS     {
        tmnxIPsecIsaGrpActiveIsa
    }
    STATUS      current
    DESCRIPTION
        "The tmnxIPsecIsaGrpUnableToSwitch notification is generated when an
         IPsec ISA (Integrated Service Adaptor) module group is unable to
         switch due to lack of resources.

         In such an event the IPsec ISA group is left without an active MDA and
         the tmnxIPsecIsaGrpOperState is set to 'outOfService'.

         Recovery is possible by releasing resources, and setting the
         tmnxIPsecIsaGrpAdminState object to 'outOfService' followed by a reset
         to 'inService' to bring up the ISA group."
    ::= { tmnxChassisNotification 52 }

tmnxIPsecIsaGrpTnlLowWMark       NOTIFICATION-TYPE
    OBJECTS     {
        tmnxIPsecIsaGrpTunnels,
        tmnxIPsecIsaGrpMaxTunnels
    }
    STATUS      current
    DESCRIPTION
        "The tmnxIPsecIsaGrpTnlLowWMark notification is generated when number
         of tunnels for an IPsec ISA (Integrated Service Adaptor) module has
         dropped to the low watermark which is 90% of the
         tmnxIPsecIsaGrpMaxTunnels."
    ::= { tmnxChassisNotification 53 }

tmnxIPsecIsaGrpTnlHighWMark      NOTIFICATION-TYPE
    OBJECTS     {
        tmnxIPsecIsaGrpTunnels,
        tmnxIPsecIsaGrpMaxTunnels
    }
    STATUS      current
    DESCRIPTION
        "The tmnxIPsecIsaGrpTnlHighWMark notification is generated when number
         of tunnels for an IPsec ISA (Integrated Service Adaptor) module has
         reached to the high watermark which is 95% of the
         tmnxIPsecIsaGrpMaxTunnels."
    ::= { tmnxChassisNotification 54 }

tmnxIPsecIsaGrpTnlMax            NOTIFICATION-TYPE
    OBJECTS     {
        tmnxIPsecIsaGrpTunnels,
        tmnxIPsecIsaGrpMaxTunnels
    }
    STATUS      current
    DESCRIPTION
        "The tmnxIPsecIsaGrpTnlMax notification is generated when number of
         tunnels for an IPsec ISA (Integrated Service Adaptor) module has
         reached the maximum of the tmnxIPsecIsaGrpMaxTunnels."
    ::= { tmnxChassisNotification 55 }

tmnxEqSyncIfTimingRef1Quality    NOTIFICATION-TYPE
    OBJECTS     {
        tmnxSyncIfTimingRef1RxQltyLevel
    }
    STATUS      current
    DESCRIPTION
        "Generated when there is a change of the received quality level on
         timing reference 1."
    ::= { tmnxChassisNotification 56 }

tmnxEqSyncIfTimingRef2Quality    NOTIFICATION-TYPE
    OBJECTS     {
        tmnxSyncIfTimingRef2RxQltyLevel
    }
    STATUS      current
    DESCRIPTION
        "Generated when there is a change of the received quality level on
         timing reference 2."
    ::= { tmnxChassisNotification 57 }

tmnxEqSyncIfTimingBITSQuality    NOTIFICATION-TYPE
    OBJECTS     {
        tmnxSyncIfTimingBITSRxQltyLevel
    }
    STATUS      current
    DESCRIPTION
        "Generated when there is a change of the received quality level on the
         bits interface."
    ::= { tmnxChassisNotification 58 }

tmnxEqSyncIfTimingBITS2Quality   NOTIFICATION-TYPE
    OBJECTS     {
        tmnxSyncIfTimingBITS2RxQltyLevel
    }
    STATUS      current
    DESCRIPTION
        "Generated when there is a change of the received quality level on the
         second bits interface."
    ::= { tmnxChassisNotification 59 }

tmnxEqSyncIfTimingRefSwitch      NOTIFICATION-TYPE
    OBJECTS     {
        tmnxSyncIfTimingRef1InUse,
        tmnxSyncIfTimingRef2InUse,
        tmnxSyncIfTimingBITSInUse,
        tmnxSyncIfTimingBITS2InUse,
        tmnxSyncIfTimingPTPInUse,
        tmnxSyncIfTimingSyncEInUse,
        tmnxSyncIfTimingSyncE2InUse,
        tmnxSyncIfTimingGnssInUse,
        tmnxSyncIfTimingGnss2InUse
    }
    STATUS      current
    DESCRIPTION
        "Generated when there is a change of which timing reference is
         providing timing for the system."
    ::= { tmnxChassisNotification 60 }

tmnxEqSyncIfTimingBITS2Alarm     NOTIFICATION-TYPE
    OBJECTS     {
        tmnxChassisNotifyHwIndex,
        tmnxHwID,
        tmnxHwClass,
        tmnxSyncIfTimingNotifyAlarm
    }
    STATUS      current
    DESCRIPTION
        "Generated when an alarm condition on the BITS 2 timing reference is
         detected. This notification will have the same indices as those of the
         tmnxCpmCardTable."
    ::= { tmnxChassisNotification 61 }

tmnxEqSyncIfTimingBITS2AlarmClr  NOTIFICATION-TYPE
    OBJECTS     {
        tmnxChassisNotifyHwIndex,
        tmnxHwID,
        tmnxHwClass,
        tmnxSyncIfTimingNotifyAlarm
    }
    STATUS      current
    DESCRIPTION
        "Generated when an alarm condition on the BITS 2 timing reference is
         cleared. This notification will have the same indices as those of the
         tmnxCpmCardTable."
    ::= { tmnxChassisNotification 62 }

tmnxEqSyncIfTimingBITSOutRefChg  NOTIFICATION-TYPE
    OBJECTS     {
        tmnxSyncIfTimingBITSOutRefSel
    }
    STATUS      current
    DESCRIPTION
        "Generated when the BITS Out timing reference selection changes."
    ::= { tmnxChassisNotification 63 }

tmnxEqCardPChipCamEvent          NOTIFICATION-TYPE
    OBJECTS     {
        tmnxChassisNotifyHwIndex,
        tmnxHwID,
        tmnxHwClass,
        tmnxCardComplexNumber
    }
    STATUS      current
    DESCRIPTION
        "[CAUSE] The tmnxEqCardPChipCamEvent notification is generated when
         either an IOM or a CPM experiences a persistent occurrence of a PChip
         CAM error. On a CPM card, the tmnxCardComplexNumber will be fixed to
         the value zero (0).

         [EFFECT] Contact Nokia customer support.

         [RECOVERY] Contact Nokia customer support."
    ::= { tmnxChassisNotification 64 }

tmnxEqSyncIfTimingSystemQuality  NOTIFICATION-TYPE
    OBJECTS     {
        tmnxSyncIfTimingSystemQltyLevel
    }
    STATUS      current
    DESCRIPTION
        "The tmnxEqSyncIfTimingSystemQuality notification is generated when
         there is a change in the system timing quality level. This
         notification is a point-in-time state change event.

         [CAUSE] This notification may be triggered for the following reasons:

         1) There has been a switch in the timing reference in use by the
            network element, either because the previously active timing
            reference was disqualified, or to ensure that the network element
            is using the timing reference with the best timing quality.
         2) There has been a change in the active timing reference's quality
            and the change does not result in a timing reference switch.
         3) The network element has transitioned into or out of the holdover
            state.

         [EFFECT] The system quality level is used to determine the SSM code
         transmitted on synchronous interfaces. This may affect the SSM code
         transmitted on some or all interfaces, which may affect the
         distribution of timing throughout the network.

         [RECOVERY] If the customer is expecting the system to be locked to a
         reference of a particular quality and the system quality has
         decreased, the customer will need to determine the root cause (for
         example, loss of communication with a satellite) and resolve the
         issue."
    ::= { tmnxChassisNotification 65 }

tmnxEqHwEnhancedCapability       NOTIFICATION-TYPE
    OBJECTS     {
        tmnxChassisNotifyHwIndex,
        tmnxHwID,
        tmnxHwClass
    }
    STATUS      current
    DESCRIPTION
        "The tmnxEqHwEnhancedCapability notification is generated when the
         hardware, specified by the supplied objects, consists of enhanced
         capabilities as compared to the active hardware.

         [EFFECT] The system behaves normally under this situation, however,
         switching to the newer hardware will put the system in an incompatible
         state with the currently active hardware. That is, once this device
         takes activity, the lesser capable hardware will fail to communicate
         with it.

         In this mode, the system is deemed to be in a 'one-way upgrade'
         scenario.

         [RECOVERY] Two modes of recovery exist for this notification:
            1. Remove the enhanced hardware, and supply a more compatible
               device (status quo) with the active hardware.
            2. Switch to the enhanced device, and replace the older hardware
               with a similarly enhanced device (upgrade)."
    ::= { tmnxChassisNotification 66 }

tmnxEqSyncIfTimingPTPQuality     NOTIFICATION-TYPE
    OBJECTS     {
        tmnxSyncIfTimingPTPRxQltyLevel
    }
    STATUS      current
    DESCRIPTION
        "Generated when there is a change of the received quality level on the
         Precision Timing Protocol (PTP)."
    ::= { tmnxChassisNotification 67 }

tmnxEqSyncIfTimingPTPAlarm       NOTIFICATION-TYPE
    OBJECTS     {
        tmnxChassisNotifyHwIndex,
        tmnxHwID,
        tmnxHwClass,
        tmnxSyncIfTimingNotifyAlarm
    }
    STATUS      current
    DESCRIPTION
        "Generated when an alarm condition on the Precision Timing Protocol
         (PTP) timing reference is detected. This notification will have the
         same indices as those of the tmnxCpmCardTable."
    ::= { tmnxChassisNotification 68 }

tmnxEqSyncIfTimingPTPAlarmClear  NOTIFICATION-TYPE
    OBJECTS     {
        tmnxChassisNotifyHwIndex,
        tmnxHwID,
        tmnxHwClass,
        tmnxSyncIfTimingNotifyAlarm
    }
    STATUS      current
    DESCRIPTION
        "Generated when an alarm condition on the Precision Timing Protocol
         (PTP) timing reference is cleared. This notification will have the
         same indices as those of the tmnxCpmCardTable."
    ::= { tmnxChassisNotification 69 }

tmnxPeFirmwareVersionWarning     NOTIFICATION-TYPE
    OBJECTS     {
        tmnxChassisNotifyHwIndex,
        tmnxHwID,
        tmnxHwClass,
        tmnxHwFirmwareCodeVersion
    }
    STATUS      current
    DESCRIPTION
        "Generated when a card is running compatible yet older firmware
         than the firmware associated with the current software release.
         tmnxChassisNotifyHwIndex identifies the card.  The
         tmnxHwFirmwareCodeVersion object will contain the programmed
         the firmware version."
    ::= { tmnxChassisNotification 70 }

tmnxMDAIsaTunnelGroupChange      NOTIFICATION-TYPE
    OBJECTS     {
        tmnxMDAIsaTunnelGroupInUse,
        tmnxMDAIsaTunnelGroup
    }
    STATUS      current
    DESCRIPTION
        "[CAUSE] The tmnxMDAIsaTunnelGroupChange notification is generated when
         IPsec ISA (Integrated Service Adaptor) tunnel-group in-use for the MDA
         changes value.

         [EFFECT] There is no operational impact due to this event.

         [RECOVERY] None required."
    ::= { tmnxChassisNotification 71 }

tmnxDcpCardFpEventOvrflw         NOTIFICATION-TYPE
    OBJECTS     {
        tmnxChassisNotifyChassisId,
        tmnxChassisNotifyCardSlotNum,
        tmnxDcpTimeEventOccured
    }
    STATUS      current
    DESCRIPTION
        "[CAUSE] The tmnxDcpCardFpEventOvrflw notification is generated when a
         flood of distributed CPU FP protection events occur on a particular
         card and some of the events are lost due to event throttling
         mechanism.

         [EFFECT] Some FP notifications configured on the card may not be
         received.

         [RECOVERY] Notifications will resume once the event throttling ends."
    ::= { tmnxChassisNotification 72 }

tmnxDcpCardSapEventOvrflw        NOTIFICATION-TYPE
    OBJECTS     {
        tmnxChassisNotifyChassisId,
        tmnxChassisNotifyCardSlotNum,
        tmnxDcpTimeEventOccured
    }
    STATUS      current
    DESCRIPTION
        "[CAUSE] The tmnxDcpCardSapEventOvrflw notification is generated when a
         flood of distributed CPU protection SAP events occur on a particular
         card and some of the events are lost due to event throttling
         mechanism.

         [EFFECT] Some SAP notifications configured on the card may not be
         received.

         [RECOVERY] Notifications will resume once the event throttling ends."
    ::= { tmnxChassisNotification 73 }

tmnxDcpCardVrtrIfEventOvrflw     NOTIFICATION-TYPE
    OBJECTS     {
        tmnxChassisNotifyChassisId,
        tmnxChassisNotifyCardSlotNum,
        tmnxDcpTimeEventOccured
    }
    STATUS      current
    DESCRIPTION
        "[CAUSE] The tmnxDcpCardVrtrIfEventOvrflw notification is generated
         when a flood of distributed CPU protection network-interface events
         occur on a particular card and some of the events are lost due to
         event throttling mechanism.

         [EFFECT] Some network-interface notifications configured on the card
         may not be received.

         [RECOVERY] Notifications will resume once the event throttling ends."
    ::= { tmnxChassisNotification 74 }

tmnxDcpFpDynPoolUsageHiAlmRaise  NOTIFICATION-TYPE
    OBJECTS     {
        tmnxFPDCpuProtDynEnfrcPlcrPool,
        tmnxDcpTimeEventOccured
    }
    STATUS      current
    DESCRIPTION
        "[CAUSE] The tmnxDcpFpDynPoolUsageHiAlmRaise notification is generated
         when the dynamic enforcement policer pool usage on the forwarding
         plane is nearly exhausted.

         [EFFECT] Dynamic enforcement policers may not get allocated on the
         forwarding plane.

         [RECOVERY] This notification will be cleared when either the dynamic
         enforcement policer pool is increased or the usage drops."
    ::= { tmnxChassisNotification 75 }

tmnxDcpFpDynPoolUsageHiAlmClear  NOTIFICATION-TYPE
    OBJECTS     {
        tmnxFPDCpuProtDynEnfrcPlcrPool,
        tmnxDcpTimeEventOccured
    }
    STATUS      current
    DESCRIPTION
        "[CAUSE] The tmnxDcpFpDynPoolUsageHiAlmClear notification is generated
         when the dynamic enforcement policer pool usage on the forwarding
         plane is no longer exhausted.

         [EFFECT] Dynamic enforcement policers are available in the free pool
         to be allocated when needed.

         [RECOVERY] There is no recovery required for this notification."
    ::= { tmnxChassisNotification 76 }

tmnxDcpCardFpEventOvrflwClr      NOTIFICATION-TYPE
    OBJECTS     {
        tmnxChassisNotifyChassisId,
        tmnxChassisNotifyCardSlotNum,
        tmnxDcpTimeEventOccured,
        tmnxDcpMissingNotificationCount
    }
    STATUS      current
    DESCRIPTION
        "[CAUSE] The tmnxDcpCardFpEventOvrflwClr notification is generated when
         the event throttling has ended for distributed CPU protection FP
         events on a particular card.

         [EFFECT] Notifications are received again since the event throttling
         has ended.

         [RECOVERY] There is no recovery for this notification."
    ::= { tmnxChassisNotification 77 }

tmnxDcpCardSapEventOvrflwClr     NOTIFICATION-TYPE
    OBJECTS     {
        tmnxChassisNotifyChassisId,
        tmnxChassisNotifyCardSlotNum,
        tmnxDcpTimeEventOccured,
        tmnxDcpMissingNotificationCount
    }
    STATUS      current
    DESCRIPTION
        "[CAUSE] The tmnxDcpCardSapEventOvrflwClr notification is generated
         when the event throttling has ended for distributed CPU protection SAP
         events on a particular card.

         [EFFECT] Notifications are received again since the event throttling
         has ended.

         [RECOVERY] There is no recovery for this notification."
    ::= { tmnxChassisNotification 78 }

tmnxDcpCardVrtrIfEventOvrflwClr  NOTIFICATION-TYPE
    OBJECTS     {
        tmnxChassisNotifyChassisId,
        tmnxChassisNotifyCardSlotNum,
        tmnxDcpTimeEventOccured,
        tmnxDcpMissingNotificationCount
    }
    STATUS      current
    DESCRIPTION
        "[CAUSE] The tmnxDcpCardVrtrIfEventOvrflwClr notification is generated
         when the event throttling has ended for distributed CPU protection
         network-interface events on a particular card.

         [EFFECT] Notifications are received again since the event throttling
         has ended.

         [RECOVERY] There is no recovery for this notification."
    ::= { tmnxChassisNotification 79 }

tmnxEqPowerCapacityExceeded      NOTIFICATION-TYPE
    OBJECTS     {
        tmnxChassisNotifyChassisId,
        tmnxChassisNotifyPowerZone,
        tmnxChassisNotifyPowerCapacity
    }
    STATUS      current
    DESCRIPTION
        "[CAUSE] The tmnxEqPowerCapacityExceeded alarm is generated when a
         device needs power to boot, but there is not enough power capacity to
         support the device.

         [EFFECT] A non-powered device will not boot until the power capacity
         is increased to support the device.

         [RECOVERY] Add a new power supply to the system or change the faulty
         power supply for a working one."
    ::= { tmnxChassisNotification 80 }

tmnxEqPowerCapacityExceededClear NOTIFICATION-TYPE
    OBJECTS     {
        tmnxChassisNotifyChassisId,
        tmnxChassisNotifyPowerZone
    }
    STATUS      current
    DESCRIPTION
        "[CAUSE] The tmnxEqPowerCapacityExceededClear notification is generated
         when the available power capacity exceeds the required power to boot
         all inserted devices.

         [EFFECT] Devices that failed to boot due to power constrains, power
         up."
    ::= { tmnxChassisNotification 81 }

tmnxEqPowerLostCapacity          NOTIFICATION-TYPE
    OBJECTS     {
        tmnxChassisNotifyChassisId,
        tmnxChassisNotifyPowerZone,
        tmnxChassisNotifyPowerCapacity
    }
    STATUS      current
    DESCRIPTION
        "[CAUSE] The tmnxEqPowerLostCapacity alarm is generated when a power
         supply fails or is removed which puts the system in an overloaded
         situation.

         [EFFECT] Devices are powered off in order of lowest power priority
         (tmnxMDAHwPowerPriority) until the available power capacity can
         support the powered devices.

         [RECOVERY] Add a new power supply to the system or change the faulty
         power supply for a working one."
    ::= { tmnxChassisNotification 82 }

tmnxEqPowerLostCapacityClear     NOTIFICATION-TYPE
    OBJECTS     {
        tmnxChassisNotifyChassisId,
        tmnxChassisNotifyPowerZone
    }
    STATUS      current
    DESCRIPTION
        "[CAUSE] The tmnxEqPowerLostCapacityClear notification is generated
         when the available power capacity exceeds the required power to boot
         all inserted devices.

         [EFFECT] Devices that powered off due to power constrains, power up."
    ::= { tmnxChassisNotification 83 }

tmnxEqPowerOverloadState         NOTIFICATION-TYPE
    OBJECTS     {
        tmnxChassisNotifyChassisId,
        tmnxChassisNotifyPowerZone,
        tmnxChassisNotifyPowerCapacity
    }
    STATUS      current
    DESCRIPTION
        "[CAUSE] The tmnxEqPowerOverloadState alarm is generated when the
         overloaded power capacity cannot support the power requirements and
         there are no further devices that can be powered off.

         [EFFECT] The system runs a risk of experiencing brownouts while the
         available power capacity does not meet the required power consumption.

         [RECOVERY] Add power capacity or manually shut down devices until the
         power capacity meets the power needs."
    ::= { tmnxChassisNotification 84 }

tmnxEqPowerOverloadStateClear    NOTIFICATION-TYPE
    OBJECTS     {
        tmnxChassisNotifyChassisId,
        tmnxChassisNotifyPowerZone
    }
    STATUS      current
    DESCRIPTION
        "[CAUSE] The tmnxEqPowerOverloadStateClear notification is generated
         when the available power capacity meets or exceeds the power needs of
         the powered on devices."
    ::= { tmnxChassisNotification 85 }

tmnxEqCardQChipBufMemoryEvent    NOTIFICATION-TYPE
    OBJECTS     {
        tmnxHwID,
        tmnxHwClass,
        tmnxCardComplexNumber
    }
    STATUS      current
    DESCRIPTION
        "[CAUSE] The tmnxEqCardQChipBufMemoryEvent notification is generated
         when a Q-chip experiences an occurrence of a buffer memory error.

         [EFFECT] Contact Nokia customer support.

         [RECOVERY] Contact Nokia customer support."
    ::= { tmnxChassisNotification 86 }

tmnxEqCardQChipStatsMemoryEvent  NOTIFICATION-TYPE
    OBJECTS     {
        tmnxHwID,
        tmnxHwClass,
        tmnxCardComplexNumber
    }
    STATUS      current
    DESCRIPTION
        "[CAUSE] The tmnxEqCardQChipStatsMemoryEvent notification is generated
         when a Q-chip experiences an occurrence of a statistics memory error.

         [EFFECT] Contact Nokia customer support.

         [RECOVERY] Contact Nokia customer support."
    ::= { tmnxChassisNotification 87 }

tmnxEqCardQChipIntMemoryEvent    NOTIFICATION-TYPE
    OBJECTS     {
        tmnxHwID,
        tmnxHwClass,
        tmnxCardComplexNumber
    }
    STATUS      current
    DESCRIPTION
        "[CAUSE] The tmnxEqCardQChipIntMemoryEvent notification is generated
         when a Q-chip experiences an occurrence of an internal memory error.

         [EFFECT] Contact Nokia customer support.

         [RECOVERY] Contact Nokia customer support."
    ::= { tmnxChassisNotification 88 }

tmnxEqCardChipIfDownEvent        NOTIFICATION-TYPE
    OBJECTS     {
        tmnxHwID,
        tmnxHwClass,
        tmnxCardComplexNumber
    }
    STATUS      current
    DESCRIPTION
        "[CAUSE] The tmnxEqCardChipIfDownEvent notification is generated when
         an inter-chip interface (XPL2 bundle) experiences an internal datapath
         problem.

         [EFFECT] 7750 SR/7450 ESS: The IOM or IMM will either remain
         operational or the card will reset along with its associated MDAs.
         7950 XRS: The associated XMA (MDA CLI context) will either remain
         operational or it will reset. The XCM (CLI card context) will not
         reset.

         [RECOVERY] Contact Nokia customer support."
    ::= { tmnxChassisNotification 89 }

tmnxEqCardChipIfCellEvent        NOTIFICATION-TYPE
    OBJECTS     {
        tmnxHwID,
        tmnxHwClass,
        tmnxCardComplexNumber
    }
    STATUS      current
    DESCRIPTION
        "[CAUSE] The tmnxEqCardChipIfCellEvent notification is generated when
         an inter-chip interface (XPL2 bundle) experiences internal datapath
         cell errors.

         [EFFECT] Contact Nokia customer support.

         [RECOVERY] Contact Nokia customer support."
    ::= { tmnxChassisNotification 90 }

tmnxEqLowSwitchFabricCap         NOTIFICATION-TYPE
    OBJECTS     {
        tmnxHwClass
    }
    STATUS      current
    DESCRIPTION
        "[CAUSE] The tmnxEqLowSwitchFabricCap alarm is generated when the total
         switch fabric capacity becomes less than the IOM capacity due to link
         failures. At least one of the taps on the IOM is below 100% capacity.

         [EFFECT] There is diminished switch fabric capacity to forward
         service-impacting information.

         [RECOVERY] If the system does not self-recover, the IOM must be
         rebooted."
    ::= { tmnxChassisNotification 91 }

tmnxEqLowSwitchFabricCapClear    NOTIFICATION-TYPE
    OBJECTS     {
        tmnxHwClass
    }
    STATUS      current
    DESCRIPTION
        "[CAUSE] The tmnxEqLowSwitchFabricCapClear notification is generated
         when the link failures that resulted in the tmnxEqLowSwitchFabricCap
         alarm to be raised have been resolved.

         [EFFECT] There is sufficient switch fabric capacity to forward
         service-impacting information."
    ::= { tmnxChassisNotification 92 }

tmnxEqPowerSafetyAlertThreshold  NOTIFICATION-TYPE
    OBJECTS     {
        tmnxChassisPwrMgmtSafetyAlert
    }
    STATUS      current
    DESCRIPTION
        "[CAUSE] The tmnxEqPowerSafetyAlertThreshold notification is generated
         when the system power capacity drops below the configured safety alert
         threshold.

         [EFFECT] This event is for notification only."
    ::= { tmnxChassisNotification 93 }

tmnxEqPowerSafetyAlertClear      NOTIFICATION-TYPE
    OBJECTS     {
        tmnxChassisPwrMgmtSafetyAlert
    }
    STATUS      current
    DESCRIPTION
        "[CAUSE] The tmnxEqPowerSafetyAlertClear notification is generated when
         the system power capacity meets or exceeds the configured safety alert
         threshold.

         [EFFECT] This event is for notification only."
    ::= { tmnxChassisNotification 94 }

tmnxEqPowerSafetyLevelThreshold  NOTIFICATION-TYPE
    OBJECTS     {
        tmnxChassisPwrMgmtSafetyLevel
    }
    STATUS      current
    DESCRIPTION
        "[CAUSE] The tmnxEqPowerSafetyLevelThreshold notification is generated
         when the peak nodal power consumption exceeds the configured safety
         level threshold.

         [EFFECT] This event is for notification only."
    ::= { tmnxChassisNotification 95 }

tmnxEqPowerSafetyLevelClear      NOTIFICATION-TYPE
    OBJECTS     {
        tmnxChassisPwrMgmtSafetyLevel
    }
    STATUS      current
    DESCRIPTION
        "[CAUSE] The tmnxEqPowerSafetyLevelClear notification is generated when
         the peak nodal power consumption drops below the configured safety
         level threshold.

         [EFFECT] This event is for notification only."
    ::= { tmnxChassisNotification 96 }

tmnxEqCardTChipParityEvent       NOTIFICATION-TYPE
    OBJECTS     {
        tmnxHwID,
        tmnxHwClass,
        tmnxCardComplexNumber
    }
    STATUS      current
    DESCRIPTION
        "[CAUSE] The tmnxEqCardTChipParityEvent notification is generated when
         a T-chip experiences an occurrence of an internal memory error.

         [EFFECT] Contact Nokia customer support.

         [RECOVERY] Contact Nokia customer support."
    ::= { tmnxChassisNotification 97 }

tmnxEqPowerSupplyPemACRectAlm    NOTIFICATION-TYPE
    OBJECTS     {
        tmnxHwClass,
        tmnxChassisPowerSupplyPemACRect
    }
    STATUS      obsolete
    DESCRIPTION
        "[CAUSE] The tmnxEqPowerSupplyPemACRectAlm alarm is generated if any
         one of the AC rectifiers for a given power supply is in a failed state
         or is missing.

         [EFFECT] There is an increased risk of the power supply failing,
         causing insufficient power to the system.

         [RECOVERY] Bring the AC rectifiers back online.

         This notification was made obsolete in release 15.0."
    ::= { tmnxChassisNotification 98 }

tmnxEqPowerSupplyPemACRectAlmClr NOTIFICATION-TYPE
    OBJECTS     {
        tmnxHwClass
    }
    STATUS      obsolete
    DESCRIPTION
        "[CAUSE] The tmnxEqPowerSupplyPemACRectAlmClr notification is generated
         when the last of the failed or missing AC rectifiers has been brought
         back online.

         [EFFECT] The power supply AC rectifiers are fully operational.

         This notification was made obsolete in release 15.0."
    ::= { tmnxChassisNotification 99 }

tmnxEqPowerSupplyInputFeedAlm    NOTIFICATION-TYPE
    OBJECTS     {
        tmnxHwClass,
        tmnxChassisPowerSupplyInFeedDown
    }
    STATUS      obsolete
    DESCRIPTION
        "[CAUSE] The tmnxEqPowerSupplyInputFeedAlm alarm is generated if any
         one of the input feeds for a given power supply is not supplying
         power.

         [EFFECT] There is an increased risk of system power brownouts or
         blackouts.

         [RECOVERY] Restore all of the input feeds that are not supplying
         power.

         This notification was made obsolete in release 15.0."
    ::= { tmnxChassisNotification 100 }

tmnxEqPowerSupplyInputFeedAlmClr NOTIFICATION-TYPE
    OBJECTS     {
        tmnxHwClass
    }
    STATUS      obsolete
    DESCRIPTION
        "[CAUSE] The tmnxEqPowerSupplyInputFeedAlmClr notification is generated
         when the last of the missing input feeds has been brought back online.

         [EFFECT] All power supply input feeds are supplying power.

         This notification was made obsolete in release 15.0."
    ::= { tmnxChassisNotification 101 }

tmnxEqProvPowerCapacityAlm       NOTIFICATION-TYPE
    OBJECTS     {
        tmnxHwClass,
        tmnxHwPowerZone,
        tmnxChassisNotifyPowerCapacity
    }
    STATUS      current
    DESCRIPTION
        "[CAUSE] The tmnxEqProvPowerCapacityAlm notification is generated if a
         power zone's provisioned power capacity can no longer support
         configured devices.

         [EFFECT] There is an increased risk of device power outages that may
         be service affecting.

         [RECOVERY] Increase the provisioned power capacity."
    ::= { tmnxChassisNotification 102 }

tmnxEqProvPowerCapacityAlmClr    NOTIFICATION-TYPE
    OBJECTS     {
        tmnxHwClass,
        tmnxHwPowerZone
    }
    STATUS      current
    DESCRIPTION
        "[CAUSE] The tmnxEqProvPowerCapacityAlmClr notification is generated
         when the power zone's provisioned power capacity can support
         configured devices.

         [EFFECT] All configured devices in the power zone have enough
         provisioned power capacity."
    ::= { tmnxChassisNotification 103 }

tmnxPlcyAcctStatsPoolExcResource NOTIFICATION-TYPE
    OBJECTS     {
        tmnxFPPlcyAcctStatsPool,
        tmnxFPPlcyAcctStatsInUse
    }
    STATUS      current
    DESCRIPTION
        "[CAUSE] The tmnxPlcyAcctStatsPoolExcResource notification is generated
         when the number of in-use stats resource usage as specified by
         tmnxFPPlcyAcctStatsInUse exceeds 95 percent of the stats pool limit as
         specified by tmnxFPPlcyAcctStatsPool.

         [EFFECT] The affected device may not provide accurate and complete
         statistics.

         [RECOVERY] There is no recovery required for this notification."
    ::= { tmnxChassisNotification 104 }

tmnxPlcyAcctStatsPoolLowResource NOTIFICATION-TYPE
    OBJECTS     {
        tmnxFPPlcyAcctStatsPool,
        tmnxFPPlcyAcctStatsInUse
    }
    STATUS      current
    DESCRIPTION
        "[CAUSE] The tmnxPlcyAcctStatsPoolLowResource notification is generated
         when the number of in-use stats resource as specified by
         tmnxFPPlcyAcctStatsInUse is below 85 percent of the stats pool limit
         as specified by tmnxFPPlcyAcctStatsPool.

         [EFFECT] The configured stats pool limit is cleared when the number of
         in-use stats resources falls below 85 percent of the stats pool limit.

         [RECOVERY] There is no recovery required for this notification."
    ::= { tmnxChassisNotification 105 }

tmnxPlcyAcctStatsEventOvrflwClr  NOTIFICATION-TYPE
    OBJECTS     {
        tmnxChassisNotifyChassisId,
        tmnxChassisNotifyCardSlotNum,
        tmnxPlcyAcctTimeEventOccured,
        tmnxPlcyAcctMissingNotifCount
    }
    STATUS      current
    DESCRIPTION
        "[CAUSE] The tmnxPlcyAcctStatsEventOvrflwClr notification is generated
         when the CPM polls the IOM for traps and the overflow is cleared by
         logging an overflow-clear on a particular card.

         [EFFECT] Notifications are received again since the event throttling
         has ended.

         [RECOVERY] There is no recovery for this notification."
    ::= { tmnxChassisNotification 106 }

tmnxPlcyAcctStatsEventOvrflw     NOTIFICATION-TYPE
    OBJECTS     {
        tmnxChassisNotifyChassisId,
        tmnxChassisNotifyCardSlotNum,
        tmnxPlcyAcctTimeEventOccured
    }
    STATUS      current
    DESCRIPTION
        "[CAUSE] The tmnxPlcyAcctStatsEventOvrflw notification is generated
         when tmnxPlcyAcctStatsPoolExcResource and
         tmnxPlcyAcctStatsPoolLowResource occur more than 200 times because of
         resource usage fluctuation. The IOM raises the final trap to indicate
         overflow and stops logging traps.

         [EFFECT] Some FP notifications configured on the card may not be
         received.

         [RECOVERY] Notifications will resume once the Overflow clear is set."
    ::= { tmnxChassisNotification 107 }

tmnxIomResHighLimitReached       NOTIFICATION-TYPE
    OBJECTS     {
        tmnxChassisNotifyChassisId,
        tmnxChassisNotifyCardSlotNum,
        tmnxIomResourceType,
        tmnxIomResourceLimitPct,
        tmnxIomResLimitTimeEventOccured,
        tmnxChassisNotifyFpNum
    }
    STATUS      current
    DESCRIPTION
        "[CAUSE] The tmnxIomResHighLimitReached notification is generated when
         the resource (of type tmnxIomResourceType) utilization on IOM has
         reached the value of tmnxIomResourceLimitPct.

         [EFFECT] The specified resource limit is cleared when the number of
         in-use stats resources falls below the clear threshold of the stats
         pool limit.

         [RECOVERY] There is no recovery required for this notification."
    ::= { tmnxChassisNotification 108 }

tmnxIomResExhausted              NOTIFICATION-TYPE
    OBJECTS     {
        tmnxChassisNotifyChassisId,
        tmnxChassisNotifyCardSlotNum,
        tmnxIomResourceType,
        tmnxIomResLimitTimeEventOccured,
        tmnxChassisNotifyFpNum
    }
    STATUS      current
    DESCRIPTION
        "[CAUSE] The tmnxIomResExhausted notification is  generated when
         the type of resources on IOM as specified by tmnxIomResourceType has
         reached the 100% of its utilization threshold.

         [EFFECT] The specified resource has reached the stats pool limit.

         [RECOVERY] Intervention may be required to recover resources."
    ::= { tmnxChassisNotification 109 }

tmnxIomResStateClr               NOTIFICATION-TYPE
    OBJECTS     {
        tmnxChassisNotifyChassisId,
        tmnxChassisNotifyCardSlotNum,
        tmnxIomResourceType,
        tmnxIomResourceLimitPct,
        tmnxIomResLimitTimeEventOccured,
        tmnxChassisNotifyFpNum
    }
    STATUS      current
    DESCRIPTION
        "[CAUSE] The tmnxIomResStateClr notification is generated when the type
         of resources on IOM as specified by tmnxIomResourceType has dropped
         back down below the value of tmnxIomResourceLimitPct.

         [EFFECT] The specified resource limit is cleared when the number of
         in-use stats resources falls below tmnxIomResourceLimitPct of the
         stats pool limit.

         [RECOVERY] There is no recovery required for this notification."
    ::= { tmnxChassisNotification 110 }

tmnxIomEventOverflow             NOTIFICATION-TYPE
    OBJECTS     {
        tmnxChassisNotifyChassisId,
        tmnxChassisNotifyCardSlotNum,
        tmnxIomResLimitTimeEventOccured,
        tmnxIomResourceType
    }
    STATUS      current
    DESCRIPTION
        "[CAUSE] The tmnxIomEventOverflow notification is generated when
         tmnxIomResStateClr, tmnxIomResExhausted and tmnxIomResHighLimitReached
         occur more than 200 times because of resource usage fluctuation. The
         IOM raises the final trap to indicate overflow and stops logging
         traps.

         [EFFECT] Some FP notifications configured on the card may not be
         received.

         [RECOVERY] Notifications will resume once the Overflow clear is set."
    ::= { tmnxChassisNotification 111 }

tmnxIomEventOverflowClr          NOTIFICATION-TYPE
    OBJECTS     {
        tmnxChassisNotifyChassisId,
        tmnxChassisNotifyCardSlotNum,
        tmnxIomResLimitTimeEventOccured,
        tmnxIomResLimMissingNotifCount,
        tmnxIomResourceType
    }
    STATUS      current
    DESCRIPTION
        "[CAUSE] The tmnxIomEventOverflowClr notification is generated when the
         CPM polls the IOM for traps and the overflow is cleared by logging an
         overflow-clear on a particular card.

         [EFFECT] Notifications are received again since the event throttling
         has ended.

         [RECOVERY] There is no recovery for this notification."
    ::= { tmnxChassisNotification 112 }

tmnxEqDataPathFailureProtImpact  NOTIFICATION-TYPE
    OBJECTS     {
        tmnxHwClass
    }
    STATUS      current
    DESCRIPTION
        "[CAUSE] The tmnxEqDataPathFailureProtImpact notification is generated
         when a slot experienced a data path failure which impacted a protocol.

         [EFFECT] Services-related data associated with the impacted protocol
         may be lost."
    ::= { tmnxChassisNotification 113 }

tmnxExtStandbyCpmReboot          NOTIFICATION-TYPE
    OBJECTS     {
        tmnxChassisNotifyChassisId,
        tmnxChassisNotifyCpmCardSlotNum
    }
    STATUS      current
    DESCRIPTION
        "[CAUSE] The tmnxExtStandbyCpmReboot notification is generated after a
         master standby CPM reboots and it is determined that the master
         standby CPM has transitioned into or out of an ISSU state. This
         detected transition will cause a reboot of the extension standby CPM
         (this reboot is necessary and expected for ISSU operation). This
         notification helps an operator understand why an extension standby CPM
         may have rebooted.

         [EFFECT] The extension standby CPM will reboot.

         [RECOVERY] There is no recovery for this notification."
    ::= { tmnxChassisNotification 114 }

tmnxExtStandbyCpmRebootFail      NOTIFICATION-TYPE
    OBJECTS     {
        tmnxChassisNotifyChassisId
    }
    STATUS      current
    DESCRIPTION
        "[CAUSE] The tmnxExtStandbyCpmRebootFail notification is generated
         after a master standby CPM reboots and it is determined that the
         master standby CPM has transitioned into or out of an ISSU state. The
         system will attempt to reboot the extension standby CPM as part of the
         normal ISSU process. If the system determines that it cannot reboot
         the extension standby CPM (i.e. it is not reachable) then this log
         event is raised.

         [EFFECT] The extension standby CPM may not transition to the ISSU
         state in which case the ISSU cannot proceed normally.

         [RECOVERY] Resetting the extension standby CPM can be attempted to try
         and get the CPM into an ISSU state. If that is not successful, then
         the ISSU should be aborted."
    ::= { tmnxChassisNotification 115 }

tmnxEqMdaIngrXplError            NOTIFICATION-TYPE
    OBJECTS     {
        tmnxMdaHwEventNumOccurrences
    }
    STATUS      current
    DESCRIPTION
        "[CAUSE] The tmnxEqMdaIngrXplError notification is generated when an
         MDA exhibits persistent ingress XPL errors, and the tmnxEqMdaXplError
         notification is generated when egress XPL errors occur.

         [EFFECT] Contact Nokia customer support.

         [RECOVERY] Contact Nokia customer support."
    ::= { tmnxChassisNotification 116 }

tmnxPowerSupplyWrongFanDir       NOTIFICATION-TYPE
    OBJECTS     {
        tmnxHwClass,
        tmnxChassisPowerSupplyFanDir
    }
    STATUS      obsolete
    DESCRIPTION
        "[CAUSE] The tmnxPowerSupplyWrongFanDir notification is generated when
         the airflow direction of the power supply's fan is incorrect.

         [EFFECT] The power supply is not cooling properly and may overheat.

         [RECOVERY] Replace the power supply with one that has the proper fan
         direction.

         This notification was made obsolete in release 15.0."
    ::= { tmnxChassisNotification 119 }

tmnxPowerSupplyWrongFanDirClear  NOTIFICATION-TYPE
    OBJECTS     {
        tmnxHwClass
    }
    STATUS      obsolete
    DESCRIPTION
        "[CAUSE] The tmnxPowerSupplyWrongFanDirClear notification is generated
         when the airflow direction of the power supply's fan is corrected.

         [EFFECT] The fan is cooling the power supply in the proper direction.

         [RECOVERY] No recovery required.

         This notification was made obsolete in release 15.0."
    ::= { tmnxChassisNotification 120 }

tmnxEqMgmtEthRedStandbyRaise     NOTIFICATION-TYPE
    OBJECTS     {
        tmnxHwClass,
        tmnxChassisNotifyMgmtEthRedPort
    }
    STATUS      current
    DESCRIPTION
        "[CAUSE] The tmnxEqMgmtEthRedStandbyRaise notification is generated
         when the active CPM's management Ethernet port goes operationally down
         and the standby CPM's management Ethernet port is operationally up and
         now serving as the system's management Ethernet port.

         [EFFECT] The management Ethernet port is no longer redundant. The node
         can be managed via the standby CPM's management Ethernet port only.

         [RECOVERY] Bring the active CPM's management Ethernet port
         operationally up."
    ::= { tmnxChassisNotification 121 }

tmnxEqMgmtEthRedStandbyClear     NOTIFICATION-TYPE
    OBJECTS     {
        tmnxHwClass,
        tmnxChassisNotifyMgmtEthRedPort
    }
    STATUS      current
    DESCRIPTION
        "[CAUSE] The tmnxEqMgmtEthRedStandbyClear notification is generated
         when the active CPM's management Ethernet port goes operationally up
         and the management Ethernet port reverts from the standby CPM to the
         active CPM.

         [EFFECT] The management of the node is operating from the active CPM's
         management Ethernet port and is redundant.

         [RECOVERY] No recovery required."
    ::= { tmnxChassisNotification 122 }

tmnxSyncIfTimBITS2048khzUnsup    NOTIFICATION-TYPE
    OBJECTS     {
        tmnxHwClass
    }
    STATUS      current
    DESCRIPTION
        "[CAUSE] The tmnxSyncIfTimBITS2048khzUnsup notification is generated
         when the value of tSyncIfTimingAdmBITSIfType is set to 'g703-2048khz
         (5)' and the CPM does not meet the specifications for the 2048kHz BITS
         output signal under G.703.

         [EFFECT] The BITS input will not be used as the Sync reference and the
         2048kHz BITS output signal generated by the CPM is squelched.

         [RECOVERY] Replace the CPM with one that is capable of generating the
         2048kHz BITS output signal, or set tSyncIfTimingAdmBITSIfType to a
         value other than 'g703-2048khz (5)'."
    REFERENCE
        "G.703, 'Physical/Electrical Characteristics of Hierarchical Digital
         Interfaces', Section 13, November 2001."
    ::= { tmnxChassisNotification 123 }

tmnxSyncIfTimBITS2048khzUnsupClr NOTIFICATION-TYPE
    OBJECTS     {
        tmnxHwClass
    }
    STATUS      current
    DESCRIPTION
        "[CAUSE] The tmnxSyncIfTimBITS2048khzUnsupClr notification is generated
         when a tmnxSyncIfTimBITS2048khzUnsup notification is outstanding and
         the CPM was replaced with one that meets the specifications for the
         2048kHz BITS output signal under G.703 or tSyncIfTimingAdmBITSIfType
         is set to a value other than 'g703-2048khz (5)'.

         [EFFECT] The CPM can now support the configuration of
         tSyncIfTimingAdmBITSIfType.

         [RECOVERY] No recovery required."
    REFERENCE
        "G.703, 'Physical/Electrical Characteristics of Hierarchical Digital
         Interfaces', Section 13, November 2001."
    ::= { tmnxChassisNotification 124 }

tmnxEqPhysChassPowerSupOvrTmp    NOTIFICATION-TYPE
    OBJECTS     {
        tmnxHwClass,
        tmnxPhysChassPowerSupTempStatus,
        tmnxPhysChassPowerSupTempThrshld
    }
    STATUS      current
    DESCRIPTION
        "[CAUSE] The tmnxEqPhysChassPowerSupOvrTmp notification is generated
         when a power supply's temperature surpasses the threshold of the
         particular physical chassis.

         [EFFECT] The power supply is no longer operational.

         [RECOVERY] Check input feed and/or insert a new power supply."
    ::= { tmnxChassisNotification 125 }

tmnxEqPhysChassPowerSupOvrTmpClr NOTIFICATION-TYPE
    OBJECTS     {
        tmnxHwClass,
        tmnxPhysChassPowerSupTempStatus,
        tmnxPhysChassPowerSupTempThrshld
    }
    STATUS      current
    DESCRIPTION
        "[CAUSE] The tmnxEqPhysChassPowerSupOvrTmpClr notification is generated
         when a power supply's temperature is reduced below the threshold of
         the particular physical chassis.

         [EFFECT] The power supply is operational again.

         [RECOVERY] There is no recovery for this notification."
    ::= { tmnxChassisNotification 126 }

tmnxEqPhysChassPowerSupAcFail    NOTIFICATION-TYPE
    OBJECTS     {
        tmnxHwClass,
        tmnxPhysChassPowerSupACStatus,
        tmnxPhysChassPowerSup1Status,
        tmnxPhysChassPowerSup2Status
    }
    STATUS      current
    DESCRIPTION
        "[CAUSE] The tmnxEqPhysChassPowerSupAcFail notification is generated
         when an AC failure occurs on the power supply.

         [EFFECT] The power supply is no longer operational.

         [RECOVERY] Insert a new power supply."
    ::= { tmnxChassisNotification 127 }

tmnxEqPhysChassPowerSupAcFailClr NOTIFICATION-TYPE
    OBJECTS     {
        tmnxHwClass,
        tmnxPhysChassPowerSupACStatus,
        tmnxPhysChassPowerSup1Status,
        tmnxPhysChassPowerSup2Status
    }
    STATUS      current
    DESCRIPTION
        "[CAUSE] The tmnxEqPhysChassPowerSupAcFailClr notification is generated
         when the AC failure is cleared on the power supply.

         [EFFECT] The power supply is operational again.

         [RECOVERY] There is no recovery for this notification."
    ::= { tmnxChassisNotification 128 }

tmnxEqPhysChassPowerSupDcFail    NOTIFICATION-TYPE
    OBJECTS     {
        tmnxHwClass,
        tmnxPhysChassPowerSupDCStatus,
        tmnxPhysChassPowerSup1Status
    }
    STATUS      current
    DESCRIPTION
        "[CAUSE] The tmnxEqPhysChassPowerSupDcFail notification is generated
         when a DC failure occurs on the power supply.

         [EFFECT] The power supply is no longer operational.

         [RECOVERY] Insert a new power supply."
    ::= { tmnxChassisNotification 129 }

tmnxEqPhysChassPowerSupDcFailClr NOTIFICATION-TYPE
    OBJECTS     {
        tmnxHwClass,
        tmnxPhysChassPowerSupDCStatus,
        tmnxPhysChassPowerSup1Status
    }
    STATUS      current
    DESCRIPTION
        "[CAUSE] The tmnxEqPhysChassPowerSupDcFailClr notification is generated
         when the DC failure is cleared on the power supply.

         [EFFECT] The power supply is operational again.

         [RECOVERY] There is no recovery for this notification."
    ::= { tmnxChassisNotification 130 }

tmnxEqPhysChassPowerSupInFail    NOTIFICATION-TYPE
    OBJECTS     {
        tmnxHwClass,
        tmnxPhysChassPowerSupInputStatus
    }
    STATUS      current
    DESCRIPTION
        "[CAUSE] The tmnxEqPhysChassPowerSupInFail notification is generated
         when an input failure occurs on the power supply.

         [EFFECT] The power supply is no longer operational.

         [RECOVERY] Check input feed and/or insert a new power supply."
    ::= { tmnxChassisNotification 131 }

tmnxEqPhysChassPowerSupInFailClr NOTIFICATION-TYPE
    OBJECTS     {
        tmnxHwClass,
        tmnxPhysChassPowerSupInputStatus
    }
    STATUS      current
    DESCRIPTION
        "[CAUSE] The tmnxEqPhysChassPowerSupInFailClr notification is generated
         when the input failure is cleared on the power supply.

         [EFFECT] The power supply is operational again.

         [RECOVERY] There is no recovery for this notification."
    ::= { tmnxChassisNotification 132 }

tmnxEqPhysChassPowerSupOutFail   NOTIFICATION-TYPE
    OBJECTS     {
        tmnxHwClass,
        tmnxPhysChassPowerSupOutptStatus
    }
    STATUS      current
    DESCRIPTION
        "[CAUSE] The tmnxEqPhysChassPowerSupOutFail notification is generated
         when an output failure occurs on the power supply.

         [EFFECT] The power supply is no longer operational.

         [RECOVERY] Insert a new power supply."
    ::= { tmnxChassisNotification 133 }

tmnxEqPhysChassPowerSupOutFailCl NOTIFICATION-TYPE
    OBJECTS     {
        tmnxHwClass,
        tmnxPhysChassPowerSupOutptStatus
    }
    STATUS      current
    DESCRIPTION
        "[CAUSE] The tmnxEqPhysChassPowerSupOutFailCl notification is generated
         when an output failure is cleared on the power supply.

         [EFFECT] The power supply is operational again.

         [RECOVERY] There is no recovery for this notification."
    ::= { tmnxChassisNotification 134 }

tmnxEqPhysChassisFanFailure      NOTIFICATION-TYPE
    OBJECTS     {
        tmnxHwClass,
        tmnxPhysChassisFanOperStatus,
        tmnxPhysChassisFanSpeedPercent
    }
    STATUS      current
    DESCRIPTION
        "[CAUSE] The tmnxEqPhysChassisFanFailure notification is generated when
         one of the fans in a fan tray fails on a particular physical chassis.

         [EFFECT] The fan is no longer operational.

         [RECOVERY] Insert a new fan."
    ::= { tmnxChassisNotification 135 }

tmnxEqPhysChassisFanFailureClear NOTIFICATION-TYPE
    OBJECTS     {
        tmnxHwClass,
        tmnxPhysChassisFanOperStatus,
        tmnxPhysChassisFanSpeedPercent
    }
    STATUS      current
    DESCRIPTION
        "[CAUSE] The tmnxEqPhysChassisFanFailureClear notification is generated
         when the fan failure is cleared on the particular physical chassis.

         [EFFECT] The fan is operational again.

         [RECOVERY] There is no recovery for this notification."
    ::= { tmnxChassisNotification 136 }

tIPsecIsaMemLowWatermark         NOTIFICATION-TYPE
    OBJECTS     {
        tmnxMDAHwIndex
    }
    STATUS      current
    DESCRIPTION
        "[CAUSE] A tIPsecIsaMemLowWatermark notification is generated when the
         ISA card memory usage ratio has dropped back to the normal level.

         [EFFECT] The system accepts new IKE states.

         [RECOVERY] There is no recovery required for this notification."
    ::= { tmnxChassisNotification 137 }

tIPsecIsaMemHighWatermark        NOTIFICATION-TYPE
    OBJECTS     {
        tmnxMDAHwIndex
    }
    STATUS      current
    DESCRIPTION
        "[CAUSE] A tIPsecIsaMemHighWatermark notification is generated when the
         ISA card memory usage ratio has almost reached the maximum value.

         [EFFECT] The system may stop accepting new IKE states shortly.

         [RECOVERY] Use fewer SAs for each IKE tunnel."
    ::= { tmnxChassisNotification 138 }

tIPsecIsaMemMax                  NOTIFICATION-TYPE
    OBJECTS     {
        tmnxMDAHwIndex
    }
    STATUS      current
    DESCRIPTION
        "[CAUSE] A tIPsecIsaMemMax notification is generated when the ISA card
         memory usage ratio has reached the maximum value.

         [EFFECT] The system stops accepting new IKE states.

         [RECOVERY] Use fewer SAs for each IKE tunnel."
    ::= { tmnxChassisNotification 139 }

tmnxCpmMemSizeMismatch           NOTIFICATION-TYPE
    OBJECTS     {
        tmnxHwClass,
        tmnxChassisNotifyCpmCardSlotNum,
        tmnxChassisNotifyHwIndex
    }
    STATUS      current
    DESCRIPTION
        "[CAUSE] A tmnxCpmMemSizeMismatch notification is generated when the
         RAM memory size of the standby CPM (i.e.,
         tmnxChassisNotifyCpmCardSlotNum) is different than the active CPM
         (i.e., tmnxChassisNotifyHwIndex).

         [EFFECT] There is an increased risk of the memory overflow on the
         standby CPM during the CPM switchover.

         [RECOVERY] Use CPMs with the same memory size."
    ::= { tmnxChassisNotification 140 }

tmnxCpmMemSizeMismatchClear      NOTIFICATION-TYPE
    OBJECTS     {
        tmnxHwClass,
        tmnxChassisNotifyCpmCardSlotNum,
        tmnxChassisNotifyHwIndex
    }
    STATUS      current
    DESCRIPTION
        "[CAUSE] A tmnxCpmMemSizeMismatchClear notification is generated when
         the RAM memory sizes of the standby (i.e.,
         tmnxChassisNotifyCpmCardSlotNum) and active (i.e.,
         tmnxChassisNotifyHwIndex) CPMs become matched.

         [EFFECT] The tmnxCpmMemSizeMismatch notification is cleared.

         [RECOVERY] There is no recovery required for this notification."
    ::= { tmnxChassisNotification 141 }

tmnxPhysChassPwrSupWrgFanDir     NOTIFICATION-TYPE
    OBJECTS     {
        tmnxHwClass,
        tmnxPhysChassPowerSupFanDir
    }
    STATUS      current
    DESCRIPTION
        "[CAUSE] The tmnxPhysChassPwrSupWrgFanDir notification is generated
         when the airflow direction of the power supply's fan is incorrect.

         [EFFECT] The power supply is not cooling properly and may overheat.

         [RECOVERY] Replace the power supply with one that has the proper fan
         direction."
    ::= { tmnxChassisNotification 142 }

tmnxPhysChassPwrSupWrgFanDirClr  NOTIFICATION-TYPE
    OBJECTS     {
        tmnxHwClass,
        tmnxPhysChassPowerSupFanDir
    }
    STATUS      current
    DESCRIPTION
        "[CAUSE] The tmnxPhysChassPwrSupWrgFanDirClr notification is generated
         when the airflow direction of the power supply's fan is corrected.

         [EFFECT] The fan is cooling the power supply in the proper direction.

         [RECOVERY] No recovery required."
    ::= { tmnxChassisNotification 143 }

tmnxPhysChassPwrSupPemACRect     NOTIFICATION-TYPE
    OBJECTS     {
        tmnxHwClass,
        tmnxPhysChassPowerSupPemACRect
    }
    STATUS      current
    DESCRIPTION
        "[CAUSE] The tmnxPhysChassPwrSupPemACRect notification is generated if
         any one of the AC rectifiers for a given power supply is in a failed
         state or is missing.

         [EFFECT] There is an increased risk of the power supply failing,
         causing insufficient power to the system.

         [RECOVERY] Bring the AC rectifiers back online."
    ::= { tmnxChassisNotification 144 }

tmnxPhysChassPwrSupPemACRectClr  NOTIFICATION-TYPE
    OBJECTS     {
        tmnxHwClass,
        tmnxPhysChassPowerSupPemACRect
    }
    STATUS      current
    DESCRIPTION
        "[CAUSE] The tmnxPhysChassPwrSupPemACRectClr notification is generated
         when the last of the failed or missing AC rectifiers has been brought
         back online.

         [EFFECT] The power supply AC rectifiers are fully operational.

         [RECOVERY] No recovery required."
    ::= { tmnxChassisNotification 145 }

tmnxPhysChassPwrSupInputFeed     NOTIFICATION-TYPE
    OBJECTS     {
        tmnxHwClass,
        tmnxPhysChassPowerSupInFeedDown
    }
    STATUS      current
    DESCRIPTION
        "[CAUSE] The tmnxPhysChassPwrSupInputFeed notification is generated if
         any one of the input feeds for a given power supply is not supplying
         power.

         [EFFECT] There is an increased risk of system power brownouts or
         blackouts.

         [RECOVERY] Restore all of the input feeds that are not supplying
         power."
    ::= { tmnxChassisNotification 146 }

tmnxPhysChassPwrSupInputFeedClr  NOTIFICATION-TYPE
    OBJECTS     {
        tmnxHwClass,
        tmnxPhysChassPowerSupInFeedDown
    }
    STATUS      current
    DESCRIPTION
        "[CAUSE] The tmnxPhysChassPwrSupInputFeedClr notification is generated
         when the last of the missing input feeds has been brought back online.

         [EFFECT] All power supply input feeds are supplying power.

         [RECOVERY] No recovery required."
    ::= { tmnxChassisNotification 147 }

tmnxCardResMacFdbHighUsgSet      NOTIFICATION-TYPE
    OBJECTS     {
        tmnxMacScaleCardSlotNum
    }
    STATUS      current
    DESCRIPTION
        "[CAUSE] The tmnxCardResMacFdbHighUsgSet notification is generated when
         the FDB table size exceeds 95% of the card limit.

         [EFFECT] The FDB table size for the card exceeds 95% of the card
         limit.

         [RECOVERY] None needed."
    ::= { tmnxChassisNotification 148 }

tmnxCardResMacFdbHighUsgClr      NOTIFICATION-TYPE
    OBJECTS     {
        tmnxMacScaleCardSlotNum
    }
    STATUS      current
    DESCRIPTION
        "[CAUSE] The tmnxCardResMacFdbHighUsgClr notification is generated when
         the FDB table size drops below 90% of the card limit.

         [EFFECT] The FDB table size for the card drops below 90% of the card
         limit.

         [RECOVERY] None needed."
    ::= { tmnxChassisNotification 149 }

tmnxEqBpEpromFail                NOTIFICATION-TYPE
    OBJECTS     {
        tmnxHwClass
    }
    STATUS      current
    DESCRIPTION
        "[CAUSE] The tmnxEqBpEpromFail notification is generated when the
         active CPM is no longer able to access the backplane EPROM due to a
         hardware defect.

         [EFFECT] The active CPM is at risk of failing to initialize after node
         reboot due to not being able to access the BP EPROM to read the
         chassis type.

         [RECOVERY] Contact Nokia customer support."
    ::= { tmnxChassisNotification 150 }

tmnxEqBpEpromFailClear           NOTIFICATION-TYPE
    OBJECTS     {
        tmnxHwClass
    }
    STATUS      current
    DESCRIPTION
        "[CAUSE] The tmnxEqBpEpromFailClear notification is generated when the
         EPROM error condition is cleared."
    ::= { tmnxChassisNotification 151 }

tmnxEqBpEpromWarning             NOTIFICATION-TYPE
    OBJECTS     {
        tmnxHwClass
    }
    STATUS      current
    DESCRIPTION
        "[CAUSE] The tmnxEqBpEpromWarning notification is generated when the
         active CPM is no longer able to access one backplane EPROM due to a
         hardware defect, but a redundant EPROM is present and accessible.

         [EFFECT] There is no effect on system operation.

         [RECOVERY] No recovery action required."
    ::= { tmnxChassisNotification 152 }

tmnxEqBpEpromWarningClear        NOTIFICATION-TYPE
    OBJECTS     {
        tmnxHwClass
    }
    STATUS      current
    DESCRIPTION
        "[CAUSE] The tmnxEqBpEpromWarningClear notification is generated when
         the backplane EPROM warning condition is cleared."
    ::= { tmnxChassisNotification 153 }

tmnxPhysChassisPCMInputFeed      NOTIFICATION-TYPE
    OBJECTS     {
        tmnxHwClass,
        tmnxPhysChassisPCMInFeedDown
    }
    STATUS      current
    DESCRIPTION
        "[CAUSE] The tmnxPhysChassisPCMInputFeed notification is generated if
         any one of the input feeds for a given PCM has gone offline.

         [EFFECT] There is an increased risk of system power brownouts or
         blackouts.

         [RECOVERY] Restore all of the input feeds that are not supplying
         power."
    ::= { tmnxChassisNotification 154 }

tmnxPhysChassisPCMInputFeedClr   NOTIFICATION-TYPE
    OBJECTS     {
        tmnxHwClass,
        tmnxPhysChassisPCMInFeedDown
    }
    STATUS      current
    DESCRIPTION
        "[CAUSE] The tmnxPhysChassisPCMInputFeedClr notification is generated
         when the last of the missing input feeds for a given PCM has been
         brought back online.

         [EFFECT] All PCM input feeds are supplying power.

         [RECOVERY] No recovery required."
    ::= { tmnxChassisNotification 155 }

tmnxIPMacQosIngOverload          NOTIFICATION-TYPE
    OBJECTS     {
        tmnxHwClass,
        tmnxChassisNotifyCardSlotNum,
        tmnxChassisNotifyFpNum
    }
    STATUS      current
    DESCRIPTION
        "[CAUSE] The tmnxIPMacQosIngOverload notification is generated when an
         ingress QoS policy is in overload on an FP due to its configured IPv4
         or MAC criteria entries.

         [EFFECT] The impacted IPv4 or MAC criteria entries in the ingress QoS
         policy on the affected FP will not work as expected, because not all
         entries are programmed.

         [RECOVERY] Identify the impacted ingress QoS policy, policy entries,
         and FPs using the appropriate tools commands. Remove or modify the
         policy criteria entries or change the policy assigned to the impacted
         FPs until the overload condition is cleared."
    ::= { tmnxChassisNotification 156 }

tmnxIPMacQosIngOverloadClear     NOTIFICATION-TYPE
    OBJECTS     {
        tmnxHwClass,
        tmnxChassisNotifyCardSlotNum,
        tmnxChassisNotifyFpNum
    }
    STATUS      current
    DESCRIPTION
        "[CAUSE] The tmnxIPMacQosIngOverloadClear notification is generated
         when ingress QoS policies are no longer in overload on an FP.

         [EFFECT] The IPv4 or MAC criteria entries in the ingress QoS policies
         on the affected FP will work as expected, because all entries are
         programmed.

         [RECOVERY] No recovery required."
    ::= { tmnxChassisNotification 157 }

tmnxIPQosEgrOverload             NOTIFICATION-TYPE
    OBJECTS     {
        tmnxHwClass,
        tmnxChassisNotifyCardSlotNum,
        tmnxChassisNotifyFpNum
    }
    STATUS      current
    DESCRIPTION
        "[CAUSE] The tmnxIPQosEgrOverload notification is generated when an
         egress QoS policy is in overload on an FP due to its configured IPv4
         criteria entries.

         [EFFECT] The impacted IPv4 criteria entries in the egress QoS policy
         on the affected FP will not work as expected, because not all entries
         are programmed.

         [RECOVERY] Identify the impacted egress QoS policy, policy entries,
         and FPs using the appropriate tools commands. Remove or modify the
         policy criteria entries or change the policy assigned to the impacted
         FPs until the overload condition is cleared."
    ::= { tmnxChassisNotification 158 }

tmnxIPQosEgrOverloadClear        NOTIFICATION-TYPE
    OBJECTS     {
        tmnxHwClass,
        tmnxChassisNotifyCardSlotNum,
        tmnxChassisNotifyFpNum
    }
    STATUS      current
    DESCRIPTION
        "[CAUSE] The tmnxIPQosEgrOverloadClear notification is generated when
         egress QoS policies are no longer in overload on an FP.

         [EFFECT] The IPv4 criteria entries in the egress QoS policy on the
         affected FP will work as expected, because all entries are programmed.

         [RECOVERY] No recovery required."
    ::= { tmnxChassisNotification 159 }

tmnxIPv6QosIngOverload           NOTIFICATION-TYPE
    OBJECTS     {
        tmnxHwClass,
        tmnxChassisNotifyCardSlotNum,
        tmnxChassisNotifyFpNum
    }
    STATUS      current
    DESCRIPTION
        "[CAUSE] The tmnxIPv6QosIngOverload notification is generated when an
         ingress QoS policy is in overload on an FP due to its configured IPv6
         criteria entries.

         [EFFECT] The impacted IPv6 criteria entries in the ingress QoS policy
         on the affected FP will not work as expected, because not all entries
         are programmed.

         [RECOVERY] Identify the impacted ingress QoS policy, policy entries,
         and FPs using the appropriate tools commands. Remove or modify the
         policy criteria entries or change the policy assigned to the impacted
         FPs until the overload condition is cleared."
    ::= { tmnxChassisNotification 160 }

tmnxIPv6QosIngOverloadClear      NOTIFICATION-TYPE
    OBJECTS     {
        tmnxHwClass,
        tmnxChassisNotifyCardSlotNum,
        tmnxChassisNotifyFpNum
    }
    STATUS      current
    DESCRIPTION
        "[CAUSE] The tmnxIPv6QosIngOverloadClear notification is generated when
         ingress QoS policies are no longer in overload on an FP.

         [EFFECT] The IPv6 criteria entries in the ingress QoS policy on the
         affected FP will work as expected, because all entries are programmed.

         [RECOVERY] No recovery required."
    ::= { tmnxChassisNotification 161 }

tmnxIPv6QosEgrOverload           NOTIFICATION-TYPE
    OBJECTS     {
        tmnxHwClass,
        tmnxChassisNotifyCardSlotNum,
        tmnxChassisNotifyFpNum
    }
    STATUS      current
    DESCRIPTION
        "[CAUSE] The tmnxIPv6QosEgrOverload notification is generated when an
         egress QoS policy is in overload on an FP due to its configured IPv6
         criteria entries.

         [EFFECT] The impacted IPv6 criteria entries in the egress QoS Policy
         on the affected FP will not work as expected, because not all entries
         are programmed.

         [RECOVERY] Identify the impacted egress QoS policy, policy entries,
         and FPs using the appropriate tools commands. Remove or modify the
         policy criteria entries or change the policy assigned to the impacted
         FPs until the overload condition is cleared."
    ::= { tmnxChassisNotification 162 }

tmnxIPv6QosEgrOverloadClear      NOTIFICATION-TYPE
    OBJECTS     {
        tmnxHwClass,
        tmnxChassisNotifyCardSlotNum,
        tmnxChassisNotifyFpNum
    }
    STATUS      current
    DESCRIPTION
        "[CAUSE] The tmnxIPv6QosEgrOverloadClear notification is generated when
         egress QoS policies are no longer in overload on an FP.

         [EFFECT] The IPv6 criteria entries in the egress QoS policy on the
         affected FP will work as expected, because all entries are programmed.

         [RECOVERY] No recovery required."
    ::= { tmnxChassisNotification 163 }

tmnxIPMacFilterIngOverload       NOTIFICATION-TYPE
    OBJECTS     {
        tmnxHwClass,
        tmnxChassisNotifyCardSlotNum,
        tmnxChassisNotifyFpNum
    }
    STATUS      current
    DESCRIPTION
        "[CAUSE] The tmnxIPMacFilterIngOverload notification is generated when
         an ingress IPv4 or MAC ACL Filter policy is in overload on an FP.

         [EFFECT] The impacted ingress IPv4 or MAC ACL Filter policy on the
         affected FP will not work as expected, because not all entries are
         programmed.

         [RECOVERY] Identify the impacted ingress IPv4 or MAC ACL Filter
         policy, policy entries, and FPs using the appropriate tools commands.
         Remove or modify policy entries or change the policy assigned to the
         impacted FPs until the overload condition is cleared."
    ::= { tmnxChassisNotification 164 }

tmnxIPMacFilterIngOverloadClear  NOTIFICATION-TYPE
    OBJECTS     {
        tmnxHwClass,
        tmnxChassisNotifyCardSlotNum,
        tmnxChassisNotifyFpNum
    }
    STATUS      current
    DESCRIPTION
        "[CAUSE] The tmnxIPMacFilterIngOverloadClear notification is generated
         when ingress IPv4 or MAC ACL Filter policies are no longer in overload
         on an FP.

         [EFFECT] The ingress IPv4 or MAC ACL Filter policies on the affected
         FP will work as expected, because all entries are programmed.

         [RECOVERY] No recovery required."
    ::= { tmnxChassisNotification 165 }

tmnxIPMacFilterEgrOverload       NOTIFICATION-TYPE
    OBJECTS     {
        tmnxHwClass,
        tmnxChassisNotifyCardSlotNum,
        tmnxChassisNotifyFpNum
    }
    STATUS      current
    DESCRIPTION
        "[CAUSE] The tmnxIPMacFilterEgrOverload notification is generated when
         an egress IPv4 or MAC ACL Filter policy is in overload on an FP.

         [EFFECT] The impacted egress IPv4 or MAC ACL Filter policy on the
         affected FP will not work as expected, because not all entries are
         programmed.

         [RECOVERY] Identify the impacted egress IPv4 or MAC ACL Filter policy,
         policy entries, and FPs using the appropriate tools commands. Remove
         or modify policy entries or change the policy assigned to the impacted
         FPs until the overload condition is cleared."
    ::= { tmnxChassisNotification 166 }

tmnxIPMacFilterEgrOverloadClear  NOTIFICATION-TYPE
    OBJECTS     {
        tmnxHwClass,
        tmnxChassisNotifyCardSlotNum,
        tmnxChassisNotifyFpNum
    }
    STATUS      current
    DESCRIPTION
        "[CAUSE] The tmnxIPMacFilterEgrOverloadClear notification is generated
         when egress IPv4 or MAC ACL Filter policies are no longer in overload
         on an FP.

         [EFFECT] The egress IPv4 or MAC ACL Filter policies on the affected FP
         will work as expected, because all entries are programmed.

         [RECOVERY] No recovery required."
    ::= { tmnxChassisNotification 167 }

tmnxIPv6FilterIngOverload        NOTIFICATION-TYPE
    OBJECTS     {
        tmnxHwClass,
        tmnxChassisNotifyCardSlotNum,
        tmnxChassisNotifyFpNum
    }
    STATUS      current
    DESCRIPTION
        "[CAUSE] The tmnxIPv6FilterIngOverload notification is generated when
         an ingress IPv6 ACL Filter policy is in overload on a FP.

         [EFFECT] The impacted ingress IPv6 ACL Filter policy on the affected
         FP will not work as expected, because not all entries are programmed.

         [RECOVERY] Identify the impacted ingress IPv6 ACL Filter policy,
         policy entries, and FPs using the appropriate tools commands. Remove
         or modify policy entries or change the policy assigned to the impacted
         FPs until the overload condition is cleared."
    ::= { tmnxChassisNotification 168 }

tmnxIPv6FilterIngOverloadClear   NOTIFICATION-TYPE
    OBJECTS     {
        tmnxHwClass,
        tmnxChassisNotifyCardSlotNum,
        tmnxChassisNotifyFpNum
    }
    STATUS      current
    DESCRIPTION
        "[CAUSE] The tmnxIPv6FilterIngOverloadClear notification is generated
         when ingress IPv6 ACL Filter policies are no longer in overload on an
         FP.

         [EFFECT] The ingress IPv6 ACL Filter policies on the affected FP will
         work as expected, because all entries are programmed.

         [RECOVERY] No recovery required."
    ::= { tmnxChassisNotification 169 }

tmnxIPv6FilterEgrOverload        NOTIFICATION-TYPE
    OBJECTS     {
        tmnxHwClass,
        tmnxChassisNotifyCardSlotNum,
        tmnxChassisNotifyFpNum
    }
    STATUS      current
    DESCRIPTION
        "[CAUSE] The tmnxIPv6FilterEgrOverload notification is generated when
         an egress IPv6 ACL Filter policy is in overload on an FP.

         [EFFECT] The impacted egress IPv6 ACL Filter policy on the affected FP
         will not work as expected, because not all entries are programmed.

         [RECOVERY] Identify the impacted egress IPv6 ACL Filter policy, policy
         entries, and FPs using the appropriate tools commands. Remove or
         modify policy entries or changed the policy assigned to the impacted
         FPs until the overload condition is cleared."
    ::= { tmnxChassisNotification 170 }

tmnxIPv6FilterEgrOverloadClear   NOTIFICATION-TYPE
    OBJECTS     {
        tmnxHwClass,
        tmnxChassisNotifyCardSlotNum,
        tmnxChassisNotifyFpNum
    }
    STATUS      current
    DESCRIPTION
        "[CAUSE] The tmnxIPv6FilterEgrOverloadClear notification is generated
         when egress IPv6 ACL Filter policies are no longer in overload on an
         FP.

         [EFFECT] The egress IPv6 ACL Filter policies on the affected FP will
         work as expected, because all entries are programmed.

         [RECOVERY] No recovery required."
    ::= { tmnxChassisNotification 171 }

tmnxIPMacCpmFilterOverload       NOTIFICATION-TYPE
    OBJECTS     {
        tmnxHwClass,
        tmnxChassisNotifyCpmCardSlotNum,
        tmnxChassisNotifyFpNum
    }
    STATUS      current
    DESCRIPTION
        "[CAUSE] The tmnxIPMacCpmFilterOverload notification is generated when
         an IPv4 or MAC CPM Filter policy is in overload on an FP.

         [EFFECT] The impacted IPv4 or MAC CPM Filter policy on the affected FP
         will not work as expected, because not all entries are programmed.

         [RECOVERY] Identify the impacted IPv4 or MAC CPM Filter policy, policy
         entries, and FPs using the appropriate tools commands. Remove or
         modify policy entries or change the policy assigned to the impacted
         FPs until the overload condition is cleared."
    ::= { tmnxChassisNotification 172 }

tmnxIPMacCpmFilterOverloadClear  NOTIFICATION-TYPE
    OBJECTS     {
        tmnxHwClass,
        tmnxChassisNotifyCpmCardSlotNum,
        tmnxChassisNotifyFpNum
    }
    STATUS      current
    DESCRIPTION
        "[CAUSE] The tmnxIPMacCpmFilterOverloadClear notification is generated
         when IPv4 or MAC CPM Filter policies are no longer in overload on an
         FP.

         [EFFECT] The IPv4 or MAC CPM Filter policies on the affected FP will
         work as expected, because all entries are programmed.

         [RECOVERY] No recovery required."
    ::= { tmnxChassisNotification 173 }

tmnxIPv6CpmFilterOverload        NOTIFICATION-TYPE
    OBJECTS     {
        tmnxHwClass,
        tmnxChassisNotifyCpmCardSlotNum,
        tmnxChassisNotifyFpNum
    }
    STATUS      current
    DESCRIPTION
        "[CAUSE] The tmnxIPv6CpmFilterOverload notification is generated when
         an IPv6 CPM Filter policy is in overload on an FP.

         [EFFECT] The impacted IPv6 CPM Filter policy on the affected FP will
         not work as expected, because not all entries are programmed.

         [RECOVERY] Identify the impacted IPv6 CPM Filter policy, policy
         entries, and FPs using the appropriate tools commands. Remove or
         modify policy entries or change the policy assigned to the impacted
         FPs until the overload condition is cleared."
    ::= { tmnxChassisNotification 174 }

tmnxIPv6CpmFilterOverloadClear   NOTIFICATION-TYPE
    OBJECTS     {
        tmnxHwClass,
        tmnxChassisNotifyCpmCardSlotNum,
        tmnxChassisNotifyFpNum
    }
    STATUS      current
    DESCRIPTION
        "[CAUSE] The tmnxIPv6CpmFilterOverloadClear notification is generated
         when IPv6 CPM Filter policies are no longer in overload on an FP.

         [EFFECT] The IPv6 CPM Filter policies on the affected FP will work as
         expected, because all entries are programmed.

         [RECOVERY] No recovery required."
    ::= { tmnxChassisNotification 175 }

tmnxBluetoothModuleConnectionChg NOTIFICATION-TYPE
    OBJECTS     {
        tmnxChassisNotifyCpmCardSlotNum,
        tmnxBluetoothModuleConnected,
        tmnxBluetoothModuleConnectedMac
    }
    STATUS      obsolete
    DESCRIPTION
        "[CAUSE] The tmnxBluetoothModuleConnectionChg notification is generated
         when a remote Bluetooth device connects with or disconnects from the
         indicated Bluetooth module.

         [EFFECT] A Bluetooth device has connected with or disconnected from a
         Bluetooth module.

         [RECOVERY] No recovery required."
    ::= { tmnxChassisNotification 178 }

tmnxGnssAcquiringFix             NOTIFICATION-TYPE
    OBJECTS     {
        tmnxHwClass,
        tmnxGnssPositionValid
    }
    STATUS      current
    DESCRIPTION
        "[CAUSE] The tmnxGnssAcquiringFix notification is generated when the
         GNSS receiver starts to acquire a fix.  This occurs when the GNSS
         receiver is enabled, and also when the GNSS receiver loses its fix.

         [EFFECT] The position of the system is unknown until the receiver
         acquires a fix.

         [RECOVERY] Ensure that the GNSS antenna is properly connected to the
         system."
    ::= { tmnxChassisNotification 179 }

tmnxGnssAcquiredFix              NOTIFICATION-TYPE
    OBJECTS     {
        tmnxHwClass,
        tmnxGnssPositionValid
    }
    STATUS      current
    DESCRIPTION
        "[CAUSE] The tmnxGnssAcquiredFix notification is generated when the
         GNSS receiver has acquired a valid fix on its position.

         [EFFECT] The position of the system is known.

         [RECOVERY] None needed"
    ::= { tmnxChassisNotification 180 }

tmnxPhysChassisPMOutFail         NOTIFICATION-TYPE
    OBJECTS     {
        tmnxHwClass,
        tmnxPhysChassisPMOutputStatus
    }
    STATUS      current
    DESCRIPTION
        "[CAUSE] The tmnxPhysChassisPMOutFail notification is generated when an
         output failure occurs on the power module.

         [EFFECT] The power module is no longer operational.

         [RECOVERY] Insert a new power module."
    ::= { tmnxChassisNotification 189 }

tmnxPhysChassisPMOutFailClr      NOTIFICATION-TYPE
    OBJECTS     {
        tmnxHwClass,
        tmnxPhysChassisPMOutputStatus
    }
    STATUS      current
    DESCRIPTION
        "[CAUSE] The tmnxPhysChassisPMOutFailClr notification is generated when
         an output failure is cleared on the power module.

         [EFFECT] The power module is operational again.

         [RECOVERY] There is no recovery for this notification."
    ::= { tmnxChassisNotification 190 }

tmnxPhysChassisPMInputFeed       NOTIFICATION-TYPE
    OBJECTS     {
        tmnxHwClass,
        tmnxPhysChassisPMInputFeedDown
    }
    STATUS      current
    DESCRIPTION
        "[CAUSE] The tmnxPhysChassisPMInputFeed notification is generated if
         any one of the input feeds for a given power module is not supplying
         power.

         [EFFECT] There is an increased risk of system power brownouts or
         blackouts.

         [RECOVERY] Restore all of the input feeds that are not supplying
         power."
    ::= { tmnxChassisNotification 191 }

tmnxPhysChassisPMInputFeedClr    NOTIFICATION-TYPE
    OBJECTS     {
        tmnxHwClass,
        tmnxPhysChassisPMInputFeedDown
    }
    STATUS      current
    DESCRIPTION
        "[CAUSE] The tmnxPhysChassPwrSupInputFeedClr notification is generated
         when the last of the missing input feeds has been brought back online.

         [EFFECT] All power module input feeds are supplying power.

         [RECOVERY] No recovery required."
    ::= { tmnxChassisNotification 192 }

tmnxPhysChassisFilterDoorOpen    NOTIFICATION-TYPE
    OBJECTS     {
        tmnxHwClass
    }
    STATUS      current
    DESCRIPTION
        "[CAUSE] The tmnxPhysChassisFilterDoorOpen notification is generated
         when the filter door is either open or not present.

         [EFFECT] Power shelf protection may be compromised.

         [RECOVERY] If the filter door is not installed, install it. Close the
         filter door."
    ::= { tmnxChassisNotification 193 }

tmnxPhysChassisFilterDoorClosed  NOTIFICATION-TYPE
    OBJECTS     {
        tmnxHwClass
    }
    STATUS      current
    DESCRIPTION
        "[CAUSE] The tmnxPhysChassisFilterDoorClosed notification is generated
         when the filter door is present and closed.

         [EFFECT] The power shelves are protected by the closed door.

         [RECOVERY] No recovery required."
    ::= { tmnxChassisNotification 194 }

tmnxPhysChassisPMOverTemp        NOTIFICATION-TYPE
    OBJECTS     {
        tmnxHwClass,
        tmnxHwTemperature,
        tmnxHwTempThreshold
    }
    STATUS      current
    DESCRIPTION
        "[CAUSE] The tmnxPhysChassisPMOverTemp notification is generated when a
         power module's temperature surpasses the temperature threshold.

         [EFFECT] The power module is no longer operational.

         [RECOVERY] Check input feed and/or insert a new power module."
    ::= { tmnxChassisNotification 195 }

tmnxPhysChassisPMOverTempClr     NOTIFICATION-TYPE
    OBJECTS     {
        tmnxHwClass,
        tmnxHwTemperature,
        tmnxHwTempThreshold
    }
    STATUS      current
    DESCRIPTION
        "[CAUSE] The tmnxPhysChassisPMOverTempClr notification is generated
         when a power module's temperature is reduced below the temperature
         threshold.

         [EFFECT] The power module is operational again.

         [RECOVERY] There is no recovery for this notification."
    ::= { tmnxChassisNotification 196 }

tmnxIPMacFilterIngNearFull       NOTIFICATION-TYPE
    OBJECTS     {
        tmnxHwClass,
        tmnxChassisNotifyCardSlotNum,
        tmnxChassisNotifyFpNum
    }
    STATUS      current
    DESCRIPTION
        "[CAUSE] The tmnxIPMacFilterIngNearFull notification is generated when
         an ingress IPv4 or MAC ACL Filter policies are near full utilization
         on an FP.

         [EFFECT] There is no operational impact due to this event.

         [RECOVERY] None required."
    ::= { tmnxChassisNotification 197 }

tmnxIPMacFilterIngNearFullClear  NOTIFICATION-TYPE
    OBJECTS     {
        tmnxHwClass,
        tmnxChassisNotifyCardSlotNum,
        tmnxChassisNotifyFpNum
    }
    STATUS      current
    DESCRIPTION
        "[CAUSE] The tmnxIPMacFilterIngNearFullClear notification is generated
         when ingress IPv4 or MAC ACL Filter policies are no longer near full
         utilization on an FP.

         [EFFECT] There is no operational impact due to this event.

         [RECOVERY] None required."
    ::= { tmnxChassisNotification 198 }

tmnxIPMacFilterEgrNearFull       NOTIFICATION-TYPE
    OBJECTS     {
        tmnxHwClass,
        tmnxChassisNotifyCardSlotNum,
        tmnxChassisNotifyFpNum
    }
    STATUS      current
    DESCRIPTION
        "[CAUSE] The tmnxIPMacFilterEgrNearFull notification is generated when
         an egress IPv4 or MAC ACL Filter policies are near full utilization on
         an FP.

         [EFFECT] There is no operational impact due to this event.

         [RECOVERY] None required."
    ::= { tmnxChassisNotification 199 }

tmnxIPMacFilterEgrNearFullClear  NOTIFICATION-TYPE
    OBJECTS     {
        tmnxHwClass,
        tmnxChassisNotifyCardSlotNum,
        tmnxChassisNotifyFpNum
    }
    STATUS      current
    DESCRIPTION
        "[CAUSE] The tmnxIPMacFilterEgrNearFullClear notification is generated
         when egress IPv4 or MAC ACL Filter policies are no longer near full
         utilization on an FP.

         [EFFECT] There is no operational impact due to this event.

         [RECOVERY] None required."
    ::= { tmnxChassisNotification 200 }

tmnxIPv6FilterIngNearFull        NOTIFICATION-TYPE
    OBJECTS     {
        tmnxHwClass,
        tmnxChassisNotifyCardSlotNum,
        tmnxChassisNotifyFpNum
    }
    STATUS      current
    DESCRIPTION
        "[CAUSE] The tmnxIPv6FilterIngNearFull notification is generated when
         an ingress IPv6 ACL Filter policies are near full utilization on an
         FP.

         [EFFECT] There is no operational impact due to this event.

         [RECOVERY] None required."
    ::= { tmnxChassisNotification 201 }

tmnxIPv6FilterIngNearFullClear   NOTIFICATION-TYPE
    OBJECTS     {
        tmnxHwClass,
        tmnxChassisNotifyCardSlotNum,
        tmnxChassisNotifyFpNum
    }
    STATUS      current
    DESCRIPTION
        "[CAUSE] The tmnxIPv6FilterIngNearFullClear notification is generated
         when ingress IPv6 ACL Filter policies are no longer near full
         utilization on an FP.

         [EFFECT] There is no operational impact due to this event.

         [RECOVERY] None required."
    ::= { tmnxChassisNotification 202 }

tmnxIPv6FilterEgrNearFull        NOTIFICATION-TYPE
    OBJECTS     {
        tmnxHwClass,
        tmnxChassisNotifyCardSlotNum,
        tmnxChassisNotifyFpNum
    }
    STATUS      current
    DESCRIPTION
        "[CAUSE] The tmnxIPv6FilterEgrNearFull notification is generated when
         an egress IPv6 ACL Filter policies are near full utilization on an FP.

         [EFFECT] There is no operational impact due to this event.

         [RECOVERY] None required."
    ::= { tmnxChassisNotification 203 }

tmnxIPv6FilterEgrNearFullClear   NOTIFICATION-TYPE
    OBJECTS     {
        tmnxHwClass,
        tmnxChassisNotifyCardSlotNum,
        tmnxChassisNotifyFpNum
    }
    STATUS      current
    DESCRIPTION
        "[CAUSE] The tmnxIPv6FilterEgrNearFullClear notification is generated
         when egress IPv6 ACL Filter policies are no longer near full
         utilization on an FP.

         [EFFECT] There is no operational impact due to this event.

         [RECOVERY] None required."
    ::= { tmnxChassisNotification 204 }

tmnxEqFpgaSoftError              NOTIFICATION-TYPE
    OBJECTS     {
        tmnxHwID,
        tmnxHwClass
    }
    STATUS      current
    DESCRIPTION
        "[CAUSE] The tmnxEqFpgaSoftError notification is for experimental use
         only and should remain suppressed unless advised otherwise by Nokia
         customer support.

         [EFFECT] Contact Nokia customer support.

         [RECOVERY] Contact Nokia customer support."
    ::= { tmnxChassisNotification 211 }

tmnxEqSyncIfTimingSyncEQuality   NOTIFICATION-TYPE
    OBJECTS     {
        tmnxSyncIfTimingSyncERxQltyLevel
    }
    STATUS      current
    DESCRIPTION
        "Generated when there is a change of the received quality level on
         timing reference synce."
    ::= { tmnxChassisNotification 212 }

tmnxEqSyncIfTimingSyncE2Quality  NOTIFICATION-TYPE
    OBJECTS     {
        tmnxSyncIfTimingSyncE2RxQltyLevl
    }
    STATUS      current
    DESCRIPTION
        "Generated when there is a change of the received quality level on
         timing reference synce2."
    ::= { tmnxChassisNotification 213 }

tmnxEqSyncIfTimingSyncEAlarm     NOTIFICATION-TYPE
    OBJECTS     {
        tmnxChassisNotifyHwIndex,
        tmnxHwID,
        tmnxHwClass,
        tmnxSyncIfTimingNotifyAlarm
    }
    STATUS      current
    DESCRIPTION
        "Generated when an alarm condition on the SYNCE timing reference is
         detected. This notification will have the same indices as those of the
         tmnxCpmCardTable."
    ::= { tmnxChassisNotification 214 }

tmnxEqSyncIfTimingSyncEAlarmClr  NOTIFICATION-TYPE
    OBJECTS     {
        tmnxChassisNotifyHwIndex,
        tmnxHwID,
        tmnxHwClass,
        tmnxSyncIfTimingNotifyAlarm
    }
    STATUS      current
    DESCRIPTION
        "Generated when an alarm condition on the SYNCE timing reference is
         cleared. This notification will have the same indices as those of the
         tmnxCpmCardTable."
    ::= { tmnxChassisNotification 215 }

tmnxEqSyncIfTimingSyncE2Alarm    NOTIFICATION-TYPE
    OBJECTS     {
        tmnxChassisNotifyHwIndex,
        tmnxHwID,
        tmnxHwClass,
        tmnxSyncIfTimingNotifyAlarm
    }
    STATUS      current
    DESCRIPTION
        "Generated when an alarm condition on the SYNCE 2 timing reference is
         detected. This notification will have the same indices as those of the
         tmnxCpmCardTable."
    ::= { tmnxChassisNotification 216 }

tmnxEqSyncIfTimingSyncE2AlarmClr NOTIFICATION-TYPE
    OBJECTS     {
        tmnxChassisNotifyHwIndex,
        tmnxHwID,
        tmnxHwClass,
        tmnxSyncIfTimingNotifyAlarm
    }
    STATUS      current
    DESCRIPTION
        "Generated when an alarm condition on the SYNCE 2 timing reference is
         cleared. This notification will have the same indices as those of the
         tmnxCpmCardTable."
    ::= { tmnxChassisNotification 217 }

tmnxEqHwEventDetected            NOTIFICATION-TYPE
    OBJECTS     {
        tmnxChassisNotifyHwIndex,
        tmnxHwID,
        tmnxHwClass,
        tmnxEqNotifyHwEventType,
        tmnxEqNotifyHwEventDetail,
        tmnxEqNotifyHwEventAction
    }
    STATUS      current
    DESCRIPTION
        "[CAUSE] The tmnxEqHwEventDetected notification is generated when
         events or errors being monitored are detected by hardware component.

         [EFFECT] The system will perform the configured action on the hardware
         component as indicated by tmnxEqNotifyHwEventAction.

         [RECOVERY] Check hardware component."
    ::= { tmnxChassisNotification 218 }

tmnxTunnelGrpEsaVmActivity       NOTIFICATION-TYPE
    OBJECTS     {
        tmnxTunnelGrpEsaVmGroupAssoc,
        tmnxTunnelGrpEsaVmActive
    }
    STATUS      current
    DESCRIPTION
        "The tmnxTunnelGrpEsaVmActivity notification is generated when a
         tunnel-capable ESA virtual machine that is associated with a tunnel
         group becomes active or inactive within its group."
    ::= { tmnxChassisNotification 219 }

tmnxEsaDiscovered                NOTIFICATION-TYPE
    OBJECTS     {
        tmnxEsaNotifyId
    }
    STATUS      current
    DESCRIPTION
        "The tmnxEsaDiscovered notification is generated when a new ESA is
         discovered by the system. This happens when an initial dhcp request is
         received on the configured ESA host port."
    ::= { tmnxChassisNotification 220 }

tmnxEsaConnected                 NOTIFICATION-TYPE
    OBJECTS     {
        tmnxEsaNotifyId
    }
    STATUS      current
    DESCRIPTION
        "The tmnxEsaConnected notification is generated when the ESA boots
         successfully and the system can communicate with the ESA."
    ::= { tmnxChassisNotification 221 }

tmnxEsaDisconnected              NOTIFICATION-TYPE
    OBJECTS     {
        tmnxEsaNotifyId
    }
    STATUS      current
    DESCRIPTION
        "The tmnxEsaDisconnected notification is generated when the ESA is
         unprovisioned (i.e. host port unassigned)."
    ::= { tmnxChassisNotification 222 }

tmnxEsaFailure                   NOTIFICATION-TYPE
    OBJECTS     {
        tmnxEsaNotifyId,
        tmnxEsaStatsOperFlags
    }
    STATUS      current
    DESCRIPTION
        "The tmnxEsaFailure notification is generated when a failure occurs on
         an ESA. There are several reasons that cause a failure, including
         losing communications with the ESA, detecting an incompatible ESA, or
         firmware upgrade failure."
    ::= { tmnxChassisNotification 223 }

tmnxEsaCleared                   NOTIFICATION-TYPE
    OBJECTS     {
        tmnxEsaNotifyId
    }
    STATUS      current
    DESCRIPTION
        "The tmnxEsaCleared notification is generated when an ESA is cleared or
         rebooted. A manual clear of the ESA will generate this notification."
    ::= { tmnxChassisNotification 224 }

tmnxEsaVmCreated                 NOTIFICATION-TYPE
    OBJECTS     {
        tmnxEsaNotifyId,
        tmnxEsaVmNotifyId
    }
    STATUS      current
    DESCRIPTION
        "The tmnxEsaVmCreated notification is generated when an ESA VM is
         created."
    ::= { tmnxChassisNotification 225 }

tmnxEsaVmBooted                  NOTIFICATION-TYPE
    OBJECTS     {
        tmnxEsaNotifyId,
        tmnxEsaVmNotifyId
    }
    STATUS      current
    DESCRIPTION
        "The tmnxEsaVmBooted notification is generated when an ESA VM is
         booted."
    ::= { tmnxChassisNotification 226 }

tmnxEsaVmRemoved                 NOTIFICATION-TYPE
    OBJECTS     {
        tmnxEsaNotifyId,
        tmnxEsaVmNotifyId
    }
    STATUS      current
    DESCRIPTION
        "The tmnxEsaVmRemoved notification is generated when an ESA VM is
         removed from the ESA, as a result of it being unprovisioned (i.e. host
         port or type unassigned) or unequipped (i.e. memory or cores
         unassigned)."
    ::= { tmnxChassisNotification 227 }

tmnxEsaVmCleared                 NOTIFICATION-TYPE
    OBJECTS     {
        tmnxEsaNotifyId,
        tmnxEsaVmNotifyId
    }
    STATUS      current
    DESCRIPTION
        "The tmnxEsaVmCleared notification is generated when an ESA VM is
         cleared or restarted. A manual clear of the esa-vm will generate this
         notification."
    ::= { tmnxChassisNotification 228 }

tmnxEsaVmFailure                 NOTIFICATION-TYPE
    OBJECTS     {
        tmnxEsaNotifyId,
        tmnxEsaVmNotifyId,
        tmnxEsaVmStatsOperFlags
    }
    STATUS      current
    DESCRIPTION
        "The tmnxEsaVmFailure notification is generated when an ESA VM is
         declared failed. This could be for any of the reasons listed in
         tmnxEsaVmStatsOperFlags, other than adminDown."
    ::= { tmnxChassisNotification 229 }

tIPsecEsaVmMemLowWatermark       NOTIFICATION-TYPE
    OBJECTS     {
        tmnxEsaNotifyId,
        tmnxEsaVmNotifyId
    }
    STATUS      current
    DESCRIPTION
        "[CAUSE] A tIPsecEsaVmMemLowWatermark notification is generated when
         the ESA VM memory usage ratio has dropped back to the normal level.

         [EFFECT] The system accepts new IKE states.

         [RECOVERY] There is no recovery required for this notification."
    ::= { tmnxChassisNotification 230 }

tIPsecEsaVmMemHighWatermark      NOTIFICATION-TYPE
    OBJECTS     {
        tmnxEsaNotifyId,
        tmnxEsaVmNotifyId
    }
    STATUS      current
    DESCRIPTION
        "[CAUSE] A tIPsecEsaVmMemHighWatermark notification is generated when
         the ESA VM memory usage ratio has almost reached the maximum value.

         [EFFECT] The system may stop accepting new IKE states shortly.

         [RECOVERY] Use fewer SAs for each IKE tunnel."
    ::= { tmnxChassisNotification 231 }

tmnxPeKernelVersionMismatch      NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "[CAUSE] This notification is generated when there is a mismatch
         between the software version of the host kernel software and the CPM
         software.

         This may occur if the user updates the system software without
         following the recommended software upgrade procedures.

         The object tmnxChassisNotifyHwIndex identifies the CPM card.  The
         object tmnxChassisNotifyMismatchedVer contains the version of
         the host kernel software and tmnxHwSoftwareCodeVersion contains the
         version of the CPM software.

         This notification is only applicable to systems that use both host
         kernel software and CPM software, such as the 7705 SAR-Hm and the 7250
         IXR-s.

         [EFFECT] Although the system may appear to work properly, the behavior
         of the system in this state is undefined.  Using mismatched versions of
         host kernel software and CPM software is not supported.

         [RECOVERY] Follow the recommended software upgrade procedures to
         update the host kernel software and CPM software to the desired
         software release."
    ::= { tmnxChassisNotification 232 }

tmnxFPResourcePolicyModified     NOTIFICATION-TYPE
    OBJECTS     {
        tmnxHwClass,
        tmnxChassisNotifyFpNum
    }
    STATUS      current
    DESCRIPTION
        "[CAUSE] The FP resource policy applied to the FP has been modified, or
         a different FP resource policy is applied to the FP.

         [EFFECT] Modifying the configuration could result in a failure to
         instantiate queues.

         [RECOVERY] The configuration must be saved and the system rebooted
         immediately."
    ::= { tmnxChassisNotification 233 }

tmnxFPResourcePolicyModifiedClr  NOTIFICATION-TYPE
    OBJECTS     {
        tmnxHwClass,
        tmnxChassisNotifyFpNum
    }
    STATUS      current
    DESCRIPTION
        "[CAUSE] Generates a notification when tmnxFPResourcePolicyModified is
         cleared.

         [EFFECT] None.

         [RECOVERY] None."
    ::= { tmnxChassisNotification 234 }

tmnxEqSyncIfTimingGnssQuality    NOTIFICATION-TYPE
    OBJECTS     {
        tmnxSyncIfTimingGnssRxQltyLevel
    }
    STATUS      current
    DESCRIPTION
        "Generated when there is a change of the received quality level on
         timing reference gnss."
    ::= { tmnxChassisNotification 235 }

tmnxEqSyncIfTimingGnss2Quality   NOTIFICATION-TYPE
    OBJECTS     {
        tmnxSyncIfTimingGnss2RxQltyLevel
    }
    STATUS      current
    DESCRIPTION
        "Generated when there is a change of the received quality level on
         timing reference gnss2."
    ::= { tmnxChassisNotification 236 }

tmnxEqSyncIfTimingGnssAlarm      NOTIFICATION-TYPE
    OBJECTS     {
        tmnxChassisNotifyHwIndex,
        tmnxHwID,
        tmnxHwClass,
        tmnxSyncIfTimingNotifyAlarm
    }
    STATUS      current
    DESCRIPTION
        "[CAUSE] Generated when an alarm condition on the gnss timing reference
         is detected. The type of alarm (los, oof, etc) is indicated in the
         details of the log event or alarm, and is also available in the
         tmnxSyncIfTimingNotifyAlarm attribute included in the SNMP
         notification. The SNMP notification will have the same indices as
         those of the tmnxCpmCardTable.

         [EFFECT] Timing reference gnss cannot be used as a source of timing
         into the central clock.

         [RECOVERY] Address issues with the signal associated with timing
         reference gnss."
    ::= { tmnxChassisNotification 237 }

tmnxEqSyncIfTimingGnss2Alarm     NOTIFICATION-TYPE
    OBJECTS     {
        tmnxChassisNotifyHwIndex,
        tmnxHwID,
        tmnxHwClass,
        tmnxSyncIfTimingNotifyAlarm
    }
    STATUS      current
    DESCRIPTION
        "[CAUSE] Generated when an alarm condition on the gnss2 timing
         reference is detected. The type of alarm (los, oof, etc) is indicated
         in the details of the log event or alarm, and is also available in the
         tmnxSyncIfTimingNotifyAlarm attribute included in the SNMP
         notification. The SNMP notification will have the same indices as
         those of the tmnxCpmCardTable.

         [EFFECT] Timing reference gnss2 cannot be used as a source of timing
         into the central clock.

         [RECOVERY] Address issues with the signal associated with timing
         reference gnss2."
    ::= { tmnxChassisNotification 238 }

tmnxEqSyncIfTimingGnssAlarmClr   NOTIFICATION-TYPE
    OBJECTS     {
        tmnxChassisNotifyHwIndex,
        tmnxHwID,
        tmnxHwClass,
        tmnxSyncIfTimingNotifyAlarm
    }
    STATUS      current
    DESCRIPTION
        "Generated when an alarm condition on the gnss timing reference is
         cleared. This notification will have the same indices as those of the
         tmnxCpmCardTable."
    ::= { tmnxChassisNotification 239 }

tmnxEqSyncIfTimingGnss2AlarmClr  NOTIFICATION-TYPE
    OBJECTS     {
        tmnxChassisNotifyHwIndex,
        tmnxHwID,
        tmnxHwClass,
        tmnxSyncIfTimingNotifyAlarm
    }
    STATUS      current
    DESCRIPTION
        "Generated when an alarm condition on the gnss2 timing reference is
         cleared. This notification will have the same indices as those of the
         tmnxCpmCardTable."
    ::= { tmnxChassisNotification 240 }

tmnxEsaFirmwareUpgradeStarted    NOTIFICATION-TYPE
    OBJECTS     {
        tmnxEsaNotifyId
    }
    STATUS      current
    DESCRIPTION
        "The tmnxEsaFirmwareUpgradeStarted notification is generated when an
         ESA requests a firmware upgrade and is in progress."
    ::= { tmnxChassisNotification 241 }

tmnxPlcyAcctPlcrPoolExcResource  NOTIFICATION-TYPE
    OBJECTS     {
        tmnxFPPlcyAcctPolicerLimit,
        tmnxFPPlcyAcctPolicerInUse
    }
    STATUS      current
    DESCRIPTION
        "[CAUSE] The tmnxPlcyAcctPlcrPoolExcResource notification is generated
         when the number of in-use policer resource usage as specified by
         tmnxFPPlcyAcctPolicerInUse exceeds 95 percent of the policer limit as
         specified by tmnxFPPlcyAcctPolicerLimit.

         [EFFECT] The affected device may not provide accurate and complete
         statistics.

         [RECOVERY] There is no recovery required for this notification."
    ::= { tmnxChassisNotification 242 }

tmnxPlcyAcctPlcrPoolLowResource  NOTIFICATION-TYPE
    OBJECTS     {
        tmnxFPPlcyAcctPolicerLimit,
        tmnxFPPlcyAcctPolicerInUse
    }
    STATUS      current
    DESCRIPTION
        "[CAUSE] The tmnxPlcyAcctPlcrPoolLowResource notification is generated
         when the number of in-use policer resource as specified by
         tmnxFPPlcyAcctPolicerInUse is below 85 percent of the policer limit as
         specified by tmnxFPPlcyAcctPolicerLimit.

         [EFFECT] The configured policer limit is cleared when the number of
         in-use policer resources falls below 85 percent of the policer limit.

         [RECOVERY] There is no recovery required for this notification."
    ::= { tmnxChassisNotification 243 }

tChassisAirflowDirMismatch       NOTIFICATION-TYPE
    OBJECTS     {
        tmnxChassisNotifyHwIndex,
        tmnxHwID,
        tmnxHwClass
    }
    STATUS      current
    DESCRIPTION
        "[CAUSE] The tChassisAirflowDirMismatch notification is generated when
         airflow direction is not identical for all chassis fans and
         power-supply fans equipped by the physical chassis.

         [EFFECT] Mismatched airflow direction among fans may cause increased
         temperature, intermittent errors, and could damage components.

         [RECOVERY] The operator must identify a single preferred airflow
         direction, remove any chassis fans and power-supply fans which do not
         match it, and replace them with equipment having fans of the preferred
         airflow direction."
    ::= { tmnxChassisNotification 244 }

tChassisAirflowDirMismatchClr    NOTIFICATION-TYPE
    OBJECTS     {
        tmnxChassisNotifyHwIndex,
        tmnxHwID,
        tmnxHwClass
    }
    STATUS      current
    DESCRIPTION
        "The tChassisAirflowDirMismatchClr notification is generated to
         indicate that all chassis fans and power-supply fans with mismatched
         airflow directions have been replaced, and all chassis-fans and
         power-supply fans share the same direction."
    ::= { tmnxChassisNotification 245 }

tChassisPowerSupplyMismatch      NOTIFICATION-TYPE
    OBJECTS     {
        tmnxChassisNotifyHwIndex,
        tmnxHwID,
        tmnxHwClass
    }
    STATUS      current
    DESCRIPTION
        "[CAUSE] The tChassisPowerSupplyMismatch notification is generated when
         power-supply elements equipped to the physical chassis are not all of
         the same type.

         [EFFECT] There is an increased risk of power-supply failure.
         Intermittent error or damage to components may also result.

         [RECOVERY] The operator must identify a single preferred or required
         power-supply type, remove any power-supply elements of other types,
         and replace them with equipment of the preferred power-supply type."
    ::= { tmnxChassisNotification 246 }

tChassisPowerSupplyMismatchClr   NOTIFICATION-TYPE
    OBJECTS     {
        tmnxChassisNotifyHwIndex,
        tmnxHwID,
        tmnxHwClass
    }
    STATUS      current
    DESCRIPTION
        "The tChassisPowerSupplyMismatchClr notification is generated to
         indicate that all power-supply elements of mismatched types have been
         replaced, and all power-supply elements now share the same type."
    ::= { tmnxChassisNotification 247 }

tChassisPowerSupplyUnsup         NOTIFICATION-TYPE
    OBJECTS     {
        tmnxChassisNotifyHwIndex,
        tmnxHwID,
        tmnxHwClass
    }
    STATUS      current
    DESCRIPTION
        "[CAUSE] The tChassisPowerSupplyUnsup notification is generated when
         power-supply elements equipped to the physical chassis are not of a
         supported type.

         [EFFECT] There is an increased risk of power-supply failure.
         Intermittent error or damage to components may also result.

         [RECOVERY] The operator must identify any equipped power supply
         elements of unsupported type, remove them, and replace them with
         equipment of a supported power-supply type"
    ::= { tmnxChassisNotification 248 }

tmnxIomRsrcUsageHighLimitReached NOTIFICATION-TYPE
    OBJECTS     {
        tmnxChassisNotifyChassisId,
        tmnxChassisNotifyCardSlotNum,
        tmnxChassisNotifyFpNum,
        tmnxIomRsrcTimeEventOccured,
        tmnxIomRsrcResourceType,
        tmnxIomRsrcUsagePercent
    }
    STATUS      current
    DESCRIPTION
        "[CAUSE] The tmnxIomRsrcUsageHighLimitReached notification is generated
         when the utilization of the IOM resource of type
         tmnxIomRsrcResourceType reaches or exceeds the warning high limit.

         [EFFECT] The specified IOM resource is getting close to exhaustion.

         [RECOVERY] There is no recovery required for this notification."
    ::= { tmnxChassisNotification 252 }

tmnxIomRsrcUsageExhausted        NOTIFICATION-TYPE
    OBJECTS     {
        tmnxChassisNotifyChassisId,
        tmnxChassisNotifyCardSlotNum,
        tmnxChassisNotifyFpNum,
        tmnxIomRsrcTimeEventOccured,
        tmnxIomRsrcResourceType,
        tmnxIomRsrcUsagePercent
    }
    STATUS      current
    DESCRIPTION
        "[CAUSE] The tmnxIomRsrcUsageExhausted notification is generated when
         all the IOM resources of type tmnxIomRsrcResourceType have been
         exhausted.

         [EFFECT] The specified IOM resource has reached its limit. Some
         traffic may be affected.

         [RECOVERY] Intervention may be required to recover resources."
    ::= { tmnxChassisNotification 253 }

tmnxIomRsrcUsageRecovered        NOTIFICATION-TYPE
    OBJECTS     {
        tmnxChassisNotifyChassisId,
        tmnxChassisNotifyCardSlotNum,
        tmnxChassisNotifyFpNum,
        tmnxIomRsrcTimeEventOccured,
        tmnxIomRsrcResourceType,
        tmnxIomRsrcUsagePercent
    }
    STATUS      current
    DESCRIPTION
        "[CAUSE] The tmnxIomRsrcUsageRecovered notification is generated when
         the utilization of the IOM resource of type tmnxIomRsrcResourceType
         drops below the warning threshold.

         [EFFECT] The utilization of the specified IOM resource has dropped
         below the warning threshold.

         [RECOVERY] There is no recovery required for this notification."
    ::= { tmnxChassisNotification 254 }

tmnxIomRsrcUserOversubscribed    NOTIFICATION-TYPE
    OBJECTS     {
        tmnxChassisNotifyChassisId,
        tmnxChassisNotifyCardSlotNum,
        tmnxIomRsrcTimeEventOccured,
        tmnxIomRsrcResourceType,
        tmnxIomRsrcUserType
    }
    STATUS      obsolete
    DESCRIPTION
        "[CAUSE] The tmnxIomRsrcUserOversubscribed notification is generated
         when the IOM resource of type tmnxIomRsrcResourceType has been
         exhausted for user tmnxIomRsrcUserType.

         This notification is replaced by tmnxIomRsrcOwnerOversubscribed in
         22.10 and obsoleted in 23.3.

         [EFFECT] Traffic for user tmnxIomRsrcUserType may be affected.

         [RECOVERY] Intervention may be required to recover resources."
    ::= { tmnxChassisNotification 255 }

tmnxIomRsrcUserOversubscribedClr NOTIFICATION-TYPE
    OBJECTS     {
        tmnxChassisNotifyChassisId,
        tmnxChassisNotifyCardSlotNum,
        tmnxIomRsrcTimeEventOccured,
        tmnxIomRsrcResourceType,
        tmnxIomRsrcUserType
    }
    STATUS      obsolete
    DESCRIPTION
        "[CAUSE] The tmnxIomRsrcUserOversubscribedClr notification is generated
         when all the required IOM resources of type tmnxIomRsrcResourceType
         for user tmnxIomRsrcUserType have been allocated.

         This notification is replaced by tmnxIomRsrcOwnerOversubscrbdClr in
         22.10 and obsoleted in 23.3.

         [EFFECT] Traffic for user tmnxIomRsrcUserType is no longer affected.

         [RECOVERY] There is no recovery for this notification."
    ::= { tmnxChassisNotification 256 }

tmnxIomRsrcEventOverflow         NOTIFICATION-TYPE
    OBJECTS     {
        tmnxChassisNotifyChassisId,
        tmnxChassisNotifyCardSlotNum,
        tmnxIomRsrcTimeEventOccured
    }
    STATUS      current
    DESCRIPTION
        "[CAUSE] The tmnxIomRsrcEventOverflow notification is generated when
         tmnxIomRsrcUsageHighLimitReached, tmnxIomRsrcUsageExhausted,
         tmnxIomRsrcUsageRecovered, tmnxIomRsrcOwnerOversubscribed, or
         tmnxIomRsrcOwnerOversubscrbdClr occur more than 200 times because of
         resource usage fluctuation. The IOM raises the final trap to indicate
         overflow and stops logging traps.

         [EFFECT] Some IOM notifications may not be received.

         [RECOVERY] Notifications will resume once the Overflow clear is set."
    ::= { tmnxChassisNotification 257 }

tmnxIomRsrcEventOverflowClr      NOTIFICATION-TYPE
    OBJECTS     {
        tmnxChassisNotifyChassisId,
        tmnxChassisNotifyCardSlotNum,
        tmnxIomRsrcTimeEventOccured,
        tmnxIomRsrcMissingNotifCount
    }
    STATUS      current
    DESCRIPTION
        "[CAUSE] The tmnxIomRsrcEventOverflowClr notification is generated when
         the CPM polls the IOM for traps and the overflow is cleared by logging
         an overflow-clear on a particular card.

         [EFFECT] Notifications are received again since the event throttling
         has ended.

         [RECOVERY] There is no recovery for this notification."
    ::= { tmnxChassisNotification 258 }

tmnxHwAggShpSchedEventOvrflwClr  NOTIFICATION-TYPE
    OBJECTS     {
        tmnxChassisNotifyChassisId,
        tmnxChassisNotifyCardSlotNum,
        tmnxHwAggShpTimeEventOccured,
        tmnxHwAggShpMissingNotifCount
    }
    STATUS      current
    DESCRIPTION
        "[CAUSE] The tmnxHwAggShpSchedEventOvrflwClr notification is generated
         when the CPM polls the IOM for Hw Agg Shaper Scheduler traps and the
         overflow is cleared by logging an overflow-clear on a particular card.

         [EFFECT] Notifications are received again since the event throttling
         has ended.

         [RECOVERY] There is no recovery for this notification."
    ::= { tmnxChassisNotification 259 }

tmnxHwAggShpSchedEventOvrflw     NOTIFICATION-TYPE
    OBJECTS     {
        tmnxChassisNotifyChassisId,
        tmnxChassisNotifyCardSlotNum,
        tmnxHwAggShpTimeEventOccured
    }
    STATUS      current
    DESCRIPTION
        "[CAUSE] The tmnxHwAggShpSchedEventOvrflwClr notification is generated
         when HW Agg Shaper Scheduler oper color occurs more than 200 times
         because of Number of agg-shapers parented to a scheduler. The IOM
         raises the final trap to indicate overflow and stops logging traps.

         [EFFECT] Hw Agg shaper scheduler color notifications on the card may
         not be received.

         [RECOVERY] Notifications will resume once the Overflow clear is set."
    ::= { tmnxChassisNotification 260 }

tmnxIomRsrcOwnerOversubscribed   NOTIFICATION-TYPE
    OBJECTS     {
        tmnxChassisNotifyChassisId,
        tmnxChassisNotifyCardSlotNum,
        tmnxIomRsrcTimeEventOccured,
        tmnxIomRsrcResourceType,
        tmnxIomRsrcOwnerType
    }
    STATUS      current
    DESCRIPTION
        "[CAUSE] The tmnxIomRsrcOwnerOversubscribed notification is generated
         when the IOM resource of type tmnxIomRsrcResourceType has been
         exhausted for owner tmnxIomRsrcOwnerType.

         [EFFECT] Traffic for owner tmnxIomRsrcOwnerType may be affected.

         [RECOVERY] Intervention may be required to recover resources."
    ::= { tmnxChassisNotification 261 }

tmnxIomRsrcOwnerOversubscrbdClr  NOTIFICATION-TYPE
    OBJECTS     {
        tmnxChassisNotifyChassisId,
        tmnxChassisNotifyCardSlotNum,
        tmnxIomRsrcTimeEventOccured,
        tmnxIomRsrcResourceType,
        tmnxIomRsrcOwnerType
    }
    STATUS      current
    DESCRIPTION
        "[CAUSE] The tmnxIomRsrcOwnerOversubscrbdClr notification is generated
         when all the required IOM resources of type tmnxIomRsrcResourceType
         for owner tmnxIomRsrcOwnerType have been allocated.

         [EFFECT] Traffic for owner tmnxIomRsrcOwnerType is no longer affected.

         [RECOVERY] There is no recovery for this notification."
    ::= { tmnxChassisNotification 262 }

tmnxFPResOversubscribed          NOTIFICATION-TYPE
    OBJECTS     {
        tFPResOversub
    }
    STATUS      current
    DESCRIPTION
        "[CAUSE] The tmnxFPResOversubscribed notification is generated when one
         or more of the FP resources have been oversubscribed.

         [EFFECT] Usage beyond limits can result in the system dropping packets
         which may cause degradation in service quality.

         [RECOVERY] Reduce traffic load and/or congestion on the system. More
         specific action might be required depending on the specific
         oversubscription."
    ::= { tmnxChassisNotification 263 }

tmnxFPResOversubscribedCleared   NOTIFICATION-TYPE
    OBJECTS     {
        tmnxChassisNotifyCardSlotNum,
        tmnxChassisNotifyFabricSlotNum
    }
    STATUS      current
    DESCRIPTION
        "[CAUSE] The tmnxFPResOversubscribedCleared notification is generated
         when none of the FP resources are oversubscribed.

         [EFFECT] The system returns to normal mode of operation and can
         service all the received traffic in the configured manner.

         [RECOVERY] There is no recovery for this notification."
    ::= { tmnxChassisNotification 264 }

tmnxEsaHwStatusDegraded          NOTIFICATION-TYPE
    OBJECTS     {
        tmnxHwClass
    }
    STATUS      current
    DESCRIPTION
        "[CAUSE] The tmnxEsaHwStatusDegraded notification is generated when one
         or more ESA hardware components are degraded.

         [EFFECT] Service may be affected.

         [RECOVERY] Contact Nokia customer support."
    ::= { tmnxChassisNotification 265 }

tmnxEsaHwStatusDegradedClr       NOTIFICATION-TYPE
    OBJECTS     {
        tmnxHwClass,
        tmnxEsaStatsHardwareStatus
    }
    STATUS      current
    DESCRIPTION
        "[CAUSE] The tmnxEsaHwStatusDegradedClr notification is generated when
         ESA hardware components are no longer degraded."
    ::= { tmnxChassisNotification 266 }

tmnxEsaHwStatusCritical          NOTIFICATION-TYPE
    OBJECTS     {
        tmnxHwClass
    }
    STATUS      current
    DESCRIPTION
        "[CAUSE] The tmnxEsaHwStatusCritical notification is generated when the
         ESA hardware status is critical.

         [EFFECT] Service may be affected.

         [RECOVERY] Contact Nokia customer support."
    ::= { tmnxChassisNotification 267 }

tmnxEsaHwStatusCriticalClr       NOTIFICATION-TYPE
    OBJECTS     {
        tmnxHwClass,
        tmnxEsaStatsHardwareStatus
    }
    STATUS      current
    DESCRIPTION
        "[CAUSE] The tmnxEsaHwStatusCriticalClr notification is generated when
         the ESA hardware status is no longer critical."
    ::= { tmnxChassisNotification 268 }

tmnxEsaHwPwrSup1Degraded         NOTIFICATION-TYPE
    OBJECTS     {
        tmnxHwClass
    }
    STATUS      current
    DESCRIPTION
        "[CAUSE] The tmnxEsaHwPwrSup1Degraded notification is generated when
         the ESA power supply 1 is degraded.

         [EFFECT] Power supply operation and reliability may be affected.

         [RECOVERY] Contact Nokia customer support."
    ::= { tmnxChassisNotification 269 }

tmnxEsaHwPwrSup1DegradedClr      NOTIFICATION-TYPE
    OBJECTS     {
        tmnxHwClass,
        tmnxEsaStatsPowerSupply1Status
    }
    STATUS      current
    DESCRIPTION
        "[CAUSE] The tmnxEsaHwPwrSup1DegradedClr notification is generated when
         the ESA power supply 1 is no longer degraded."
    ::= { tmnxChassisNotification 270 }

tmnxEsaHwPwrSup1Failed           NOTIFICATION-TYPE
    OBJECTS     {
        tmnxHwClass
    }
    STATUS      current
    DESCRIPTION
        "[CAUSE] The tmnxEsaHwPwrSup1Failed notification is generated when the
         ESA power supply 1 fails.

         [EFFECT] Power supply and redundancy are affected. ESA operation may
         be affected.

         [RECOVERY] Contact Nokia customer support."
    ::= { tmnxChassisNotification 271 }

tmnxEsaHwPwrSup1FailedClr        NOTIFICATION-TYPE
    OBJECTS     {
        tmnxHwClass,
        tmnxEsaStatsPowerSupply1Status
    }
    STATUS      current
    DESCRIPTION
        "[CAUSE] The tmnxEsaHwPwrSup1FailedClr notification is generated when
         the ESA power supply 1 is restored."
    ::= { tmnxChassisNotification 272 }

tmnxEsaHwPwrSup2Degraded         NOTIFICATION-TYPE
    OBJECTS     {
        tmnxHwClass
    }
    STATUS      current
    DESCRIPTION
        "[CAUSE] The tmnxEsaHwPwrSup2Degraded notification is generated when
         the ESA power supply 2 is degraded.

         [EFFECT] Power supply operation and reliability may be affected.

         [RECOVERY] Contact Nokia customer support."
    ::= { tmnxChassisNotification 273 }

tmnxEsaHwPwrSup2DegradedClr      NOTIFICATION-TYPE
    OBJECTS     {
        tmnxHwClass,
        tmnxEsaStatsPowerSupply2Status
    }
    STATUS      current
    DESCRIPTION
        "[CAUSE] The tmnxEsaHwPwrSup2DegradedClr notification is generated when
         the ESA power supply 2 is no longer degraded."
    ::= { tmnxChassisNotification 274 }

tmnxEsaHwPwrSup2Failed           NOTIFICATION-TYPE
    OBJECTS     {
        tmnxHwClass
    }
    STATUS      current
    DESCRIPTION
        "[CAUSE] The tmnxEsaHwPwrSup2Failed notification is generated when the
         ESA power supply 2 fails.

         [EFFECT] Power supply and redundancy are affected. ESA operation may
         be affected.

         [RECOVERY] Contact Nokia customer support."
    ::= { tmnxChassisNotification 275 }

tmnxEsaHwPwrSup2FailedClr        NOTIFICATION-TYPE
    OBJECTS     {
        tmnxHwClass,
        tmnxEsaStatsPowerSupply2Status
    }
    STATUS      current
    DESCRIPTION
        "[CAUSE] The tmnxEsaHwPwrSup2FailedClr notification is generated when
         the ESA power supply 2 is restored."
    ::= { tmnxChassisNotification 276 }

tmnxEsaHwFanBankNonRedun         NOTIFICATION-TYPE
    OBJECTS     {
        tmnxHwClass
    }
    STATUS      current
    DESCRIPTION
        "[CAUSE] The tmnxEsaHwFanBankNonRedun notification is generated when a
         condition compromises the ESA fan bank redundancy.

         [EFFECT] ESA cooling may be inadequate if fan failure occurs.

         [RECOVERY] Contact Nokia customer support."
    ::= { tmnxChassisNotification 277 }

tmnxEsaHwFanBankNonRedunClr      NOTIFICATION-TYPE
    OBJECTS     {
        tmnxHwClass,
        tmnxEsaStatsFanRedundancy
    }
    STATUS      current
    DESCRIPTION
        "[CAUSE] The tmnxEsaHwFanBankNonRedunClr notification is generated when
         the ESA fan bank redundancy is restored."
    ::= { tmnxChassisNotification 278 }

tmnxEsaHwFanBankFailRedun        NOTIFICATION-TYPE
    OBJECTS     {
        tmnxHwClass
    }
    STATUS      current
    DESCRIPTION
        "[CAUSE] The tmnxEsaHwFanBankFailRedun notification is generated when
         one or more ESA fans fail, compromising the fan bank redundancy.

         [EFFECT] ESA cooling may be inadequate if fan failure occurs.

         [RECOVERY] Contact Nokia customer support."
    ::= { tmnxChassisNotification 279 }

tmnxEsaHwFanBankFailRedunClr     NOTIFICATION-TYPE
    OBJECTS     {
        tmnxHwClass,
        tmnxEsaStatsFanRedundancy
    }
    STATUS      current
    DESCRIPTION
        "[CAUSE] The tmnxEsaHwFanBankFailRedunClr notification is generated
         when all ESA fans recover, restoring the fan bank redundancy."
    ::= { tmnxChassisNotification 280 }

tmnxEsaHwFanStatusDegraded       NOTIFICATION-TYPE
    OBJECTS     {
        tmnxHwClass
    }
    STATUS      current
    DESCRIPTION
        "[CAUSE] The tmnxEsaHwFanStatusDegraded notification is generated when
         one or more ESA fans are degraded.

         [EFFECT] ESA cooling may be inadequate.

         [RECOVERY] Contact Nokia customer support."
    ::= { tmnxChassisNotification 281 }

tmnxEsaHwFanStatusDegradedClr    NOTIFICATION-TYPE
    OBJECTS     {
        tmnxHwClass,
        tmnxEsaStatsFanStatus
    }
    STATUS      current
    DESCRIPTION
        "[CAUSE] The tmnxEsaHwFanStatusDegradedClr notification is generated
         when ESA fans are no longer degraded."
    ::= { tmnxChassisNotification 282 }

tmnxEsaHwFanStatusFailed         NOTIFICATION-TYPE
    OBJECTS     {
        tmnxHwClass
    }
    STATUS      current
    DESCRIPTION
        "[CAUSE] The tmnxEsaHwFanStatusFailed notification is generated when
         one or more ESA fans fail.

         [EFFECT] ESA cooling may be inadequate.

         [RECOVERY] Contact Nokia customer support."
    ::= { tmnxChassisNotification 283 }

tmnxEsaHwFanStatusFailedClr      NOTIFICATION-TYPE
    OBJECTS     {
        tmnxHwClass,
        tmnxEsaStatsFanStatus
    }
    STATUS      current
    DESCRIPTION
        "[CAUSE] The tmnxEsaHwFanStatusFailedClr notification is generated when
         the ESA fans are restored."
    ::= { tmnxChassisNotification 284 }

tmnxEsaHwPwrSupMismatch          NOTIFICATION-TYPE
    OBJECTS     {
        tmnxHwClass
    }
    STATUS      current
    DESCRIPTION
        "[CAUSE] The tmnxEsaHwPwrSupMismatch notification is generated when the
         ESA power supplies do not match.

         [EFFECT] ESA power supplies must be matched.

         [RECOVERY] Equip the ESA with matching power supplies."
    ::= { tmnxChassisNotification 285 }

tmnxEsaHwPwrSupMismatchClr       NOTIFICATION-TYPE
    OBJECTS     {
        tmnxHwClass,
        tmnxEsaStatsPwrSupMismatchStatus
    }
    STATUS      current
    DESCRIPTION
        "[CAUSE] The tmnxEsaHwPwrSupMismatchClr notification is generated when
         the ESA power supplies are no longer mismatched."
    ::= { tmnxChassisNotification 286 }

tmnxEsaHwPwrSupBankNonRedun      NOTIFICATION-TYPE
    OBJECTS     {
        tmnxHwClass
    }
    STATUS      current
    DESCRIPTION
        "[CAUSE] The tmnxEsaHwPwrSupBankNonRedun notification is generated when
         the ESA power supply redundancy is degraded.

         [EFFECT] ESA may lose power supply redundancy if power supply failures
         occur.

         [RECOVERY] Contact Nokia customer support."
    ::= { tmnxChassisNotification 287 }

tmnxEsaHwPwrSupBankNonRedunClr   NOTIFICATION-TYPE
    OBJECTS     {
        tmnxHwClass,
        tmnxEsaStatsPwrSupRedundancy
    }
    STATUS      current
    DESCRIPTION
        "[CAUSE] The tmnxEsaHwPwrSupBankNonRedunClr notification is generated
         when the ESA power supplies return to a fully redundant state."
    ::= { tmnxChassisNotification 288 }

tmnxEsaHwPwrSupBankFailRedun     NOTIFICATION-TYPE
    OBJECTS     {
        tmnxHwClass
    }
    STATUS      current
    DESCRIPTION
        "[CAUSE] The tmnxEsaHwPwrSupBankFailRedun notification is generated
         when the ESA power supply redundancy fails.

         [EFFECT] ESA operation may be affected if additional power supply
         failures occur.

         [RECOVERY] Contact Nokia customer support."
    ::= { tmnxChassisNotification 289 }

tmnxEsaHwPwrSupBankFailRedunClr  NOTIFICATION-TYPE
    OBJECTS     {
        tmnxHwClass,
        tmnxEsaStatsPwrSupRedundancy
    }
    STATUS      current
    DESCRIPTION
        "[CAUSE] The tmnxEsaHwPwrSupBankFailRedunClr notification is generated
         when the ESA power supplies regain redundancy."
    ::= { tmnxChassisNotification 290 }

tmnxEsaHwTemperatureDegraded     NOTIFICATION-TYPE
    OBJECTS     {
        tmnxHwClass
    }
    STATUS      current
    DESCRIPTION
        "[CAUSE] The tmnxEsaHwTemperatureDegraded notification is generated
         when the ESA temperature is outside the expected operating range.

         [EFFECT] If the ESA temperature remains outside the expected operating
         range, the ESA may shut down.

         [RECOVERY] The ESA may need manual maintenance to rectify the issue.
         Contact Nokia customer support."
    ::= { tmnxChassisNotification 291 }

tmnxEsaHwTemperatureDegradedClr  NOTIFICATION-TYPE
    OBJECTS     {
        tmnxHwClass,
        tmnxEsaStatsTemperatureStatus
    }
    STATUS      current
    DESCRIPTION
        "[CAUSE] The tmnxEsaHwTemperatureDegradedClr notification is generated
         when the ESA returns to a temperature within the expected operating
         range."
    ::= { tmnxChassisNotification 292 }

tmnxEsaHwTemperatureFailed       NOTIFICATION-TYPE
    OBJECTS     {
        tmnxHwClass
    }
    STATUS      current
    DESCRIPTION
        "[CAUSE] The tmnxEsaHwTemperatureFailed notification is generated when
         the ESA temperature is critical.

         [EFFECT] If the ESA temperature remains outside the expected operating
         range, the ESA may shut down.

         [RECOVERY] The ESA may need manual maintenance to rectify the issue.
         Contact Nokia customer support."
    ::= { tmnxChassisNotification 293 }

tmnxEsaHwTemperatureFailedClr    NOTIFICATION-TYPE
    OBJECTS     {
        tmnxHwClass,
        tmnxEsaStatsTemperatureStatus
    }
    STATUS      current
    DESCRIPTION
        "[CAUSE] The tmnxEsaHwTemperatureFailedClr notification is generated
         when the ESA returns to a temperature within the expected operating
         range."
    ::= { tmnxChassisNotification 294 }

tmnxPowerSupplyFanFailed         NOTIFICATION-TYPE
    OBJECTS     {
        tmnxHwClass
    }
    STATUS      current
    DESCRIPTION
        "[CAUSE] The tmnxPowerSupplyFanFailed notification is generated when a
         fan within a particular power-supply has ceased to function normally.

         [EFFECT] Cooling to the power-supply may be reduced, potentially
         leading to overheating.

         [RECOVERY] The power-supply should be replaced by one with
         fully-functioning fan elements."
    ::= { tmnxChassisNotification 295 }

tmnxPowerSupplyFanFailedClear    NOTIFICATION-TYPE
    OBJECTS     {
        tmnxHwClass
    }
    STATUS      current
    DESCRIPTION
        "[CAUSE] The tmnxPowerSupplyFanFailedClear notification is generated
         when the fan component of a power-supply has been restored to normal
         operation."
    ::= { tmnxChassisNotification 296 }

tmnxIxrResourceHighUsage         NOTIFICATION-TYPE
    OBJECTS     {
        tmnxChassisNotifyChassisId,
        tmnxNotifIxrResource,
        tmnxNotifIxrRsrcUtilPercentage
    }
    STATUS      current
    DESCRIPTION
        "[CAUSE] The tmnxIxrResourceHighUsage notification is generated when
         the number of allocated resources reaches or exceeds the warning high
         limit.

         [EFFECT] The specified resource is getting close to exhaustion.

         [RECOVERY] There is no recovery required for this notification."
    ::= { tmnxChassisNotification 297 }

tmnxIxrResourceExhausted         NOTIFICATION-TYPE
    OBJECTS     {
        tmnxChassisNotifyChassisId,
        tmnxNotifIxrResource
    }
    STATUS      current
    DESCRIPTION
        "[CAUSE] The tmnxIxrResourceExhausted notification is generated when
         the utilization of the resource specified by tmnxNotifIxrResource has
         reached its limit.

         [EFFECT] The utilization of the specified resource has reached its
         limit.

         [RECOVERY] Intervention may be required to recover resources."
    ::= { tmnxChassisNotification 298 }

tmnxIxrResourceRecovered         NOTIFICATION-TYPE
    OBJECTS     {
        tmnxChassisNotifyChassisId,
        tmnxNotifIxrResource,
        tmnxNotifIxrRsrcUtilPercentage
    }
    STATUS      current
    DESCRIPTION
        "[CAUSE] The tmnxIxrResourceRecovered notification is generated when
         the number of allocated resources drops below the warning threshold.
         This trap is generated only if the tmnxIxrResourceHighUsage
         notification or the tmnxIxrResourceExhausted notification had been
         generated.

         [EFFECT] The utilization of the specified resource has dropped below
         the warning threshold.

         [RECOVERY] There is no recovery required for this notification."
    ::= { tmnxChassisNotification 299 }

tmnxIxrResourceHighUsageByOwner  NOTIFICATION-TYPE
    OBJECTS     {
        tmnxChassisNotifyChassisId,
        tmnxNotifIxrResource,
        tmnxNotifIxrResourceOwner,
        tmnxNotifIxrRsrcUtilPercentage
    }
    STATUS      current
    DESCRIPTION
        "[CAUSE] The tmnxIxrResourceHighUsageByOwner notification is generated
         when the number of allocated resources by an owner reaches or exceeds
         the warning high limit.

         [EFFECT] The specified application is getting close to its maximal
         usage of the specified resource.

         [RECOVERY] There is no recovery required for this notification."
    ::= { tmnxChassisNotification 300 }

tmnxIxrResourceExhaustedByOwner  NOTIFICATION-TYPE
    OBJECTS     {
        tmnxChassisNotifyChassisId,
        tmnxNotifIxrResource,
        tmnxNotifIxrResourceOwner
    }
    STATUS      current
    DESCRIPTION
        "[CAUSE] The tmnxIxrResourceExhaustedByOwner notification is generated
         when the utilization of the resource specified by tmnxNotifIxrResource
         reached its limit  for application specified by
         tmnxNotifIxrResourceOwner.

         [EFFECT] Usage of the resource specified by tmnxNotifIxrResource
         reached its limit for application specified by
         tmnxNotifIxrResourceOwner.

         [RECOVERY] Intervention may be required to recover resources."
    ::= { tmnxChassisNotification 301 }

tmnxIxrResourceRecoveredByOwner  NOTIFICATION-TYPE
    OBJECTS     {
        tmnxChassisNotifyChassisId,
        tmnxNotifIxrResource,
        tmnxNotifIxrResourceOwner,
        tmnxNotifIxrRsrcUtilPercentage
    }
    STATUS      current
    DESCRIPTION
        "[CAUSE] The tmnxIxrResourceRecoveredByOwner notification is generated
         when the number of allocated resources by the specified application
         drops below the warning threshold. This trap is generated only if the
         tmnxIxrResourceHighUsageByOwner notification or the
         tmnxIxrResourceExhaustedByOwner notification had been generated.

         [EFFECT] The utilization of the specified resource by a given
         application has dropped below the warning threshold.

         [RECOVERY] There is no recovery required for this notification."
    ::= { tmnxChassisNotification 302 }

tmnxEqCardMissing                NOTIFICATION-TYPE
    OBJECTS     {
        tmnxChassisNotifyHwIndex,
        tmnxHwID,
        tmnxHwClass
    }
    STATUS      current
    DESCRIPTION
        "[CAUSE] The tmnxEqCardMissing notification is generated when the card
         configuration is present but the card is not detected in the slot.

         [EFFECT] The missing card will cause a loss of service for all
         services running on that card.

         [RECOVERY] Before taking any recovery steps collect a tech-support
         file, then try inserting a compatible card into the slot."
    ::= { tmnxChassisNotification 303 }

tmnxEqCardMissingClear           NOTIFICATION-TYPE
    OBJECTS     {
        tmnxChassisNotifyHwIndex,
        tmnxHwID,
        tmnxHwClass
    }
    STATUS      current
    DESCRIPTION
        "[CAUSE] The tmnxEqCardMissingClear notification is generated when the
         card configuration is removed or the card is detected in the slot."
    ::= { tmnxChassisNotification 304 }

tmnxEsaStolenTimeDetected        NOTIFICATION-TYPE
    OBJECTS     {
        tmnxEsaNotifyId
    }
    STATUS      current
    DESCRIPTION
        "[CAUSE] The tmnxEsaStolenTimeDetected notification is generated when
         stolen time monitoring on the ESA detects periods of time that ESA-VMs
         are ready to run,  but are unable to do so. The stolen time is
         reported in ms.

         [EFFECT] If the periods of stolen time exceeds a certain value, they
         may result in ESA-VM reset or temporary loss of connection of the ESA
         with the host node.

         [RECOVERY] Before taking any recovery steps, collect a tech-support
         and consult with support for best recovery method."
    ::= { tmnxChassisNotification 305 }

tmnxEqEsaHostPortCrcAlarm        NOTIFICATION-TYPE
    OBJECTS     {
        tmnxEsaPortNotifyPortId,
        tmnxEsaHostPortNotifCrcThreshold,
        tmnxEsaHostPortNotifCrcMltiplier,
        tmnxEsaHostPortNotifCrcAlrmValue
    }
    STATUS      current
    DESCRIPTION
        "[CAUSE] The tmnxEqEsaHostPortCrcAlarm is generated when an Ethernet
         port CRC alarm condition is detected. It is generated only when the
         type of alarm being raised is enabled on the port.

         [EFFECT] On a signal failure (SF) fault, the port is taken out of
         service until the CRC alarm condition is cleared.

         [RECOVERY] tmnxEqEsaHostPortCrcAlarm is cleared by taking the port out
         of service (e.g. shutdown, card/mda reset, physical link loss), or
         changing/disabling the associated threshold/multiplier values. Signal
         Degradation is self clearing and will clear once the error rate drops
         below 1/10th of the configured rate."
    ::= { tmnxChassisNotification 306 }

tmnxEqEsaHostPortCrcAlarmClear   NOTIFICATION-TYPE
    OBJECTS     {
        tmnxEsaPortNotifyPortId,
        tmnxEsaHostPortNotifCrcThreshold,
        tmnxEsaHostPortNotifCrcMltiplier,
        tmnxEsaHostPortNotifCrcAlrmValue
    }
    STATUS      current
    DESCRIPTION
        "[CAUSE] The tmnxEqEsaHostPortCrcAlarmClear is generated when an
         Ethernet port CRC alarm condition is cleared or disabled."
    ::= { tmnxChassisNotification 307 }

tmnxEsaFirmwareUpgradeInProgress NOTIFICATION-TYPE
    OBJECTS     {
        tmnxEsaNotifyId
    }
    STATUS      current
    DESCRIPTION
        "[CAUSE] The tmnxEsaFirmwareUpgradeInProgress notification is generated
         to indicate the different upgrade stages/devices and the expected ESA
         reboots."
    ::= { tmnxChassisNotification 308 }

tmnxEsaFirmwareUpgradeDone       NOTIFICATION-TYPE
    OBJECTS     {
        tmnxEsaNotifyId
    }
    STATUS      current
    DESCRIPTION
        "[CAUSE] The tmnxEsaFirmwareUpgradeDone notification is generated to
         indicate whenever a certain upgrade stage/device is complete."
    ::= { tmnxChassisNotification 309 }

tmnxEsaFirmwareUpgradeFailed     NOTIFICATION-TYPE
    OBJECTS     {
        tmnxEsaNotifyId
    }
    STATUS      current
    DESCRIPTION
        "[CAUSE] The tmnxEsaFirmwareUpgradeFailed notification is generated to
         indicate that the ESA firmware upgrade did not successfully finish.
         The ESA has one or more devices that still require firmware upgrade.

         [EFFECT] An ESA running with partially upgraded firmware might
         potentially exhibit sub-optimal performance, or other service
         affecting issues.

         [RECOVERY] A manual clear of the esa using the clear esa command, or
         power cycling the ESA would trigger a firmware upgrade to be
         re-attempted."
    ::= { tmnxChassisNotification 310 }

tmnxChassisAntiTheftModeBoot     NOTIFICATION-TYPE
    OBJECTS     {
        tmnxChassisNotifyHwIndex,
        tmnxHwID,
        tmnxHwClass
    }
    STATUS      current
    DESCRIPTION
        "The tmnxChassisAntiTheftModeBoot notification is generated to indicate
         that the system has booted in Anti-Theft mode, and must be unlocked
         before protected features can be used."
    ::= { tmnxChassisNotification 311 }

tmnxChassisAntiTheftUnlocked     NOTIFICATION-TYPE
    OBJECTS     {
        tmnxChassisNotifyHwIndex,
        tmnxHwID,
        tmnxHwClass
    }
    STATUS      current
    DESCRIPTION
        "The tmnxChassisAntiTheftUnlocked notification is generated to indicate
         that the system has successfully been unlocked following a reboot
         while Anti-Theft mode was enabled."
    ::= { tmnxChassisNotification 312 }

tmnxEqLowPowerSwFabModeEnabled   NOTIFICATION-TYPE
    STATUS      current
    DESCRIPTION
        "[CAUSE] The tmnxEqLowPowerSwFabModeEnabled event is generated when low
         power switch fabric mode is enabled.

         [EFFECT] SFMs are in power save mode and the switch fabric operates at
         a reduced capacity to save power.

         [RECOVERY] Disable the low power switch fabric mode configuration."
    ::= { tmnxChassisNotification 313 }

tmnxEqLowPowerSwFabModeDisabled  NOTIFICATION-TYPE
    STATUS      current
    DESCRIPTION
        "[CAUSE] The tmnxEqLowPowerSwFabModeDisabled event is generated when
         low power switch fabric mode is disabled.

         [EFFECT] SFMs are operational and the switch fabric is at full
         capacity."
    ::= { tmnxChassisNotification 314 }

tmnxChassisGoldenStatusEvent     NOTIFICATION-TYPE
    OBJECTS     {
        tmnxHwID,
        tmnxHwClass,
        tmnxChassisNotifyCpmCardSlotNum
    }
    STATUS      current
    DESCRIPTION
        "The tmnxChassisGoldenStatusEvent is sent when the backup BIOS update
         was unsuccessful. BIOS fails to program BACKUP or ACTIVE BIOS SPI
         FLASH."
    ::= { tmnxChassisNotification 315 }

tmnxEqFlashDiskFormatStart       NOTIFICATION-TYPE
    OBJECTS     {
        tmnxChassisNotifyHwIndex,
        tmnxHwID,
        tmnxHwClass,
        tmnxChassisNotifyDiskFormatType
    }
    STATUS      current
    DESCRIPTION
        "[CAUSE] The tmnxEqFlashDiskFormatStart notification is generated when
         a flash disk format or secure erase operation was initiated by a user.

         [EFFECT] The format or secure erase has started on the indicated flash
         disk."
    ::= { tmnxChassisNotification 318 }

tmnxEqFlashDiskFormatFinish      NOTIFICATION-TYPE
    OBJECTS     {
        tmnxChassisNotifyHwIndex,
        tmnxHwID,
        tmnxHwClass,
        tmnxChassisNotifyDiskFormatType
    }
    STATUS      current
    DESCRIPTION
        "[CAUSE] The tmnxEqFlashDiskFormatFinish notification is generated when
         a flash disk format or secure erase operation initiated by a user
         finished.

         [EFFECT] The indicated flash disk has been formatted or secured
         erased."
    ::= { tmnxChassisNotification 319 }

tmnxEsaColdRebooted              NOTIFICATION-TYPE
    OBJECTS     {
        tmnxEsaNotifyId
    }
    STATUS      current
    DESCRIPTION
        "The tmnxEsaColdRebooted notification is generated when an ESA performs
         a cold reboot.

         [CAUSE] The ESA has undergone a cold reboot, for example due to a
         power-cycle, a user-initiated forced cold-reboot action, or a
         hardware-initiated reset.

         [EFFECT] The ESA restarts in a fresh cold-boot state; any previously
         established session/state information is lost and the ESA begins its
         normal startup sequence."
    ::= { tmnxChassisNotification 320 }

tmnxChassisAntiTheftMismatch     NOTIFICATION-TYPE
    OBJECTS     {
        tmnxHwClass,
        tmnxChassisNotifyCpmCardSlotNum,
        tmnxChassisNotifyHwIndex
    }
    STATUS      current
    DESCRIPTION
        "[CAUSE] The tmnxChassisAntiTheftMismatch notification is generated
         when the anti-theft enabled state on the standby CPM does not match
         the anti-theft enabled state on the active CPM.

         [EFFECT] Redundant control plane anti-theft configuration is
         inconsistent, which may affect switchover behavior and security policy
         enforcement.

         [RECOVERY] Align anti-theft on both CPMs so the enabled state matches
         on the active and standby CPM."
    ::= { tmnxChassisNotification 325 }

tmnxChassisAntiTheftMismatchClr  NOTIFICATION-TYPE
    OBJECTS     {
        tmnxHwClass,
        tmnxChassisNotifyCpmCardSlotNum,
        tmnxChassisNotifyHwIndex
    }
    STATUS      current
    DESCRIPTION
        "[CAUSE] The tmnxChassisAntiTheftMismatchClr notification is generated
         when the anti-theft enabled state on the standby CPM and the
         anti-theft enabled state on the active CPM no longer mismatch.

         [EFFECT] The tmnxChassisAntiTheftMismatch notification is cleared.

         [RECOVERY] There is no recovery required for this notification."
    ::= { tmnxChassisNotification 326 }

END
